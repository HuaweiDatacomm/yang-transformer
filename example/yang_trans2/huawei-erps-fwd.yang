/*
Copyright (C) 2020 Huawei Technologies Co., Ltd. All rights reserved.
*/

 module huawei-erps-fwd {
   namespace "urn:huawei:yang:huawei-erps-fwd";
   prefix "erps-fwd";
   import huawei-extension {
     prefix "ext";
   }
   import huawei-erps {
     prefix "erps";
   }
   ext:task-name "erps";
   organization
     "Huawei Technologies Co., Ltd.";
   contact
     "Huawei Industrial Base\nBantian, Longgang\nShenzhen 518129\nPeople's "+
     "Republic of China\nWebsite: http://www.huawei.com\nEmail: support@huawei.c"+
     "om";
   description
     "Ethernet ring protection switching.";
   revision "2020-06-02" {
     description
       "Init revision.";
     reference
       "Huawei private.";
   }
   augment "/erps:erps/erps:rings/erps:ring" {
     description
       "ERPS ring configuration.";
     container fast-switch {
       description
         "Configure ERPS fast switch.";
       leaf force-bc-time {
         type "uint32" {
           range "0..30";
         }
         units "s";
         default "15";
         description
           "ERPS fast switch force broadcast time (in seconds), ranging from 0 "+
           "to 30.";
       }
     }
   }
 }

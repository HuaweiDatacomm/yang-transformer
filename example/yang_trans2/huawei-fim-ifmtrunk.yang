/*
Copyright (C) 2020 Huawei Technologies Co., Ltd. All rights reserved.
*/

 module huawei-fim-ifmtrunk {
   namespace "urn:huawei:yang:huawei-fim-ifmtrunk";
   prefix "fim-ifmtrunk";
   import huawei-ifm {
     prefix "ifm";
   }
   import huawei-ifm-trunk {
     prefix "ifm-trunk";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Common interface management, which includes the public configuration of "+
     "interfaces.";
   reference
     "Huawei private.";
   revision "2020-02-29" {
     description
       "Initial revision.";
     reference
       "Huawei private.";
   }
   ext:task-name "forwarding";
   typedef enable-type {
     type "enumeration" {
       enum "disable" {
         value "0";
         description
           "Disable.";
       }
       enum "enable" {
         value "1";
         description
           "Enable.";
       }
     }
     description
       "Enable type.";
   }
   augment "/ifm:ifm/ifm:interfaces/ifm:interface/ifm-trunk:trunk" {
     description
       "FIM configuration to the ifm module.";
     container fim-ifmtrunk {
       description
         "Configure the FIM configuration to Eth-Trunk interface.";
       leaf trunk-locality-flag {
         when "../../ifm-trunk:type='eth-trunk' or ../../ifm-trunk:type='ip-trun"+
              "k'";
         type "boolean";
         default "true";
         description
           "Enable/disable virtual-cluster trunk localization.";
       }
       leaf dual-receive-enable {
         when "../../ifm-trunk:type='eth-trunk' and ../../ifm-trunk:work-mode='b"+
              "ackup'";
         type "enable-type";
         default "disable";
         description
           "Enable the backup-dual-receiving function of the Eth-trunk "+
           "interface.";
       }
     }
   }
   augment "/ifm:ifm/ifm:interfaces/ifm:interface/ifm-trunk:trunk/ifm-trunk:memb"+
           "ers/ifm-trunk:member" {
     description
       "FIM configuration to the ifm module.";
     container fim-ifmtrunk-member {
       description
         "Configure the FIM configuration to trunk member interface.";
       leaf hash-index {
         when "../../../../ifm-trunk:hash-type='symmetric' or ../../../../ifm-tr"+
              "unk:hash-type ='symmetric-complement'";
         type "uint16" {
           range "1..64";
         }
         description
           "Hash index.";
       }
     }
   }
 }

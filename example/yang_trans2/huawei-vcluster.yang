/*
Copyright (C) 2019-2020 Huawei Technologies Co., Ltd. All rights reserved.
*/

 module huawei-vcluster {
   namespace "urn:huawei:yang:huawei-vcluster";
   prefix "vcluster";
   import huawei-network-instance {
     prefix "ni";
   }
   import ietf-inet-types {
     prefix "inet";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Configuration and Information of IPRAN Virtual Cluster Access.";
   revision "2020-07-11" {
     description
       "Add private syntax to the keychain name.";
     reference
       "Huawei private.";
   }
   revision "2020-03-20" {
     description
       "Fixed some problems.";
     reference
       "Huawei private.";
   }
   revision "2020-03-10" {
     description
       "Fixed some nodes description.";
     reference
       "Huawei private.";
   }
   revision "2019-11-13" {
     description
       "Initial revision.";
     reference
       "Huawei private.";
   }
   ext:task-name "virtual-cluster";
   typedef vc-role {
     type "enumeration" {
       enum "default" {
         value "0";
         description
           "Default is no configuration.";
       }
       enum "master" {
         value "1";
         description
           "Role of virtual cluster access is Master.";
       }
     }
     description
       "Role.";
   }
   container vcluster {
     description
       "Virtual Cluster Access.";
     container global {
       presence "Enable/disable vcluster function.";
       description
         "Configure basic function of virtural cluster.";
       leaf role {
         type "vc-role";
         default "default";
         description
           "Role of virtual cluster access. Include ap and master. Default is no"+
           " configuration.";
       }
       leaf admin-ip-address {
         type "inet:ip-address";
         description
           "Admin IP of virtual cluster access.";
       }
       leaf vpn-name {
         when "../admin-ip-address";
         type "leafref" {
           path "/ni:network-instance/ni:instances/ni:instance/ni:name";
         }
         must "../vpn-name='_public_'";
         default "_public_";
         description
           "VPN name.";
       }
       leaf keychain-name {
         type "string" {
           length "0..47";
           pattern "[^A-Z]+";
         }
         ext:case-sensitivity "lower-only";
         description
           "Keychain name.";
       }
       leaf vc-min-tx-interval {
         when "../role='master'";
         type "uint32" {
           range "3..1000";
         }
         units "ms";
         default "50";
         description
           "The minimum transmit interval of VC BFD.";
       }
       leaf vc-min-rx-interval {
         when "../role='master'";
         type "uint32" {
           range "3..1000";
         }
         units "ms";
         default "50";
         description
           "The minimum receive interval of VC BFD.";
       }
       leaf vc-detect-multiplier {
         when "../role='master'";
         type "uint32" {
           range "3..50";
         }
         default "3";
         description
           "Detection multiplier of VC BFD.";
       }
       leaf vc-bit-error-detection {
         when "../role='master'";
         type "boolean";
         default "false";
         description
           "Enable/disable VC bit error detection.";
       }
       leaf vp-min-rx-interval {
         when "../role='master'";
         type "uint32" {
           range "3..1000";
         }
         units "ms";
         default "10";
         description
           "The minimum receive interval of VP BFD.";
       }
       leaf vp-min-tx-interval {
         when "../role='master'";
         type "uint32" {
           range "3..1000";
         }
         units "ms";
         default "10";
         description
           "The minimum transmit interval of VP BFD.";
       }
       leaf vp-detect-multiplier {
         when "../role='master'";
         type "uint32" {
           range "3..50";
         }
         default "3";
         description
           "Detection multiplier of VP BFD.";
       }
       leaf vp-bit-error-detection {
         when "../role='master'";
         type "boolean";
         default "false";
         description
           "Enable/disable VP bit error detection.";
       }
     }
   }
 }

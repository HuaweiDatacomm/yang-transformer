/*
Copyright (C) 2020 Huawei Technologies Co., Ltd. All rights reserved.
*/

 module huawei-l2vpn-aps-notification {
   yang-version "1";
   namespace "urn:huawei:yang:huawei-l2vpn-aps-notification";
   prefix "l2vpn-aps-notification";
   import ietf-inet-types {
     prefix "inet";
   }
   import huawei-l2vpn {
     prefix "l2vpn";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of L2VPN-APS.";
   revision "2020-03-20" {
     description
       "Initial revision.";
     reference
       "Huawei private.";
   }
   ext:task-name "l2vpn";
   notification aps-tunnel-not-support {
     description
       "PW APS does not support the current public tunnel.";
     leaf vc-id {
       type "uint32";
       description
         "Identifier of the layer 2 virtual circuit.";
     }
     leaf vc-type {
       type "l2vpn:encapsulation-type";
       description
         "Encapsulation type of a L2VPN instance.";
     }
     leaf peer-address {
       type "inet:ipv4-address-no-zone";
       description
         "Peer IP address.";
     }
   }
   notification aps-tunnel-not-support-resume {
     description
       "The alarm that PW APS does not support the current public tunnel is "+
       "resumed.";
     leaf vc-id {
       type "uint32";
       description
         "Identifier of the layer 2 virtual circuit.";
     }
     leaf vc-type {
       type "l2vpn:encapsulation-type";
       description
         "Encapsulation type of a L2VPN instance.";
     }
     leaf peer-address {
       type "inet:ipv4-address-no-zone";
       description
         "Peer IP address.";
     }
   }
 }

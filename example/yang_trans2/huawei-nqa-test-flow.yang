/*
Copyright (C) 2021 Huawei Technologies Co., Ltd. All rights reserved.
*/

 submodule huawei-nqa-test-flow {
   yang-version "1";
   belongs-to huawei-nqa {
     prefix "nqa";
   }
   organization
     "Huawei Technologies Co., Ltd.";
   contact
     "Huawei Industrial Base\nBantian, Longgang\nShenzhen 518129\nPeople's "+
     "Republic of China\nWebsite: http://www.huawei.com\nEmail: support@huawei.c"+
     "om";
   description
     "Description of submodule nqa-instance.";
   revision "2021-04-29" {
     description
       "Init revision.";
     reference
       "Huawei private.";
   }
 }

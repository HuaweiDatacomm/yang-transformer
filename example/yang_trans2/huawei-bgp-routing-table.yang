/*
Copyright (C) 2019-2021 Huawei Technologies Co., Ltd. All rights reserved.
*/

 module huawei-bgp-routing-table {
   namespace "urn:huawei:yang:huawei-bgp-routing-table";
   prefix "bgp-rt";
   import huawei-bgp {
     prefix "bgp";
   }
   import huawei-extension {
     prefix "ext";
   }
   import ietf-inet-types {
     prefix "inet";
   }
   import huawei-pub-type {
     prefix "pub-type";
   }
   import huawei-network-instance {
     prefix "ni";
   }
   organization
     "Huawei Technologies Co., Ltd.";
   contact
     "Huawei Industrial Base\nBantian, Longgang\nShenzhen 518129\nPeople's "+
     "Republic of China\nWebsite: http://www.huawei.com\nEmail: support@huawei.c"+
     "om";
   description
     "Inter-AS routing protocol that exchanges Network Layer Reachability "+
     "Information (NLRI) with other BGP systems.";
   revision "2021-09-15" {
     description
       "The YANG descriptions are modified according to new standards.";
     reference
       "Huawei private.";
   }
   revision "2019-03-22" {
     description
       "Initial revision.";
     reference
       "Huawei private.";
   }
   ext:task-name "bgp";
   typedef bgp-origin-type {
     type "enumeration" {
       enum "igp" {
         value "1";
         description
           "IBGP route.";
       }
       enum "egp" {
         value "2";
         description
           "EBGP route.";
       }
       enum "incomplete" {
         value "3";
         description
           "Route whose source is unknown.";
       }
     }
     description
       "The origin of bgpcommon.";
   }
   typedef flapping-af-type {
     type "enumeration" {
       enum "ipv4uni" {
         value "1";
         description
           "IPv4 unicast address family.";
       }
       enum "ipv4multi" {
         value "2";
         description
           "IPv4 multicast address family.";
       }
       enum "ipv4vpn" {
         value "3";
         description
           "IPv4 VPN address family.";
       }
       enum "ipv4labeluni" {
         value "4";
         description
           "IPv4 labeled address family.";
       }
       enum "ipv6uni" {
         value "5";
         description
           "IPv6 unicast address family.";
       }
       enum "ipv6vpn" {
         value "6";
         description
           "IPv6 VPN address family.";
       }
     }
     description
       "The address family type of flapping.";
   }
   typedef bgp-external-flag-type {
     type "bits" {
       bit type5-ip-prefix {
         position "5";
         description
           "Ip prefix.";
       }
       bit type2-irb {
         position "13";
         description
           "IRB.";
       }
     }
     description
       "Route external flags.";
   }
   typedef hierarchy-convergence-type {
     type "enumeration" {
       enum "base" {
         value "1";
         description
           "Base route.";
       }
       enum "hierarchy" {
         value "2";
         description
           "Hierarchy route.";
       }
     }
     description
       "Hierarchy route flags.";
   }
   typedef bgp-route-type-flag {
     type "bits" {
       bit ibgp {
         description
           "IBGP route.";
       }
       bit ebgp {
         description
           "EBGP route.";
       }
       bit network {
         description
           "Network route.";
       }
       bit import {
         description
           "Imported route.";
       }
       bit auto-summary {
         description
           "Automatcially summarized route.";
       }
       bit aggregate {
         description
           "Aggregated route.";
       }
       bit cpri {
         description
           "Route received by CBGP from PD-BGP.";
       }
       bit pcri {
         description
           "Route received by PD-BGP from CBGP.";
       }
       bit suppressed {
         description
           "Suppressed.";
       }
       bit nhp-empty {
         description
           "NHP-empty.";
       }
       bit no-adv {
         description
           "Routes that are not advertised to other routers.";
       }
       bit local-cross {
         description
           "Locally crossed routes.";
       }
       bit remote-cross {
         description
           "Remotely crossed routes.";
       }
       bit vd-bgp {
         description
           "VD-BGP route.";
       }
       bit path-local {
         description
           "Path_Local route.";
       }
       bit path-gateway {
         description
           "Path_Gateway route.";
       }
       bit policy-nopass {
         description
           "Policy_NoPass route.";
       }
       bit supprenet {
         description
           "Supernet route.";
       }
       bit dampened {
         description
           "Dampened route.";
       }
       bit history {
         description
           "History route.";
       }
       bit select {
         description
           "Selected route.";
       }
       bit best {
         description
           "Best route.";
       }
       bit backup {
         description
           "Backup route.";
       }
       bit attr-change {
         description
           "ATTR_Change route.";
       }
       bit nhlfe-created {
         description
           "NHLFE_Created route.";
       }
       bit ilm-created {
         description
           "ILM_Created route.";
       }
       bit nexthop-change {
         description
           "Route whose next hop changed.";
       }
       bit invalid {
         description
           "Invalid route.";
       }
       bit source-change {
         description
           "Route whose source address changed.";
       }
       bit in-selectedq {
         description
           "Route in a selected queue.";
       }
       bit exitif-error {
         description
           "EXITIF_ERROR route.";
       }
       bit group-head {
         description
           "GROUP_HEAD route.";
       }
     }
     description
       "BGP-route-type-flag.";
   }
   typedef region-validation-result-type {
     type "enumeration" {
       enum "valid" {
         value "1";
         description
           "The BGP region validation result is valid.";
       }
       enum "invalid" {
         value "2";
         description
           "The BGP region validation result is invalid.";
       }
     }
     description
       "The type of BGP region validation result.";
   }
   augment "/bgp:bgp/bgp:base-process" {
     description
       "Top level container for BGP routes information.";
     container bgp-route {
       config "false";
       description
         "Statistics of BGP routes information.";
       container ipv4-unicast {
         config "false";
         description
           "Statistics of BGP routes information of IPv4-unicast address "+
           "family.";
         container routes {
           config "false";
           description
             "List of displayed route information in an address family.";
           list route {
             key "vpn-name route-distinguisher prefix mask-length route-type "+
                 "im-table-id from path-id";
             description
               "Statistics of routes.";
             leaf vpn-name {
               type "leafref" {
                 path "/ni:network-instance/ni:instances/ni:instance/ni:name";
               }
               description
                 "VPN name of a BGP instance.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf entropy-label-padding {
               type "string" {
                 length "1..50";
               }
               description
                 "The padding value of the entropy label attribute.";
             }
             leaf region-validation-result {
               type "region-validation-result-type";
               description
                 "BGP region validation result.";
             }
             leaf label-index {
               type "uint32";
               description
                 "Label index.";
             }
             leaf start-of-srgb {
               type "uint32";
               description
                 "Start of segment routing global block.";
             }
             leaf range-size-of-srgb {
               type "uint32";
               description
                 "Range size of segment routing global block.";
             }
             leaf attribute-index {
               type "leafref" {
                 path "/bgp:bgp/bgp:base-process/bgp-rt:bgp-route/bgp-rt:ipv4-un"+
                      "icast/bgp-rt:attributes/bgp-rt:attribute/bgp-rt:index";
               }
               description
                 "The ID of attribute.";
             }
           }
         }
         container peer-advertise-routes {
           config "false";
           description
             "List of displayed advertised route information in an address "+
             "family.";
           list peer-advertise-route {
             key "vpn-name remote-peer-address route-distinguisher prefix "+
                 "mask-length route-type im-table-id from path-id";
             description
               "Statistics of advertised routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf entropy-label-padding {
               type "string" {
                 length "1..50";
               }
               description
                 "The padding value of the entropy label attribute.";
             }
             leaf region-validation-result {
               type "region-validation-result-type";
               description
                 "BGP region validation result.";
             }
             leaf label-index {
               type "uint32";
               description
                 "Label index.";
             }
             leaf start-of-srgb {
               type "uint32";
               description
                 "Start of segment routing global block.";
             }
             leaf range-size-of-srgb {
               type "uint32";
               description
                 "Range size of segment routing global block.";
             }
             leaf attribute-index {
               type "leafref" {
                 path "/bgp:bgp/bgp:base-process/bgp-rt:bgp-route/bgp-rt:ipv4-un"+
                      "icast/bgp-rt:attributes/bgp-rt:attribute/bgp-rt:index";
               }
               description
                 "The ID of attribute.";
             }
           }
         }
         container peer-receive-routes {
           config "false";
           description
             "List of displayed received route information in an address "+
             "family.";
           list peer-receive-route {
             key "vpn-name remote-peer-address route-distinguisher prefix "+
                 "mask-length route-type im-table-id from path-id";
             description
               "Statistics of received routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf entropy-label-padding {
               type "string" {
                 length "1..50";
               }
               description
                 "The padding value of the entropy label attribute.";
             }
             leaf region-validation-result {
               type "region-validation-result-type";
               description
                 "BGP region validation result.";
             }
             leaf label-index {
               type "uint32";
               description
                 "Label index.";
             }
             leaf start-of-srgb {
               type "uint32";
               description
                 "Start of segment routing global block.";
             }
             leaf range-size-of-srgb {
               type "uint32";
               description
                 "Range size of segment routing global block.";
             }
             leaf attribute-index {
               type "leafref" {
                 path "/bgp:bgp/bgp:base-process/bgp-rt:bgp-route/bgp-rt:ipv4-un"+
                      "icast/bgp-rt:attributes/bgp-rt:attribute/bgp-rt:index";
               }
               description
                 "The ID of attribute.";
             }
           }
         }
         container peer-receive-active-routes {
           config "false";
           description
             "List of displayed received active route information in an address "+
             "family.";
           list peer-receive-active-route {
             key "vpn-name remote-peer-address route-distinguisher prefix "+
                 "mask-length route-type im-table-id from path-id";
             description
               "Statistics of received routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
           }
         }
         container attributes {
           description
             "List of attributes of BGP routes.";
           list attribute {
             key "index";
             description
               "BGP routes attributes state.";
             leaf index {
               type "uint64";
               description
                 "BGP route attribute id.";
             }
             leaf-list loop {
               type "string" {
                 length "1..30";
               }
               max-elements "4";
               description
                 "Statistics of loop attribute. Loop attribute is composed of "+
                 "paired vrfId and random.";
             }
           }
         }
         container statistics {
           description
             "List of BGP routes statistics information of IPv4-unicast address "+
             "family.";
           list statistic {
             key "vpn-name";
             description
               "BGP IPv4-unicast address family routes statistics.";
             leaf vpn-name {
               type "leafref" {
                 path "/ni:network-instance/ni:instances/ni:instance/ni:name";
               }
               description
                 "VPN name of a BGP instance.";
             }
             leaf total-number {
               type "uint32";
               description
                 "Total number of routes.";
             }
             leaf advertise-rm-total-number {
               type "uint32";
               description
                 "Total number of prefix advertised to RM.";
             }
             leaf active-route-number {
               type "uint32";
               description
                 "Total number of active route.";
             }
             leaf best-route-number {
               type "uint32";
               description
                 "Total number of best routes.";
             }
             leaf add-path-route-number {
               type "uint32";
               description
                 "Total number of add-path routes.";
             }
             leaf best-external-route-number {
               type "uint32";
               description
                 "Total number of best-external routes.";
             }
             leaf cidr-route-number {
               type "uint32";
               description
                 "Total number of cidr routes.";
             }
             leaf community-route-number {
               type "uint32";
               description
                 "Total number of community routes.";
             }
             leaf different-origin-as-route-number {
               type "uint32";
               description
                 "Total number of different-origin-as routes.";
             }
             leaf dampened-route-number {
               type "uint32";
               description
                 "Total number of dampened routes.";
             }
           }
         }
       }
       container ipv6-unicast {
         config "false";
         description
           "Statistics of BGP routes information of IPv6-unicast address "+
           "family.";
         container routes {
           config "false";
           description
             "List of displayed route information in an address family.";
           list route {
             key "vpn-name route-distinguisher prefix mask-length route-type "+
                 "im-table-id from path-id";
             description
               "Statistics of routes.";
             leaf vpn-name {
               type "leafref" {
                 path "/ni:network-instance/ni:instances/ni:instance/ni:name";
               }
               description
                 "VPN name of a BGP instance.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf region-validation-result {
               type "region-validation-result-type";
               description
                 "BGP region validation result.";
             }
             leaf attribute-index {
               type "leafref" {
                 path "/bgp:bgp/bgp:base-process/bgp-rt:bgp-route/bgp-rt:ipv6-un"+
                      "icast/bgp-rt:attributes/bgp-rt:attribute/bgp-rt:index";
               }
               description
                 "The ID of attribute.";
             }
           }
         }
         container peer-advertise-routes {
           config "false";
           description
             "List of displayed advertised route information in an address "+
             "family.";
           list peer-advertise-route {
             key "vpn-name remote-peer-address route-distinguisher prefix "+
                 "mask-length route-type im-table-id from path-id";
             description
               "Statistics of advertised routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf region-validation-result {
               type "region-validation-result-type";
               description
                 "BGP region validation result.";
             }
             leaf attribute-index {
               type "leafref" {
                 path "/bgp:bgp/bgp:base-process/bgp-rt:bgp-route/bgp-rt:ipv6-un"+
                      "icast/bgp-rt:attributes/bgp-rt:attribute/bgp-rt:index";
               }
               description
                 "The ID of attribute.";
             }
           }
         }
         container peer-receive-routes {
           config "false";
           description
             "List of displayed received route information in an address "+
             "family.";
           list peer-receive-route {
             key "vpn-name remote-peer-address route-distinguisher prefix "+
                 "mask-length route-type im-table-id from path-id";
             description
               "Statistics of received routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf region-validation-result {
               type "region-validation-result-type";
               description
                 "BGP region validation result.";
             }
             leaf attribute-index {
               type "leafref" {
                 path "/bgp:bgp/bgp:base-process/bgp-rt:bgp-route/bgp-rt:ipv6-un"+
                      "icast/bgp-rt:attributes/bgp-rt:attribute/bgp-rt:index";
               }
               description
                 "The ID of attribute.";
             }
           }
         }
         container peer-receive-active-routes {
           config "false";
           description
             "List of displayed received active route information in an address "+
             "family.";
           list peer-receive-active-route {
             key "vpn-name remote-peer-address route-distinguisher prefix "+
                 "mask-length route-type im-table-id from path-id";
             description
               "Statistics of received routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
           }
         }
         container attributes {
           description
             "List of attributes of BGP routes.";
           list attribute {
             key "index";
             description
               "BGP routes attributes state.";
             leaf index {
               type "uint64";
               description
                 "BGP route attribute id.";
             }
             leaf-list loop {
               type "string" {
                 length "1..30";
               }
               max-elements "4";
               description
                 "Statistics of loop attribute. Loop attribute is composed of "+
                 "paired vrfId and random.";
             }
           }
         }
         container statistics {
           description
             "List of BGP routes statistics information of IPv6-unicast address "+
             "family.";
           list statistic {
             key "vpn-name";
             description
               "BGP IPv6-unicast address family routes statistics.";
             leaf vpn-name {
               type "leafref" {
                 path "/ni:network-instance/ni:instances/ni:instance/ni:name";
               }
               description
                 "VPN name of a BGP instance.";
             }
             leaf total-number {
               type "uint32";
               description
                 "Total number of routes.";
             }
             leaf advertise-rm-total-number {
               type "uint32";
               description
                 "Total number of prefix advertised to RM.";
             }
             leaf active-route-number {
               type "uint32";
               description
                 "Total number of active route.";
             }
             leaf best-route-number {
               type "uint32";
               description
                 "Total number of best routes.";
             }
             leaf add-path-route-number {
               type "uint32";
               description
                 "Total number of add-path routes.";
             }
             leaf best-external-route-number {
               type "uint32";
               description
                 "Total number of best-external routes.";
             }
             leaf community-route-number {
               type "uint32";
               description
                 "Total number of community routes.";
             }
             leaf dampened-route-number {
               type "uint32";
               description
                 "Total number of dampened routes.";
             }
           }
         }
       }
       container ipv4-vpn {
         config "false";
         description
           "Statistics of BGP routes information of IPv4-VPN address family.";
         container routes {
           config "false";
           description
             "List of displayed route information in an address family.";
           list route {
             key "vpn-name route-distinguisher prefix mask-length route-type "+
                 "im-table-id from path-id";
             description
               "Statistics of routes.";
             leaf vpn-name {
               type "leafref" {
                 path "/ni:network-instance/ni:instances/ni:instance/ni:name";
               }
               description
                 "VPN name of a BGP instance.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf attribute-index {
               type "leafref" {
                 path "/bgp:bgp/bgp:base-process/bgp-rt:bgp-route/bgp-rt:ipv4-vp"+
                      "n/bgp-rt:attributes/bgp-rt:attribute/bgp-rt:index";
               }
               description
                 "The ID of attribute.";
             }
           }
         }
         container peer-advertise-routes {
           config "false";
           description
             "List of displayed advertised route information in an address "+
             "family.";
           list peer-advertise-route {
             key "vpn-name remote-peer-address route-distinguisher prefix "+
                 "mask-length route-type im-table-id from path-id";
             description
               "Statistics of advertised routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf attribute-index {
               type "leafref" {
                 path "/bgp:bgp/bgp:base-process/bgp-rt:bgp-route/bgp-rt:ipv4-vp"+
                      "n/bgp-rt:attributes/bgp-rt:attribute/bgp-rt:index";
               }
               description
                 "The ID of attribute.";
             }
           }
         }
         container peer-receive-routes {
           config "false";
           description
             "List of displayed received route information in an address "+
             "family.";
           list peer-receive-route {
             key "vpn-name remote-peer-address route-distinguisher prefix "+
                 "mask-length route-type im-table-id from path-id";
             description
               "Statistics of received routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf attribute-index {
               type "leafref" {
                 path "/bgp:bgp/bgp:base-process/bgp-rt:bgp-route/bgp-rt:ipv4-vp"+
                      "n/bgp-rt:attributes/bgp-rt:attribute/bgp-rt:index";
               }
               description
                 "The ID of attribute.";
             }
           }
         }
         container peer-receive-active-routes {
           config "false";
           description
             "List of displayed received active route information in an address "+
             "family.";
           list peer-receive-active-route {
             key "vpn-name remote-peer-address route-distinguisher prefix "+
                 "mask-length route-type im-table-id from path-id";
             description
               "Statistics of received routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
           }
         }
         container attributes {
           description
             "List of attributes of BGP routes.";
           list attribute {
             key "index";
             description
               "BGP routes attributes state.";
             leaf index {
               type "uint64";
               description
                 "BGP route attribute id.";
             }
             leaf-list loop {
               type "string" {
                 length "1..30";
               }
               max-elements "4";
               description
                 "Statistics of loop attribute. Loop attribute is composed of "+
                 "paired vrfId and random.";
             }
           }
         }
         container statistic {
           description
             "Statistics of BGP routes information of IPv4-VPN address family.";
           leaf total-number {
             type "uint32";
             description
               "Total number of routes.";
           }
           leaf active-route-number {
             type "uint32";
             description
               "Total number of active route.";
           }
           leaf best-route-number {
             type "uint32";
             description
               "Total number of best routes.";
           }
           leaf add-path-route-number {
             type "uint32";
             description
               "Total number of add-path routes.";
           }
           leaf best-external-route-number {
             type "uint32";
             description
               "Total number of best-external routes.";
           }
           leaf cidr-route-number {
             type "uint32";
             description
               "Total number of cidr routes.";
           }
           leaf community-route-number {
             type "uint32";
             description
               "Total number of community routes.";
           }
           leaf different-origin-as-route-number {
             type "uint32";
             description
               "Total number of different-origin-as routes.";
           }
           leaf dampened-route-number {
             type "uint32";
             description
               "Total number of dampened routes.";
           }
         }
       }
       container ipv6-vpn {
         config "false";
         description
           "Statistics of BGP routes information of IPv6-VPN address family.";
         container routes {
           config "false";
           description
             "List of displayed route information in an address family.";
           list route {
             key "vpn-name route-distinguisher prefix mask-length route-type "+
                 "im-table-id from path-id";
             description
               "Statistics of routes.";
             leaf vpn-name {
               type "leafref" {
                 path "/ni:network-instance/ni:instances/ni:instance/ni:name";
               }
               description
                 "VPN name of a BGP instance.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf attribute-index {
               type "leafref" {
                 path "/bgp:bgp/bgp:base-process/bgp-rt:bgp-route/bgp-rt:ipv6-vp"+
                      "n/bgp-rt:attributes/bgp-rt:attribute/bgp-rt:index";
               }
               description
                 "The ID of attribute.";
             }
           }
         }
         container peer-advertise-routes {
           config "false";
           description
             "List of displayed advertised route information in an address "+
             "family.";
           list peer-advertise-route {
             key "vpn-name remote-peer-address route-distinguisher prefix "+
                 "mask-length route-type im-table-id from path-id";
             description
               "Statistics of advertised routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf attribute-index {
               type "leafref" {
                 path "/bgp:bgp/bgp:base-process/bgp-rt:bgp-route/bgp-rt:ipv6-vp"+
                      "n/bgp-rt:attributes/bgp-rt:attribute/bgp-rt:index";
               }
               description
                 "The ID of attribute.";
             }
           }
         }
         container peer-receive-routes {
           config "false";
           description
             "List of displayed received route information in an address "+
             "family.";
           list peer-receive-route {
             key "vpn-name remote-peer-address route-distinguisher prefix "+
                 "mask-length route-type im-table-id from path-id";
             description
               "Statistics of received routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
             leaf attribute-index {
               type "leafref" {
                 path "/bgp:bgp/bgp:base-process/bgp-rt:bgp-route/bgp-rt:ipv6-vp"+
                      "n/bgp-rt:attributes/bgp-rt:attribute/bgp-rt:index";
               }
               description
                 "The ID of attribute.";
             }
           }
         }
         container peer-receive-active-routes {
           config "false";
           description
             "List of displayed received active route information in an address "+
             "family.";
           list peer-receive-active-route {
             key "vpn-name remote-peer-address route-distinguisher prefix "+
                 "mask-length route-type im-table-id from path-id";
             description
               "Statistics of received routes.";
             leaf vpn-name {
               type "leafref" {
                 path "/ni:network-instance/ni:instances/ni:instance/ni:name";
               }
               description
                 "VPN name of a BGP instance.";
             }
             leaf remote-peer-address {
               type "inet:ip-address-no-zone";
               description
                 "BGP neighbour address.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
           }
         }
         container attributes {
           description
             "List of attributes of BGP routes.";
           list attribute {
             key "index";
             description
               "BGP routes attributes state.";
             leaf index {
               type "uint64";
               description
                 "BGP route attribute id.";
             }
             leaf-list loop {
               type "string" {
                 length "1..30";
               }
               max-elements "4";
               description
                 "Statistics of loop attribute. Loop attribute is composed of "+
                 "paired vrfId and random.";
             }
           }
         }
         container statistic {
           description
             "Statistics of BGP routes information of IPv6-VPN address family.";
           leaf total-number {
             type "uint32";
             description
               "Total number of routes.";
           }
           leaf active-route-number {
             type "uint32";
             description
               "Total number of active route.";
           }
           leaf best-route-number {
             type "uint32";
             description
               "Total number of best routes.";
           }
           leaf add-path-route-number {
             type "uint32";
             description
               "Total number of add-path routes.";
           }
           leaf best-external-route-number {
             type "uint32";
             description
               "Total number of best-external routes.";
           }
           leaf community-route-number {
             type "uint32";
             description
               "Total number of community routes.";
           }
           leaf different-origin-as-route-number {
             type "uint32";
             description
               "Total number of different-origin-as routes.";
           }
         }
       }
       container ipv4-labeluni {
         config "false";
         description
           "Statistics of BGP routes information of IPv4-label-uni address "+
           "family.";
         container statistics {
           description
             "List of BGP routes statistics information of IPv4-label-uni "+
             "address family.";
           list statistic {
             key "vpn-name";
             description
               "BGP IPv4-label-uni address family routes statistics.";
             leaf vpn-name {
               type "leafref" {
                 path "/ni:network-instance/ni:instances/ni:instance/ni:name";
               }
               description
                 "VPN name of a BGP instance.";
             }
             leaf total-number {
               type "uint32";
               description
                 "Total number of routes.";
             }
             leaf advertise-rm-total-number {
               type "uint32";
               description
                 "Total number of prefix advertised to RM.";
             }
             leaf active-route-number {
               type "uint32";
               description
                 "Total number of active route.";
             }
             leaf best-route-number {
               type "uint32";
               description
                 "Total number of best routes.";
             }
             leaf add-path-route-number {
               type "uint32";
               description
                 "Total number of add-path routes.";
             }
             leaf best-external-route-number {
               type "uint32";
               description
                 "Total number of best-external routes.";
             }
             leaf cidr-route-number {
               type "uint32";
               description
                 "Total number of cidr routes.";
             }
             leaf community-route-number {
               type "uint32";
               description
                 "Total number of community routes.";
             }
             leaf different-origin-as-route-number {
               type "uint32";
               description
                 "Total number of different-origin-as routes.";
             }
             leaf dampened-route-number {
               type "uint32";
               description
                 "Total number of dampened routes.";
             }
           }
         }
       }
       container ipv4-multicast {
         config "false";
         description
           "Statistics of BGP routes information of IPv4-multicast address "+
           "family.";
         container routes {
           config "false";
           description
             "List of displayed route information in an address family.";
           list route {
             key "vpn-name route-distinguisher prefix mask-length route-type "+
                 "im-table-id from path-id";
             description
               "Statistics of routes.";
             leaf vpn-name {
               type "leafref" {
                 path "/ni:network-instance/ni:instances/ni:instance/ni:name";
               }
               description
                 "VPN name of a BGP instance.";
             }
             leaf route-distinguisher {
               type "string" {
                 length "1..22";
               }
               description
                 "Route distinguisher.";
             }
             leaf prefix {
               type "inet:ip-address-no-zone";
               description
                 "BGP route prefix.";
             }
             leaf mask-length {
               type "uint8";
               description
                 "Prefix mask length.";
             }
             leaf route-type {
               type "bgp-rt:bgp-route-type-flag";
               description
                 "Route type.";
             }
             leaf im-table-id {
               type "uint32";
               description
                 "ID of the routing table to which routes are imported.";
             }
             leaf from {
               type "inet:ip-address-no-zone";
               description
                 "Source peer that sends a route.";
             }
             leaf path-id {
               type "string" {
                 length "1..50";
               }
               description
                 "Path ID.";
             }
             leaf remote-nexthop-tunnel-address {
               type "inet:ip-address-no-zone";
               description
                 "The remote next hop tunnel address.";
             }
             leaf remote-nexthop-mac-address {
               type "pub-type:mac-address";
               description
                 "The remote next hop mac.";
             }
             leaf nexthop {
               type "inet:ip-address-no-zone";
               description
                 "Next hop address to which packets are forwarded.";
             }
             leaf local-preference {
               type "uint32";
               description
                 "Local priority. The attribute is only fit for the routes from "+
                 "IBGP peer, not suit for which of EBGP peer.";
             }
             leaf preferred-value {
               type "uint32";
               description
                 "Preferred value of a protocol.";
             }
             leaf preference {
               type "uint8";
               description
                 "Priority of BGP routes.";
             }
             leaf path-as {
               type "string" {
                 length "1..300";
               }
               description
                 "List of the AS_Paths that packets pass through.";
             }
             leaf origin {
               type "bgp-rt:bgp-origin-type";
               description
                 "Route origin.";
             }
             leaf med {
               type "uint32";
               description
                 "Route MED.The attribute is only fit for the routes from EBGP "+
                 "peer, not suit for which of IBGP peer.";
             }
             leaf flag-string {
               type "string" {
                 length "1..100";
               }
               description
                 "Route flag that contains a string of characters.";
             }
             leaf worse-reason {
               type "string" {
                 length "1..50";
               }
               description
                 "Reason why a route is not selected.";
             }
             leaf sending-peers {
               type "string" {
                 length "1..300";
               }
               description
                 "List of route sending peers.";
             }
             leaf time {
               type "pub-type:time-tick";
               description
                 "Time stamp of a route.";
             }
             leaf community {
               type "string" {
                 length "1..300";
               }
               description
                 "Community attribute.";
             }
             leaf large-community {
               type "string" {
                 length "1..200";
               }
               description
                 "Large-community attribute information.";
             }
             leaf ext-community {
               type "string" {
                 length "1..300";
               }
               description
                 "Extended community attribute.";
             }
             leaf interface-name {
               type "string" {
                 length "1..63";
               }
               description
                 "Name of the outbound interface of a route.";
             }
             leaf originator {
               type "inet:ip-address-no-zone";
               description
                 "Router ID of the route initiator.";
             }
             leaf cluster-list {
               type "string" {
                 length "1..300";
               }
               description
                 "List of cluster IDs.";
             }
             leaf remote-route-id {
               type "inet:ipv4-address-no-zone";
               description
                 "Router ID of a peer.";
             }
             leaf relay-nexthop {
               type "inet:ip-address-no-zone";
               description
                 "Next hop to which a route is iterated.";
             }
             leaf relay-tunnel-name {
               type "string" {
                 length "1..64";
               }
               description
                 "Name of a tunnel to which a route is iterated.";
             }
             leaf atomic-aggregate {
               type "boolean";
               description
                 "Route carrying the atomic-aggregate attribute.";
             }
             leaf aggregator-as {
               type "string" {
                 length "1..11";
               }
               description
                 "AS number of the route summarizer.";
             }
             leaf aggregator-id {
               type "inet:ip-address-no-zone";
               description
                 "ID of the route summarizer.";
             }
             leaf in-label {
               type "uint32";
               description
                 "In-label.";
             }
             leaf out-label {
               type "uint32";
               description
                 "Out-label.";
             }
             leaf iterated-vpn {
               type "string" {
                 length "1..31";
               }
               description
                 "Iterated vrf.";
             }
             leaf remote-nexthop-vni {
               type "uint32";
               description
                 "The remote next hop vni.";
             }
             leaf advertise-nexthop {
               type "inet:ip-address-no-zone";
               description
                 "Advertise next hop.";
             }
             leaf prefix-sid {
               type "string" {
                 length "1..60";
               }
               description
                 "PrefixSid attribute information of route.";
             }
             leaf aigp {
               type "uint64";
               description
                 "AIGP attribute information of route.";
             }
             leaf attribute-set {
               type "string" {
                 length "1..300";
               }
               description
                 "The attribute set information of route.";
             }
             leaf gateway-ip {
               type "inet:ip-address-no-zone";
               description
                 "Gateway IP address.";
             }
             leaf external-flags {
               type "bgp-rt:bgp-external-flag-type";
               description
                 "Route External Flags.";
             }
             leaf hierarchy-convergence-route-type {
               type "bgp-rt:hierarchy-convergence-type";
               description
                 "Hierarchy convergence route type.";
             }
             leaf hierarchy-route-relay-ip {
               when "../hierarchy-convergence-route-type='hierarchy'";
               type "inet:ip-address-no-zone";
               description
                 "BGP route prefix.";
             }
             leaf hierarchy-route-relay-ip-mask {
               when "../hierarchy-convergence-route-type='hierarchy'";
               type "uint8";
               description
                 "Prefix mask length.";
             }
           }
         }
         container statistic {
           description
             "Statistics of BGP routes information of IPv4-multicast address "+
             "family.";
           leaf total-number {
             type "uint32";
             description
               "Total number of routes.";
           }
           leaf advertise-rm-total-number {
             type "uint32";
             description
               "Total number of prefix advertised to RM.";
           }
           leaf active-route-number {
             type "uint32";
             description
               "Total number of active route.";
           }
           leaf dampened-route-number {
             type "uint32";
             description
               "Total number of dampened routes.";
           }
         }
       }
       container routing-flappings {
         config "false";
         description
           "List of displayed BGP route flapping information.";
         list routing-flapping {
           key "vpn-name address-family prefix mask-length";
           description
             "Statistics of BGP route flapping.";
           leaf vpn-name {
             type "leafref" {
               path "/ni:network-instance/ni:instances/ni:instance/ni:name";
             }
             description
               "VPN name of a BGP instance.";
           }
           leaf address-family {
             type "flapping-af-type";
             description
               "The address family type.";
           }
           leaf prefix {
             type "inet:ip-address-no-zone";
             description
               "The network address in the BGP routing table.";
           }
           leaf mask-length {
             type "uint8";
             description
               "Prefix mask length.";
           }
           leaf from {
             type "inet:ip-address-no-zone";
             description
               "IP address of the neighbor that receives routes.";
           }
           leaf origin {
             type "bgp-origin-type";
             description
               "The attributes of Origin.";
           }
           leaf flaps {
             type "uint16" {
               range "0..65535";
             }
             description
               "Total number of route flapping.";
           }
           leaf reuse-time {
             type "pub-type:time-tick";
             description
               "Reuse value.";
           }
           leaf duration-time {
             type "pub-type:time-tick";
             description
               "Total duration since the flapping happens.";
           }
         }
       }
     }
   }
 }

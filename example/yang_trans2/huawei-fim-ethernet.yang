/*
Copyright (C) 2020 Huawei Technologies Co., Ltd. All rights reserved.
*/

 module huawei-fim-ethernet {
   namespace "urn:huawei:yang:huawei-fim-ethernet";
   prefix "fim-ethernet";
   import huawei-ethernet {
     prefix "ethernet";
   }
   import huawei-ifm {
     prefix "ifm";
   }
   import huawei-extension {
     prefix "ext";
   }
   import huawei-ifm-trunk {
     prefix "ifm-trunk";
   }
   organization
     "Huawei Technologies Co., Ltd.";
   contact
     "Huawei Industrial Base\nBantian, Longgang\nShenzhen 518129\nPeople's "+
     "Republic of China\nWebsite: http://www.huawei.com\nEmail: support@huawei.c"+
     "om";
   description
     "Common interface management, which includes the public configuration of "+
     "interfaces.";
   reference
     "Huawei private.";
   revision "2020-03-11" {
     description
       "Initial revision.";
     reference
       "Huawei private.";
   }
   ext:task-name "forwarding";
   typedef enable-type {
     type "enumeration" {
       enum "disable" {
         value "0";
         description
           "Disable.";
       }
       enum "enable" {
         value "1";
         description
           "Enable.";
       }
     }
     description
       "Enable type.";
   }
   augment "/ifm:ifm/ifm:interfaces/ifm:interface/ethernet:ethernet/ethernet:l3-"+
           "sub-interface" {
     description
       "FIM configuration to the IFM module.";
     container mode-channel {
       when "(../ethernet:vlan-type-dot1q)";
       description
         "Configure the mode Channel sub-interface.";
       leaf mode-channel-enable {
         type "enable-type";
         default "disable";
         description
           "Enable or disable mode channel sub-interface.";
       }
       leaf bandwidth {
         when "../mode-channel-enable='enable'";
         type "uint32" {
           range "2..1000000000";
         }
         units "Mbit/s";
         default "2";
         description
           "Specify bandwidth of an mode channel sub-interface (Mbit/s).";
       }
     }
   }
   augment "/ifm:ifm/ifm:interfaces/ifm:interface/ethernet:ethernet/ethernet:mai"+
           "n-interface" {
     description
       "FIM configuration to the IFM module.";
     container fim-main {
       when "not((../../../ifm:name) = (/ifm:ifm/ifm:interfaces/ifm:interface/if"+
            "m-trunk:trunk/ifm-trunk:members/ifm-trunk:member/ifm-trunk:name)) "+
            "and ../../../ifm:type!='FlexE-200GE' and ../../../ifm:type!='FlexE-"+
            "50G' and ../../../ifm:type!='FlexE-100G' and ../../../ifm:type!='Fl"+
            "exE-10G' and ../../../ifm:type!='FlexE-400G' and ../../../ifm:type!"+
            "='FlexE-50|100G' and ../../../ifm:type!='Virtual-Ethernet' and "+
            "../../../ifm:type!='Tunnel' and ../../../ifm:type!='NULL' and "+
            "../../../ifm:type!='LoopBack' and ../../../ifm:type!='Global-VE' "+
            "and ../../../ifm:type!='Nve' and ../../../ifm:type!='Vbdif' and "+
            "../../../ifm:type!='Vlanif' and ../../../ifm:type!='PW-VE'";
       description
         "Configure the FIM configuration to the main interface.";
       leaf outer-vlan-enable {
         type "enable-type";
         default "disable";
         description
           "Modify one tag ethernet type.";
       }
     }
     container modechannel-main {
       when "not((../../../ifm:name) = (/ifm:ifm/ifm:interfaces/ifm:interface/if"+
            "m-trunk:trunk/ifm-trunk:members/ifm-trunk:member/ifm-trunk:name)) "+
            "and (../../../ifm:type='GigabitEthernet' or ../../../ifm:type='XGig"+
            "abitEthernet' or ../../../ifm:type='FlexE' or ../../../ifm:type='Et"+
            "h-Trunk' or ../../../ifm:type='10GE' or ../../../ifm:type='25GE' or"+
            " ../../../ifm:type='40GE' or ../../../ifm:type='50GE' or ../../../i"+
            "fm:type='50|100GE' or ../../../ifm:type='100GE' or ../../../ifm:typ"+
            "e='200GE' or ../../../ifm:type='400GE' or ../../../ifm:type='Ethern"+
            "et')";
       config "false";
       description
         "Statistics of the main interface that supports channelized sub-interfa"+
         "ces.";
       leaf remain-bandwidth {
         type "uint32";
         units "Mbit/s";
         description
           "Remaining bandwidth of the main interface.";
       }
     }
   }
   augment "/ifm:ifm/ifm:interfaces/ifm:interface/ethernet:ethernet/ethernet:l2-"+
           "sub-interface" {
     description
       "FIM configuration to the IFM module.";
     container fim-l2-sub {
       description
         "Configure the FIM configuration to L2 sub interface.";
       leaf egress-strict-filter {
         type "enable-type";
         description
           "Enable or disable strict filter on an EVC sub-interface.";
       }
     }
   }
 }

module ietf-inet-types {
   namespace "urn:ietf:params:xml:ns:yang:ietf-inet-types";
   prefix "inet";
   organization
     "IETF NETMOD (NETCONF Data Modeling Language) Working Group";
   contact
     "WG Web:   <http://tools.ietf.org/wg/netmod/>\nWG List:  <mailto:netmod@iet"+
     "f.org>\n\nWG Chair: David Kessens\n          <mailto:david.kessens@nsn.com"+
     ">\n\nWG Chair: Juergen Schoenwaelder\n          <mailto:j.schoenwaelder@ja"+
     "cobs-university.de>\n\nEditor:   Juergen Schoenwaelder\n          "+
     "<mailto:j.schoenwaelder@jacobs-university.de>";
   description
     "This module contains a collection of generally useful derived\nYANG data "+
     "types for Internet addresses and related things.\n\nCopyright (c) 2013 "+
     "IETF Trust and the persons identified as\nauthors of the code.  All rights"+
     " reserved.\n\nRedistribution and use in source and binary forms, with "+
     "or\nwithout modification, is permitted pursuant to, and subject\nto the "+
     "license terms contained in, the Simplified BSD License\nset forth in "+
     "Section 4.c of the IETF Trust's Legal Provisions\nRelating to IETF "+
     "Documents\n(http://trustee.ietf.org/license-info).\n\nThis version of this"+
     " YANG module is part of RFC 6991; see\nthe RFC itself for full legal "+
     "notices.";
   revision "2013-07-15" {
     description
       "This revision adds the following new data types:\n- ip-address-no-zone\n"+
       "- ipv4-address-no-zone\n- ipv6-address-no-zone";
     reference
       "RFC 6991: Common YANG Data Types";
   }
   revision "2010-09-24" {
     description
       "Initial revision.";
     reference
       "RFC 6021: Common YANG Data Types";
   }
   typedef ip-version {
     type "enumeration" {
       enum "unknown" {
         value "0";
         description
           "An unknown or unspecified version of the Internet\nprotocol.";
       }
       enum "ipv4" {
         value "1";
         description
           "The IPv4 protocol as defined in RFC 791.";
       }
       enum "ipv6" {
         value "2";
         description
           "The IPv6 protocol as defined in RFC 2460.";
       }
     }
     description
       "This value represents the version of the IP protocol.\n\nIn the value "+
       "set and its semantics, this type is equivalent\nto the InetVersion "+
       "textual convention of the SMIv2.";
     reference
       "RFC  791: Internet Protocol\nRFC 2460: Internet Protocol, Version 6 "+
       "(IPv6) Specification\nRFC 4001: Textual Conventions for Internet Network"+
       " Addresses";
   }
   typedef dscp {
     type "uint8" {
       range "0..63";
     }
     description
       "The dscp type represents a Differentiated Services Code Point\nthat may "+
       "be used for marking packets in a traffic stream.\nIn the value set and "+
       "its semantics, this type is equivalent\nto the Dscp textual convention "+
       "of the SMIv2.";
     reference
       "RFC 3289: Management Information Base for the Differentiated\n        "+
       "Services Architecture\nRFC 2474: Definition of the Differentiated "+
       "Services Field\n          (DS Field) in the IPv4 and IPv6 Headers\nRFC "+
       "2780: IANA Allocation Guidelines For Values In\n          the Internet "+
       "Protocol and Related Headers";
   }
   typedef port-number {
     type "uint16" {
       range "0..65535";
     }
     description
       "The port-number type represents a 16-bit port number of an\nInternet "+
       "transport-layer protocol such as UDP, TCP, DCCP, or\nSCTP.  Port numbers"+
       " are assigned by IANA.  A current list of\nall assignments is available "+
       "from <http://www.iana.org/>.\n\nNote that the port number value zero is "+
       "reserved by IANA.  In\nsituations where the value zero does not make "+
       "sense, it can\nbe excluded by subtyping the port-number type.\nIn the "+
       "value set and its semantics, this type is equivalent\nto the InetPortNum"+
       "ber textual convention of the SMIv2.";
     reference
       "RFC  768: User Datagram Protocol\nRFC  793: Transmission Control "+
       "Protocol\nRFC 4960: Stream Control Transmission Protocol\nRFC 4340: "+
       "Datagram Congestion Control Protocol (DCCP)\nRFC 4001: Textual "+
       "Conventions for Internet Network Addresses";
   }
   typedef ip-address {
     type "union" {
       type "inet:ipv4-address";
       type "inet:ipv6-address";
     }
     description
       "The ip-address type represents an IP address and is IP\nversion neutral."+
       "  The format of the textual representation\nimplies the IP version.  "+
       "This type supports scoped addresses\nby allowing zone identifiers in the"+
       " address format.";
     reference
       "RFC 4007: IPv6 Scoped Address Architecture";
   }
   typedef ipv4-address {
     type "string" {
       pattern "(([0-9]|[1-9][0-9]|1[0-9][0-9]|2[0-4][0-9]|25[0-5])\\.){3}([0-"+
               "9]|[1-9][0-9]|1[0-9][0-9]|2[0-4][0-9]|25[0-5])(%[\\p{N}\\p{L"+
               "}]+)?";
     }
     description
       "The ipv4-address type represents an IPv4 address in\ndotted-quad "+
       "notation.  The IPv4 address may include a zone\nindex, separated by a % "+
       "sign.\n\nThe zone index is used to disambiguate identical address\nvalue"+
       "s.  For link-local addresses, the zone index will\ntypically be the "+
       "interface index number or the name of an\ninterface.  If the zone index "+
       "is not present, the default\nzone of the device will be used.\n\nThe "+
       "canonical format for the zone index is the numerical\nformat";
   }
   typedef ipv6-address {
     type "string" {
       pattern "((:|[0-9a-fA-F]{0,4}):)([0-9a-fA-F]{0,4}:){0,5}((([0-9a-fA-F]{0,"+
               "4}:)?(:|[0-9a-fA-F]{0,4}))|(((25[0-5]|2[0-4][0-9]|[01]?[0-9]?[0-"+
               "9])\\.){3}(25[0-5]|2[0-4][0-9]|[01]?[0-9]?[0-9])))(%[\\p{N}"+
               "\\p{L}]+)?";
       pattern "(([^:]+:){6}(([^:]+:[^:]+)|(.*\\..*)))|((([^:]+:)*[^:]+)?::((["+
               "^:]+:)*[^:]+)?)(%.+)?";
     }
     description
       "The ipv6-address type represents an IPv6 address in full,\nmixed, "+
       "shortened, and shortened-mixed notation.  The IPv6\naddress may include "+
       "a zone index, separated by a % sign.\n\nThe zone index is used to "+
       "disambiguate identical address\nvalues.  For link-local addresses, the "+
       "zone index will\ntypically be the interface index number or the name of "+
       "an\ninterface.  If the zone index is not present, the default\nzone of "+
       "the device will be used.\n\n\n\nThe canonical format of IPv6 addresses "+
       "uses the textual\nrepresentation defined in Section 4 of RFC 5952.  "+
       "The\ncanonical format for the zone index is the numerical\nformat as "+
       "described in Section 11.2 of RFC 4007.";
     reference
       "RFC 4291: IP Version 6 Addressing Architecture\nRFC 4007: IPv6 Scoped "+
       "Address Architecture\nRFC 5952: A Recommendation for IPv6 Address Text\n"+
       "          Representation";
   }
   typedef ip-address-no-zone {
     type "union" {
       type "inet:ipv4-address-no-zone";
       type "inet:ipv6-address-no-zone";
     }
     description
       "The ip-address-no-zone type represents an IP address and is\nIP version "+
       "neutral.  The format of the textual representation\nimplies the IP "+
       "version.  This type does not support scoped\naddresses since it does not"+
       " allow zone identifiers in the\naddress format.";
     reference
       "RFC 4007: IPv6 Scoped Address Architecture";
   }
   typedef ipv4-address-no-zone {
     type "inet:ipv4-address" {
       pattern "[0-9\\.]*";
     }
     description
       "An IPv4 address without a zone index.  This type, derived from\nipv4-add"+
       "ress, may be used in situations where the zone is\nknown from the "+
       "context and hence no zone index is needed.";
   }
   typedef ipv6-address-no-zone {
     type "inet:ipv6-address" {
       pattern "[0-9a-fA-F:\\.]*";
     }
     description
       "An IPv6 address without a zone index.  This type, derived from\nipv6-add"+
       "ress, may be used in situations where the zone is\nknown from the "+
       "context and hence no zone index is needed.";
     reference
       "RFC 4291: IP Version 6 Addressing Architecture\nRFC 4007: IPv6 Scoped "+
       "Address Architecture\nRFC 5952: A Recommendation for IPv6 Address Text\n"+
       "          Representation";
   }
   typedef ipv4-prefix {
     type "string" {
       pattern "(([0-9]|[1-9][0-9]|1[0-9][0-9]|2[0-4][0-9]|25[0-5])\\.){3}([0-"+
               "9]|[1-9][0-9]|1[0-9][0-9]|2[0-4][0-9]|25[0-5])/(([0-9])|([1-2][0"+
               "-9])|(3[0-2]))";
     }
     description
       "The ipv4-prefix type represents an IPv4 address prefix.\nThe prefix "+
       "length is given by the number following the\nslash character and must be"+
       " less than or equal to 32.\n\nA prefix length value of n corresponds to "+
       "an IP address\nmask that has n contiguous 1-bits from the most\nsignific"+
       "ant bit (MSB) and all other bits set to 0.\n\nThe canonical format of an"+
       " IPv4 prefix has all bits of\nthe IPv4 address set to zero that are not "+
       "part of the\nIPv4 prefix.";
   }
   typedef ipv6-prefix {
     type "string" {
       pattern "((:|[0-9a-fA-F]{0,4}):)([0-9a-fA-F]{0,4}:){0,5}((([0-9a-fA-F]{0,"+
               "4}:)?(:|[0-9a-fA-F]{0,4}))|(((25[0-5]|2[0-4][0-9]|[01]?[0-9]?[0-"+
               "9])\\.){3}(25[0-5]|2[0-4][0-9]|[01]?[0-9]?[0-9])))(/(([0-9])|("+
               "[0-9]{2})|(1[0-1][0-9])|(12[0-8])))";
       pattern "(([^:]+:){6}(([^:]+:[^:]+)|(.*\\..*)))|((([^:]+:)*[^:]+)?::((["+
               "^:]+:)*[^:]+)?)(/.+)";
     }
     description
       "The ipv6-prefix type represents an IPv6 address prefix.\nThe prefix "+
       "length is given by the number following the\nslash character and must be"+
       " less than or equal to 128.\n\nA prefix length value of n corresponds to"+
       " an IP address\nmask that has n contiguous 1-bits from the most\nsignifi"+
       "cant bit (MSB) and all other bits set to 0.\n\nThe IPv6 address should "+
       "have all bits that do not belong\nto the prefix set to zero.\n\nThe "+
       "canonical format of an IPv6 prefix has all bits of\nthe IPv6 address set"+
       " to zero that are not part of the\nIPv6 prefix.  Furthermore, the IPv6 "+
       "address is represented\nas defined in Section 4 of RFC 5952.";
     reference
       "RFC 5952: A Recommendation for IPv6 Address Text\n        Representation"+
       "";
   }
   typedef domain-name {
     type "string" {
       pattern "((([a-zA-Z0-9_]([a-zA-Z0-9\\-_]){0,61})?[a-zA-Z0-9]\\.)*([a-"+
               "zA-Z0-9_]([a-zA-Z0-9\\-_]){0,61})?[a-zA-Z0-9]\\.?)|\\.";
       length "1..253";
     }
     description
       "The domain-name type represents a DNS domain name.  The\nname SHOULD be "+
       "fully qualified whenever possible.\n\nInternet domain names are only "+
       "loosely specified.  Section\n3.5 of RFC 1034 recommends a syntax "+
       "(modified in Section\n2.1 of RFC 1123).  The pattern above is intended "+
       "to allow\nfor current practice in domain name use, and some possible\nfu"+
       "ture expansion.  It is designed to hold various types of\ndomain names, "+
       "including names used for A or AAAA records\n(host names) and other "+
       "records, such as SRV records.  Note\nthat Internet host names have a "+
       "stricter syntax (described\nin RFC 952) than the DNS recommendations in "+
       "RFCs 1034 and\n1123, and that systems that want to store host names "+
       "in\nschema nodes using the domain-name type are recommended to\nadhere "+
       "to this stricter standard to ensure interoperability.\n\nThe encoding of"+
       " DNS names in the DNS protocol is limited\nto 255 characters.  Since the"+
       " encoding consists of labels\nprefixed by a length bytes and there is a "+
       "trailing NULL\nbyte, only 253 characters can appear in the textual "+
       "dotted\nnotation.\n\nThe description clause of schema nodes using the "+
       "domain-name\ntype MUST describe when and how these names are resolved "+
       "to\nIP addresses.  Note that the resolution of a domain-name value\nmay "+
       "require to query multiple DNS records (e.g., A for IPv4\nand AAAA for "+
       "IPv6).  The order of the resolution process and\nwhich DNS record takes "+
       "precedence can either be defined\nexplicitly or may depend on the "+
       "configuration of the\nresolver.\n\nDomain-name values use the US-ASCII "+
       "encoding.  Their canonical\nformat uses lowercase US-ASCII characters.  "+
       "Internationalized\ndomain names MUST be A-labels as per RFC 5890.";
     reference
       "RFC  952: DoD Internet Host Table Specification\nRFC 1034: Domain Names "+
       "- Concepts and Facilities\nRFC 1123: Requirements for Internet Hosts -- "+
       "Application\n          and Support\nRFC 2782: A DNS RR for specifying "+
       "the location of services\n          (DNS SRV)\nRFC 5890: Internationaliz"+
       "ed Domain Names in Applications\n          (IDNA): Definitions and "+
       "Document Framework";
   }
   typedef host {
     type "union" {
       type "inet:ip-address";
       type "inet:domain-name";
     }
     description
       "The host type represents either an IP address or a DNS\ndomain name.";
   }
   typedef uri {
     type "string";
     description
       "The uri type represents a Uniform Resource Identifier\n(URI) as defined "+
       "by STD 66.\n\nObjects using the uri type MUST be in US-ASCII encoding,\n"+
       "and MUST be normalized as described by RFC 3986 Sections\n6.2.1, "+
       "6.2.2.1, and 6.2.2.2.  All unnecessary\npercent-encoding is removed, and"+
       " all case-insensitive\ncharacters are set to lowercase except for "+
       "hexadecimal\ndigits, which are normalized to uppercase as described "+
       "in\nSection 6.2.2.1.\n\nThe purpose of this normalization is to help "+
       "provide\nunique URIs.  Note that this normalization is not\nsufficient "+
       "to provide uniqueness.  Two URIs that are\ntextually distinct after this"+
       " normalization may still be\nequivalent.\n\nObjects using the uri type "+
       "may restrict the schemes that\nthey permit.  For example, 'data:' and "+
       "'urn:' schemes\nmight not be appropriate.\n\nA zero-length URI is not a "+
       "valid URI.  This can be used to\nexpress 'URI absent' where required.\n"+
       "\nIn the value set and its semantics, this type is equivalent\nto the "+
       "Uri SMIv2 textual convention defined in RFC 5017.";
     reference
       "RFC 3986: Uniform Resource Identifier (URI): Generic Syntax\nRFC 3305: "+
       "Report from the Joint W3C/IETF URI Planning Interest\n          Group: "+
       "Uniform Resource Identifiers (URIs), URLs,\n          and Uniform "+
       "Resource Names (URNs): Clarifications\n          and Recommendations\nRF"+
       "C 5017: MIB Textual Conventions for Uniform Resource\n          "+
       "Identifiers (URIs)";
   }
 }

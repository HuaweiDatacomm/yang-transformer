/*
* Copyright (C) 2019 Huawei Technologies Co., Ltd. All rights reserved.
*/

 module huawei-extension {
   namespace "urn:huawei:yang:huawei-extension";
   prefix "ext";
   organization
     "Huawei Technologies Co., Ltd.";
   contact
     "Huawei Industrial Base\nBantian, Longgang\nShenzhen 518129\nPeople's "+
     "Republic of China\nWebsite: http://www.huawei.com\nEmail: support@huawei.c"+
     "om";
   description
     "Huawei private extensions to the YANG language.";
   revision "2019-12-13" {
     description
       "Add refine-ext, deviation-ext and deviate-ext.";
     reference
       "Huawei private.";
   }
   revision "2019-11-09" {
     description
       "Update example for generated-by.";
     reference
       "Huawei private.";
   }
   revision "2019-09-26" {
     description
       "Add new extensions.";
     reference
       "Huawei private.";
   }
   revision "2019-05-07" {
     description
       "Init revision.";
     reference
       "Huawei private.";
   }
   extension support-filter {
     argument value;
     description
       "The syntax indicates whether a non-key node supports filtering in list "+
       "or leaf-list node.\nThe key node does not need to define this syntax "+
       "because it must support filtering.\nThe options are as follows: true, "+
       "false. Default is false.";
   }
   extension value-replace {
     description
       "Value-replace.";
   }
   extension value-meaning {
     description
       "The syntax indicates meanings of some special values through using item "+
       "and meaning syntax.";
   }
   extension item {
     argument value;
     description
       "The syntax indicates one special value and it is substatement of "+
       "value-meaning. See value-meaning for usage.";
   }
   extension meaning {
     argument value;
     description
       "The syntax indicates meaning of the special value and it is substatement"+
       " of item. See value-meaning for usage.";
   }
   extension case-sensitivity {
     argument value;
     description
       "The syntax indicates case sensitivity of string type or its derived type"+
       " nodes.\nThe options are as follows:\n1. lower-and-upper: Server can "+
       "accept both lower and upper case, and it is case-sensitive when checking"+
       " uniqueness.\n2. lower-or-upper: Server can accept both lower and upper "+
       "case, and it is case-insensitive when checking uniqueness.\n3. "+
       "lower-only: Server can accept lower case only.\n4. upper-only: Server "+
       "can accept upper case only.\n5. lower2upper: Server transfers lower case"+
       " into upper case automatically.\n6. upper2lower: Server transfers upper "+
       "case into lower case automatically.\nDefault is lower-and-upper.";
   }
   extension masklen {
     argument value;
     description
       "The syntax indicates total number of bit for the node using pub-type:bit"+
       "s8/bits16/bits32/bits64 type.";
   }
   extension bit {
     argument value;
     description
       "The syntax indicates the name of one bit for the node using pub-type:bit"+
       "s8/bits16/bits32/bits64 type.\nSee masklen for usage.";
   }
   extension allowDelete {
     argument value;
     description
       "AllowDelete.";
   }
   extension value-range {
     argument value;
     description
       "The syntax indicates numerical range of value that can be entered using "+
       "id-range type or its derived type nodes.";
   }
   extension task-name {
     argument value;
     description
       "The syntax indicates which task the module belongs to and should be "+
       "defined before the root node.";
   }
   extension entry-from {
     argument value;
     description
       "Applies only to a list or presence container whose config is true. "+
       "entry-from specifies an instance to be automatically generated by the "+
       "system based on other data or to be created by a user.";
   }
   extension node-ref {
     argument value;
     description
       "The syntax indicates the xpath of the data node for which the rpc "+
       "operation is performed.\nIf the rpc operation is performed for the "+
       "entire system (the corresponding node cannot \nbe found in the model "+
       "tree), this syntax is not required.";
   }
   extension dynamic-default {
     description
       "The syntax indicates dynamic default value according to system or other "+
       "nodes.";
   }
   extension default-value {
     argument value;
     description
       "The syntax indicates one dynamic default value and it is substatement of"+
       " dynamic-default. See dynamic-default for usage.";
   }
   extension operation-exclude {
     argument value;
     description
       "The syntax indicates which operations are not supported.\nThe options "+
       "are as follows:\ncreate, delete, update and various combinations "+
       "separated by '|'.";
   }
   extension filter {
     argument value;
     description
       "The syntax indicates rules satisfying specific constraints and it is "+
       "substatement of operation-exclude or generated-by syntax.\nSee "+
       "operation-exclude or generated-by for usage.";
   }
   extension generated-by {
     argument value;
     description
       "The syntax indicates whether config datas are generated by the "+
       "system.\nThe options are as follows: system, user. Default is user.";
   }
   extension can-be-deleted {
     description
       "The syntax is used for the generated-by system scenario to indicate that"+
       " the deleted configuration data cannot be automatically restored.";
   }
   extension upper2lower {
     argument value;
     description
       "Convert upper-case letters to lower-case letters.";
   }
   extension refine-ext {
     argument value;
     description
       "The syntax is used to define a private syntax for a xpath node in an "+
       "extended manner, the value is xpath.";
   }
   extension deviation-ext {
     argument value;
     description
       "This syntax is used to tailor and customize multiple products for "+
       "private syntax, the value is XPath.";
   }
   extension deviate-ext {
     argument value;
     description
       "This syntax is used to tailor and customize multiple products for "+
       "private syntax, it is substatement of deviation-ext syntax,\nThe options"+
       " are as follows: add, delete, replace.\nSee deviation-ext for usage.";
   }
 }

/*
Copyright (C) 2021 Huawei Technologies Co., Ltd. All rights reserved.
*/

 submodule huawei-bgp-common-multiprotocol {
   yang-version "1";
   belongs-to huawei-bgp {
     prefix "bgp";
   }
   include huawei-bgp-type;
   organization
     "Huawei Technologies Co., Ltd.";
   contact
     "Huawei Industrial Base\nBantian, Longgang\nShenzhen 518129\nPeople's "+
     "Republic of China\nWebsite: http://www.huawei.com\nEmail: support@huawei.c"+
     "om";
   description
     "Inter-AS routing protocol that exchanges Network Layer Reachability "+
     "Information (NLRI) with other BGP systems.";
   revision "2021-02-03" {
     description
       "Initial revision.";
     reference
       "Huawei private.";
   }
 }

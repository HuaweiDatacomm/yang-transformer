/*
Copyright (C) 2020 Huawei Technologies Co., Ltd. All rights reserved.
*/

 module huawei-pcep {
   namespace "urn:huawei:yang:huawei-pcep";
   prefix "pcep";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Path Computation Element Communication (PCEP).";
   revision "2020-07-10" {
     description
       "Initial revision.";
     reference
       "Huawei private.";
   }
   ext:task-name "pce";
   container pcep {
     description
       "PCEP configuration.";
     container session-car {
       description
         "Configure session CAR.";
       container ipv4 {
         must "cir<=pir";
         must "cbs<=pbs";
         description
           "Configure PCEP IPv4 session CAR.";
         leaf enable {
           type "boolean";
           default "true";
           description
             "Enable/disable PCEP IPv4 session CAR.";
         }
         leaf cir {
           type "uint32" {
             range "1..1000000";
           }
           units "kbit/s";
           default "9";
           description
             "Session CAR CIR value.";
         }
         leaf cbs {
           type "uint32" {
             range "1..9000000";
           }
           units "Byte";
           default "1758";
           description
             "Session CAR CBS value.";
         }
         leaf pir {
           type "uint32" {
             range "1..1000000";
           }
           units "kbit/s";
           default "2400";
           description
             "Session CAR PIR value.";
         }
         leaf pbs {
           type "uint32" {
             range "1..9000000";
           }
           units "Byte";
           default "450000";
           description
             "Session CAR PBS value.";
         }
       }
     }
   }
 }

/*
Copyright (C) 2020 Huawei Technologies Co., Ltd. All rights reserved.
*/

 module huawei-oammgr {
   namespace "urn:huawei:yang:huawei-oammgr";
   prefix "oammgr";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Configure the operation, administration and maintenance (OAM) association "+
     "function.";
   revision "2020-09-18" {
     description
       "Initial revision.";
     reference
       "Huawei private.";
   }
   ext:task-name "oammgr";
   container oammgr {
     presence "Enable OAMMGR";
     description
       "Configure the operation, administration and maintenance (OAM) associatio"+
       "n function.";
   }
 }

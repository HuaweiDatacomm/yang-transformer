/*
Copyright (C) 2019 Huawei Technologies Co., Ltd. All rights reserved.
*/

 submodule huawei-diagnostic-tools-common {
   yang-version "1";
   belongs-to huawei-diagnostic-tools {
     prefix "diagnostic-tools";
   }
   organization
     "Huawei Technologies Co., Ltd.";
   contact
     "Huawei Industrial Base\nBantian, Longgang\nShenzhen 518129\nPeople's "+
     "Republic of China\nWebsite: http://www.huawei.com\nEmail: support@huawei.c"+
     "om";
   description
     "Diagnosis tool.";
   revision "2019-04-15" {
     description
       "Initial revision.";
     reference
       "Huawei private.";
   }
   container diagnostic-tools {
     config "false";
     description
       "Diagnosis tool, limited to ping and trace.";
   }
 }

module openconfig-telemetry {
   yang-version "1";
   namespace "http://openconfig.net/yang/telemetry";
   prefix "oc-telemetry";
   import openconfig-inet-types {
     prefix "oc-inet";
   }
   import openconfig-extensions {
     prefix "oc-ext";
   }
   import openconfig-telemetry-types {
     prefix "oc-telemetry-types";
   }
   organization
     "OpenConfig working group";
   contact
     "OpenConfig working group www.openconfig.net";
   description
     "Data model which creates the configuration for the telemetry\nsystems and "+
     "functions on the device.";
   oc-ext:openconfig-version "0.4.1";
   revision "2017-08-24" {
     description
       "Minor formatting fixes";
     reference
       "0.4.1";
   }
   revision "2017-02-20" {
     description
       "Fixes for YANG 1.0 compliance, add types module";
     reference
       "0.4.0";
   }
   revision "2016-04-05" {
     description
       "OpenConfig public release";
     reference
       "0.2.0";
   }
   container telemetry-system {
     description
       "Top level configuration and state for the\ndevice's telemetry system.";
     container sensor-groups {
       description
         "Top level container for sensor-groups.";
       list sensor-group {
         key "sensor-group-id";
         description
           "List of telemetry sensory groups on the local\nsystem, where a "+
           "sensor grouping represents a resuable\ngrouping of multiple paths "+
           "and exclude filters.";
         leaf sensor-group-id {
           type "leafref" {
             path "../config/sensor-group-id";
           }
           description
             "Reference to the name or identifier of the\nsensor grouping";
         }
         container config {
           description
             "Configuration parameters relating to the\ntelemetry sensor "+
             "grouping";
           leaf sensor-group-id {
             type "string" {
               length "1..64";
               pattern "[A-Za-z0-9]+";
             }
             description
               "Name or identifier for the sensor group itself.\nWill be "+
               "referenced by other configuration specifying a\nsensor group";
           }
         }
         container state {
           config "false";
           description
             "State information relating to the telemetry\nsensor group";
           leaf sensor-group-id {
             type "string" {
               length "1..64";
               pattern "[A-Za-z0-9]+";
             }
             description
               "Name or identifier for the sensor group itself.\nWill be "+
               "referenced by other configuration specifying a\nsensor group";
           }
         }
         container sensor-paths {
           description
             "Top level container to hold a set of sensor\npaths grouped "+
             "together";
           list sensor-path {
             key "path";
             description
               "List of paths in the model which together\ncomprise a sensor "+
               "grouping. Filters for each path\nto exclude items are also "+
               "provided.";
             leaf path {
               type "leafref" {
                 path "../config/path";
               }
               description
                 "Reference to the path of interest";
             }
             container config {
               description
                 "Configuration parameters to configure a set\nof data model "+
                 "paths as a sensor grouping";
               leaf path {
                 type "string" {
                   length "1..511";
                 }
                 description
                   "Path to a section of operational state of interest\n(the "+
                   "sensor).";
               }
             }
             container state {
               config "false";
               description
                 "Configuration parameters to configure a set\nof data model "+
                 "paths as a sensor grouping";
               leaf path {
                 type "string" {
                   length "1..511";
                 }
                 description
                   "Path to a section of operational state of interest\n(the "+
                   "sensor).";
               }
             }
           }
         }
       }
     }
     container destination-groups {
       description
         "Top level container for destination group configuration\nand state.";
       list destination-group {
         key "group-id";
         description
           "List of destination-groups. Destination groups allow the\nreuse of "+
           "common telemetry destinations across the\ntelemetry configuration. "+
           "An operator references a\nset of destinations via the configurable\n"+
           "destination-group-identifier.\n\nA destination group may contain one"+
           " or more telemetry\ndestinations";
         leaf group-id {
           type "leafref" {
             path "../config/group-id";
           }
           description
             "Unique identifier for the destination group";
         }
         container config {
           description
             "Top level config container for destination groups";
           leaf group-id {
             type "string" {
               length "1..64";
               pattern "[A-Za-z0-9]+";
             }
             description
               "Unique identifier for the destination group";
           }
         }
         container state {
           config "false";
           description
             "Top level state container for destination groups";
           leaf group-id {
             type "string" {
               length "1..64";
               pattern "[A-Za-z0-9]+";
             }
             description
               "Unique identifier for destination group";
           }
         }
         container destinations {
           description
             "The destination container lists the destination\ninformation such "+
             "as IP address and port of the\ntelemetry messages from the network"+
             " element.";
           list destination {
             key "destination-address destination-port";
             description
               "List of telemetry stream destinations";
             leaf destination-address {
               type "leafref" {
                 path "../config/destination-address";
               }
               description
                 "Reference to the destination address of the\ntelemetry stream";
             }
             leaf destination-port {
               type "leafref" {
                 path "../config/destination-port";
               }
               description
                 "Reference to the port number of the stream\ndestination";
             }
             container config {
               description
                 "Configuration parameters relating to\ntelemetry destinations";
               leaf destination-address {
                 type "oc-inet:ip-address";
                 description
                   "IP address of the telemetry stream destination";
               }
               leaf destination-port {
                 type "uint16" {
                   range "1..65535";
                 }
                 description
                   "Protocol (udp or tcp) port number for the telemetry\nstream "+
                   "destination";
               }
             }
             container state {
               config "false";
               description
                 "State information associated with\ntelemetry destinations";
               leaf destination-address {
                 type "oc-inet:ip-address";
                 description
                   "IP address of the telemetry stream destination";
               }
               leaf destination-port {
                 type "uint16" {
                   range "1..65535";
                 }
                 description
                   "Protocol (udp or tcp) port number for the telemetry\nstream "+
                   "destination";
               }
             }
           }
         }
       }
     }
     container subscriptions {
       description
         "This container holds information for both persistent\nand dynamic "+
         "telemetry subscriptions.";
       container persistent {
         description
           "This container holds information relating to persistent\ntelemetry "+
           "subscriptions. A persistent telemetry\nsubscription is configued "+
           "locally on the device through\nconfiguration, and is persistent "+
           "across device restarts or\nother redundancy changes.";
         list subscription {
           key "subscription-name";
           description
             "List of telemetry subscriptions. A telemetry\nsubscription "+
             "consists of a set of collection\ndestinations, stream attributes, "+
             "and associated paths to\nstate information in the model (sensor "+
             "data)";
           leaf subscription-name {
             type "leafref" {
               path "../config/subscription-name";
             }
             description
               "Reference to the identifier of the subscription\nitself. The id "+
               "will be the handle to refer to the\nsubscription once created";
           }
           container config {
             description
               "Config parameters relating to the telemetry\nsubscriptions on "+
               "the local device";
             leaf subscription-name {
               type "string" {
                 length "1..64";
                 pattern "[A-Za-z0-9]+";
               }
               description
                 "User configured identifier of the telemetry\nsubscription. "+
                 "This value is used primarily for\nsubscriptions configured "+
                 "locally on the network\nelement.";
             }
             leaf local-source-address {
               type "oc-inet:ip-address";
               description
                 "The IP address which will be the source of packets from\nthe "+
                 "device to a telemetry collector destination.";
             }
             leaf originated-qos-marking {
               type "oc-inet:dscp";
               description
                 "DSCP marking of packets generated by the telemetry\nsubsystem "+
                 "on the network device.";
               default "0";
             }
             leaf protocol {
               type "identityref" {
                 base "oc-telemetry-types:STREAM_PROTOCOL";
               }
               description
                 "Selection of the transport protocol for the telemetry\nstream."+
                 "";
             }
             leaf encoding {
               type "identityref" {
                 base "oc-telemetry-types:DATA_ENCODING_METHOD";
               }
               description
                 "Selection of the specific encoding or RPC framework\nfor "+
                 "telemetry messages to and from the network element.";
               default "oc-telemetry-types:ENC_PROTO3";
               must "(../oc-telemetry:encoding='oc-telemetry-types:ENC_PROTO3') "+
                    "or (../oc-telemetry:encoding='oc-telemetry-types:ENC_JSON_I"+
                    "ETF')";
             }
           }
           container state {
             config "false";
             description
               "State parameters relating to the telemetry\nsubscriptions on the"+
               " local device";
             leaf subscription-name {
               type "string" {
                 length "1..64";
                 pattern "[A-Za-z0-9]+";
               }
               description
                 "User configured identifier of the telemetry\nsubscription. "+
                 "This value is used primarily for\nsubscriptions configured "+
                 "locally on the network\nelement.";
             }
             leaf subscription-id {
               type "uint64";
               description
                 "System generated identifer of the telemetry\nsubscription.";
             }
             leaf local-source-address {
               type "oc-inet:ip-address";
               description
                 "The IP address which will be the source of packets from\nthe "+
                 "device to a telemetry collector destination.";
             }
             leaf originated-qos-marking {
               type "oc-inet:dscp";
               description
                 "DSCP marking of packets generated by the telemetry\nsubsystem "+
                 "on the network device.";
               default "0";
             }
             leaf protocol {
               type "identityref" {
                 base "oc-telemetry-types:STREAM_PROTOCOL";
               }
               description
                 "Selection of the transport protocol for the telemetry\nstream."+
                 "";
             }
             leaf encoding {
               type "identityref" {
                 base "oc-telemetry-types:DATA_ENCODING_METHOD";
               }
               description
                 "Selection of the specific encoding or RPC framework\nfor "+
                 "telemetry messages to and from the network element.";
               default "oc-telemetry-types:ENC_PROTO3";
               must "(../oc-telemetry:encoding='oc-telemetry-types:ENC_PROTO3') "+
                    "or (../oc-telemetry:encoding='oc-telemetry-types:ENC_JSON_I"+
                    "ETF')";
             }
           }
           container sensor-profiles {
             description
               "A sensor profile is a set of sensor groups or\nindividual sensor"+
               " paths which are associated with a\ntelemetry subscription. This"+
               " is the source of the\ntelemetry data for the subscription to "+
               "send to the\ndefined collectors.";
             list sensor-profile {
               key "sensor-group";
               description
                 "List of telemetry sensor groups used\nin the subscription";
               leaf sensor-group {
                 type "leafref" {
                   path "../config/sensor-group";
                 }
                 description
                   "Reference to the telemetry sensor group name";
               }
               container config {
                 description
                   "Configuration parameters related to the sensor\nprofile for "+
                   "a subscription";
                 leaf sensor-group {
                   type "leafref" {
                     path "../../../../../../../sensor-groups/sensor-group/confi"+
                          "g/sensor-group-id";
                   }
                   description
                     "Reference to the sensor group which is used in the "+
                     "profile";
                 }
                 leaf sample-interval {
                   type "uint64" {
                     range "0|10|100|1000|5000|10000|30000|60000|180000|300000|9"+
                           "00000|1800000";
                   }
                   description
                     "Time in milliseconds between the device's sample of "+
                     "a\ntelemetry data source. For example, setting this to "+
                     "100\nwould require the local device to collect the "+
                     "telemetry\ndata every 100 milliseconds. There can be "+
                     "latency or jitter\nin transmitting the data, but the "+
                     "sample must occur at\nthe specified interval.\n\nThe "+
                     "timestamp must reflect the actual time when the data\nwas "+
                     "sampled, not simply the previous sample timestamp "+
                     "+\nsample-interval.\n\nIf sample-interval is set to 0, the"+
                     " telemetry sensor\nbecomes event based. The sensor must "+
                     "then emit data upon\nevery change of the underlying data "+
                     "source.";
                   default "60000";
                 }
                 leaf heartbeat-interval {
                   type "uint64" {
                     range "1..60";
                   }
                   description
                     "Maximum time interval in seconds that may pass\nbetween "+
                     "updates from a device to a telemetry collector.\nIf this "+
                     "interval expires, but there is no updated data to\nsend "+
                     "(such as if suppress_updates has been configured), "+
                     "the\ndevice must send a telemetry message to the "+
                     "collector.";
                   must "(../oc-telemetry:sample-interval)";
                 }
                 leaf suppress-redundant {
                   type "boolean";
                   description
                     "Boolean flag to control suppression of redundant\ntelemetr"+
                     "y updates to the collector platform. If this flag is\nset "+
                     "to TRUE, then the collector will only send an update "+
                     "at\nthe configured interval if a subscribed data value "+
                     "has\nchanged. Otherwise, the device will not send an "+
                     "update to\nthe collector until expiration of the heartbeat"+
                     " interval.";
                   default "false";
                 }
                 must "not(heartbeat-interval) or sample-interval=0 or "+
                      "((heartbeat-interval*1000)mod(sample-interval)=0)";
               }
               container state {
                 config "false";
                 description
                   "State information relating to the sensor profile\nfor a "+
                   "subscription";
                 leaf sensor-group {
                   type "leafref" {
                     path "../../../../../../../sensor-groups/sensor-group/confi"+
                          "g/sensor-group-id";
                   }
                   description
                     "Reference to the sensor group which is used in the "+
                     "profile";
                 }
                 leaf sample-interval {
                   type "uint64" {
                     range "0|10|100|1000|5000|10000|30000|60000|180000|300000|9"+
                           "00000|1800000";
                   }
                   description
                     "Time in milliseconds between the device's sample of "+
                     "a\ntelemetry data source. For example, setting this to "+
                     "100\nwould require the local device to collect the "+
                     "telemetry\ndata every 100 milliseconds. There can be "+
                     "latency or jitter\nin transmitting the data, but the "+
                     "sample must occur at\nthe specified interval.\n\nThe "+
                     "timestamp must reflect the actual time when the data\nwas "+
                     "sampled, not simply the previous sample timestamp "+
                     "+\nsample-interval.\n\nIf sample-interval is set to 0, the"+
                     " telemetry sensor\nbecomes event based. The sensor must "+
                     "then emit data upon\nevery change of the underlying data "+
                     "source.";
                   default "60000";
                 }
                 leaf heartbeat-interval {
                   type "uint64" {
                     range "1..60";
                   }
                   description
                     "Maximum time interval in seconds that may pass\nbetween "+
                     "updates from a device to a telemetry collector.\nIf this "+
                     "interval expires, but there is no updated data to\nsend "+
                     "(such as if suppress_updates has been configured), "+
                     "the\ndevice must send a telemetry message to the "+
                     "collector.";
                   must "(../oc-telemetry:sample-interval)";
                 }
                 leaf suppress-redundant {
                   type "boolean";
                   description
                     "Boolean flag to control suppression of redundant\ntelemetr"+
                     "y updates to the collector platform. If this flag is\nset "+
                     "to TRUE, then the collector will only send an update "+
                     "at\nthe configured interval if a subscribed data value "+
                     "has\nchanged. Otherwise, the device will not send an "+
                     "update to\nthe collector until expiration of the heartbeat"+
                     " interval.";
                   default "false";
                 }
               }
             }
           }
           container destination-groups {
             description
               "A subscription may specify destination addresses.\nIf the "+
               "subscription supplies destination addresses,\nthe network "+
               "element will be the initiator of the\ntelemetry streaming, "+
               "sending it to the destination(s)\nspecified.\n\nIf the "+
               "destination set is omitted, the subscription\npreconfigures "+
               "certain elements such as paths and\nsample intervals under a "+
               "specified subscription ID.\nIn this case, the network element "+
               "will NOT initiate an\noutbound connection for telemetry, but "+
               "will wait for\nan inbound connection from a network management\n"+
               "system.\n\nIt is expected that the network management system\nco"+
               "nnecting to the network element will reference\nthe preconfigure"+
               "d subscription ID when initiating\na subscription.";
             list destination-group {
               key "group-id";
               description
                 "Identifier of the previously defined destination\ngroup";
               leaf group-id {
                 type "leafref" {
                   path "../config/group-id";
                 }
                 description
                   "The destination group id references a configured\ngroup of "+
                   "destinations for the telemetry stream.";
               }
               container config {
                 description
                   "Configuration parameters related to telemetry\ndestinations."+
                   "";
                 leaf group-id {
                   type "leafref" {
                     path "../../../../../../../destination-groups/destination-g"+
                          "roup/group-id";
                   }
                   description
                     "The destination group id references a reusable\ngroup of "+
                     "destination addresses and ports for\nthe telemetry "+
                     "stream.";
                 }
               }
               container state {
                 config "false";
                 description
                   "State information related to telemetry\ndestinations";
                 leaf group-id {
                   type "leafref" {
                     path "../../../../../../../destination-groups/destination-g"+
                          "roup/group-id";
                   }
                   description
                     "The destination group id references a reusable\ngroup of "+
                     "destination addresses and ports for\nthe telemetry "+
                     "stream.";
                 }
               }
             }
           }
         }
       }
     }
   }
 }

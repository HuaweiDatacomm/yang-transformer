/*
Copyright (C) 2019-2021 Huawei Technologies Co., Ltd. All rights reserved.
*/

 module huawei-devm-vnf {
   namespace "urn:huawei:yang:huawei-devm-vnf";
   prefix "devm-vnf";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Configuration management module.";
   revision "2021-04-26" {
     description
       "Add container vms.";
     reference
       "Huawei private.";
   }
   revision "2020-04-10" {
     description
       "Modify description warnings.";
     reference
       "Huawei private.";
   }
   revision "2019-07-01" {
     description
       "Initial revision.";
     reference
       "Huawei private.";
   }
   ext:task-name "device-mgr";
 }

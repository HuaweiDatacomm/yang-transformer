/*
Copyright (C) 2019-2021 Huawei Technologies Co., Ltd. All rights reserved.
*/

 module huawei-isis-srv6 {
   namespace "urn:huawei:yang:huawei-isis-srv6";
   prefix "isis-srv6";
   import huawei-network-instance {
     prefix "ni";
   }
   import huawei-isis {
     prefix "isis";
   }
   import huawei-srv6 {
     prefix "srv6";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "ISIS segment routing IPv6 management.";
   revision "2021-03-11" {
     description
       "Add container inter level protect etc.";
     reference
       "Huawei private.";
   }
   revision "2020-03-03" {
     description
       "Modify the description.";
     reference
       "Huawei private.";
   }
   revision "2020-02-04" {
     description
       "Modify the description.";
     reference
       "Huawei private.";
   }
   revision "2019-04-04" {
     description
       "Initial revision.";
     reference
       "Huawei private.";
   }
   ext:task-name "isis";
   augment "/ni:network-instance/ni:instances/ni:instance/isis:isis/isis:sites/i"+
           "sis:site/isis:afs/isis:af" {
     description
       "ISIS segment routing IPv6 augment to ISIS.";
     container srv6 {
       when "../../../../../../ni:name='_public_' and ../isis:type='afipv6' and "+
            "(../../../isis:cost-style='wide' or ../../../isis:cost-style='trans"+
            "ition'  or ../../../isis:cost-style='wtransition')";
       description
         "Configure ISIS segment routing IPv6.";
       container locators {
         description
           "List of segment routing IPv6 locator.";
         list locator {
           key "locator-name";
           description
             "Configure segment routing IPv6 locator.";
           leaf locator-name {
             type "leafref" {
               path "/ni:network-instance/ni:instances/ni:instance/srv6:srv6/srv"+
                    "6:locators/srv6:locator/srv6:name";
             }
             description
               "Enable ISIS segment routing IPv6 with specified Locator.";
           }
           leaf auto-sid {
             type "boolean";
             default "true";
             description
               "Enable/disable automatic application for SID.";
           }
         }
       }
       container avoid-microloop {
         when "../locators/locator";
         description
           "Configure IPv6 segment routing avoid microloop.";
         leaf enable {
           type "boolean";
           default "false";
           description
             "Enable/disable IPv6 segment routing avoid microloop.";
         }
         leaf delay-value {
           type "uint16" {
             range "1000..60000";
           }
           default "5000";
           description
             "Set the route delivery delay for IPv6 segment routing avoid "+
             "microloop.";
         }
       }
       container inter-level-protect {
         when "../../isis:frr/isis:enable='true' and ../locators/locator";
         description
           "Configure Inter-Level-Protect.";
         leaf enable-level1 {
           type "boolean";
           default "false";
           description
             "Enable/disable Level 1 Inter-Level-Protect.";
         }
         leaf preferred {
           type "boolean";
           must "../enable-level1='true' or ../preferred='false'";
           default "false";
           description
             "Enable/disable Inter-Level-Protect Preferred.";
         }
       }
     }
   }
 }

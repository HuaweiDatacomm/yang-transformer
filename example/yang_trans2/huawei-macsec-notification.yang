/*
Copyright (C) 2020 Huawei Technologies Co., Ltd. All rights reserved.
*/

 module huawei-macsec-notification {
   yang-version "1";
   namespace "urn:huawei:yang:huawei-macsec-notification";
   prefix "macsec-notification";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of macsec-notification.";
   revision "2020-04-01" {
     description
       "Add new nodes.";
     reference
       "Huawei private.";
   }
   revision "2020-02-20" {
     description
       "Initial revision.";
     reference
       "Huawei private.";
   }
   ext:task-name "macsec";
   typedef role-type {
     type "enumeration" {
       enum "client" {
         value "1";
         description
           "Client.";
       }
       enum "server" {
         value "2";
         description
           "Server.";
       }
     }
     description
       "Role type.";
   }
   notification macsec-ckn-switch-fail {
     description
       "If the CKN switchover fails or the switchover is not complete three "+
       "minutes later, an alarm is generated.";
     leaf if-index {
       type "uint32";
       description
         "Interface index.";
     }
     leaf role {
       type "role-type";
       description
         "Role.";
     }
     leaf local-port {
       type "string" {
         length "1..64";
       }
       description
         "Local port.";
     }
     leaf old-ckn {
       type "string" {
         length "1..65";
       }
       description
         "Old ckn.";
     }
     leaf new-ckn {
       type "string" {
         length "1..65";
       }
       description
         "New ckn.";
     }
     leaf switch-reason {
       type "string" {
         length "1..128";
       }
       description
         "Switch reason.";
     }
     leaf fail-reason {
       type "string" {
         length "1..128";
       }
       description
         "Fail reason.";
     }
   }
   notification macsec-receive-response-timeout {
     description
       "The MKA protocol status of the local interface becomes Down because the "+
       "response message cannot be received during the timeout period.";
     leaf if-index {
       type "uint32";
       description
         "Interface index.";
     }
     leaf role {
       type "role-type";
       description
         "Role.";
     }
     leaf local-port {
       type "string" {
         length "1..64";
       }
       description
         "Local port.";
     }
   }
   notification macsec-receive-response-timeout-resume {
     description
       "The MKA protocol status is restored or the MACSEC configuration is "+
       "deleted.";
     leaf if-index {
       type "uint32";
       description
         "Interface index.";
     }
     leaf role {
       type "role-type";
       description
         "Role.";
     }
     leaf local-port {
       type "string" {
         length "1..64";
       }
       description
         "Local port.";
     }
   }
 }

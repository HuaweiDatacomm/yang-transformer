/*
Copyright (C) 2019 Huawei Technologies Co., Ltd. All rights reserved.
*/

 module huawei-ospfv3-srv6 {
   namespace "urn:huawei:yang:huawei-ospfv3-srv6";
   prefix "ospfv3-srv6";
   import huawei-network-instance {
     prefix "ni";
   }
   import huawei-ospfv3 {
     prefix "ospfv3";
   }
   import huawei-srv6 {
     prefix "srv6";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "The YANG module defines generic configuration model for IPv6 Segment "+
     "Routing (SRv6) OSPFv3 extensions that are common across all of the vendor "+
     "implementations.";
   revision "2019-12-24" {
     description
       "Initial revision.";
     reference
       "Huawei private.";
   }
   ext:task-name "ospf";
   augment "/ni:network-instance/ni:instances/ni:instance/ospfv3:ospfv3/ospfv3:s"+
           "ites/ospfv3:site" {
     description
       "This augments OSPFv3 protocol configuration with SRv6.";
     container srv6 {
       when "../../../../ni:name='_public_'";
       description
         "Configure OSPFv3 IPv6 Segment Routing (SRv6).";
       container locators {
         description
           "List of the information about segment-routing IPv6 locators.";
         list locator {
           key "locator-name";
           description
             "Configure IPv6 Segment Routing (SRv6) locators.";
           leaf locator-name {
             type "leafref" {
               path "/ni:network-instance/ni:instances/ni:instance/srv6:srv6/srv"+
                    "6:locators/srv6:locator/srv6:name";
             }
             description
               "Enable OSPFv3 IPv6 Segment Routing (SRv6) with a specified "+
               "locator.";
           }
           leaf auto-sid {
             type "boolean";
             must "../auto-sid='false'";
             mandatory "true";
             description
               "Enable/disable dynamic SID allocation.";
           }
         }
       }
     }
   }
 }

/*
Copyright (C) 2019-2020 Huawei Technologies Co., Ltd. All rights reserved.
*/

 module huawei-software-notification {
   yang-version "1";
   namespace "urn:huawei:yang:huawei-software-notification";
   prefix "software-notification";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of software.";
   revision "2020-06-23" {
     description
       "Add Smart-Upgrade-User-Data-Retention-Period-Expired.";
     reference
       "Huawei private.";
   }
   revision "2020-06-11" {
     description
       "Add system-rollback.";
     reference
       "Huawei private.";
   }
   revision "2019-10-16" {
     description
       "Initial revision.";
     reference
       "Huawei private.";
   }
   ext:task-name "rpm";
   notification package-verify-failed {
     description
       "Package digital signature verification failed to be verified.";
     leaf physical-name {
       type "string" {
         length "1..31";
       }
       description
         "Entity name.";
     }
     leaf package-name {
       type "string" {
         length "4..127";
       }
       description
         "Software package name.";
     }
     leaf fail-reason {
       type "string" {
         length "1..127";
       }
       description
         "Error reason.";
     }
   }
   notification package-verify-failed-resume {
     description
       "Package digital signature verification succeeded to be verified.";
     leaf physical-name {
       type "string" {
         length "1..31";
       }
       description
         "Entity name.";
     }
     leaf package-name {
       type "string" {
         length "4..127";
       }
       description
         "Software package name.";
     }
     leaf fail-reason {
       type "string" {
         length "1..127";
       }
       description
         "Error reason.";
     }
   }
   notification startup-secure-version-configuration-need-refresh {
     description
       "The secure boot version configuration needs to be updated.";
     leaf slot-id {
       type "string" {
         length "1..49";
       }
       description
         "Slot ID.";
     }
   }
   notification startup-secure-version-configuration-need-refresh-resume {
     description
       "The secure boot version configuration is successfully updated.";
     leaf slot-id {
       type "string" {
         length "1..49";
       }
       description
         "Slot ID.";
     }
   }
   notification system-rollback {
     description
       "Upgraded software fails to start the system, and the software rolls back"+
       " to the old version.";
     leaf package-name {
       type "string" {
         length "4..127";
       }
       description
         "The software package name before the rollback.";
     }
     leaf version {
       type "string" {
         length "1..63";
       }
       description
         "The version before the rollback.";
     }
     leaf fail-reason {
       type "string" {
         length "1..127";
       }
       description
         "Error reason.";
     }
   }
   notification smart-upgrade-user-data-retention-period-expired {
     description
       "The smart-upgrade user data retention period has expired.";
   }
   notification smart-upgrade-user-data-retention-period-expired-resume {
     description
       "The smart-upgrade user data is updated.";
   }
 }

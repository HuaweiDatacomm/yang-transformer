module openconfig-inet-types {
   yang-version "1";
   namespace "http://openconfig.net/yang/types/inet";
   prefix "oc-inet";
   import openconfig-extensions {
     prefix "oc-ext";
   }
   organization
     "OpenConfig working group";
   contact
     "OpenConfig working group\nwww.openconfig.net";
   description
     "This module contains a set of Internet address related\ntypes for use in "+
     "OpenConfig modules.\n\nPortions of this code were derived from IETF RFC "+
     "6021.\nPlease reproduce this note if possible.\n\nIETF code is subject to "+
     "the following copyright and license:\nCopyright (c) IETF Trust and the "+
     "persons identified as authors of\nthe code.\nAll rights reserved.\n\nRedis"+
     "tribution and use in source and binary forms, with or without\nmodificatio"+
     "n, is permitted pursuant to, and subject to the license\nterms contained "+
     "in, the Simplified BSD License set forth in\nSection 4.c of the IETF "+
     "Trust's Legal Provisions Relating\nto IETF Documents (http://trustee.ietf."+
     "org/license-info).";
   oc-ext:openconfig-version "0.3.3";
   revision "2019-04-25" {
     description
       "Fix regex bug for ipv6-prefix type";
     reference
       "0.3.3";
   }
   revision "2018-11-21" {
     description
       "Add OpenConfig module metadata extensions.";
     reference
       "0.3.2";
   }
   revision "2017-08-24" {
     description
       "Minor formatting fixes.";
     reference
       "0.3.1";
   }
   revision "2017-07-06" {
     description
       "Add domain-name and host typedefs";
     reference
       "0.3.0";
   }
   revision "2017-04-03" {
     description
       "Add ip-version typedef.";
     reference
       "0.2.0";
   }
   revision "2017-04-03" {
     description
       "Update copyright notice.";
     reference
       "0.1.1";
   }
   revision "2017-01-26" {
     description
       "Initial module for inet types";
     reference
       "0.1.0";
   }
   oc-ext:regexp-posix;
   oc-ext:catalog-organization "openconfig";
   oc-ext:origin "openconfig";
   typedef ipv4-address {
     type "string" {
       pattern "^(([0-9]|[1-9][0-9]|1[0-9][0-9]|2[0-4][0-9]|25[0-5])\\.){3}([0"+
               "-9]|[1-9][0-9]|1[0-9][0-9]|2[0-4][0-9]|25[0-5])$";
     }
     description
       "An IPv4 address in dotted quad notation using the default\nzone.";
   }
   typedef ipv6-address {
     type "string" {
       pattern "^(([0-9a-fA-F]{1,4}:){7}[0-9a-fA-F]{1,4}|([0-9a-fA-F]{1,4}:){1,7"+
               "}:|([0-9a-fA-F]{1,4}:){1,6}:[0-9a-fA-F]{1,4}|([0-9a-fA-F]{1,4}:)"+
               "{1,5}(:[0-9a-fA-F]{1,4}){1,2}|([0-9a-fA-F]{1,4}:){1,4}(:[0-9a-fA"+
               "-F]{1,4}){1,3}|([0-9a-fA-F]{1,4}:){1,3}(:[0-9a-fA-F]{1,4}){1,4}|"+
               "([0-9a-fA-F]{1,4}:){1,2}(:[0-9a-fA-F]{1,4}){1,5}|[0-9a-fA-F]{1,4"+
               "}:((:[0-9a-fA-F]{1,4}){1,6})|:((:[0-9a-fA-F]{1,4}){1,7}|:))$";
     }
     description
       "An IPv6 address represented as either a full address; shortened\nor "+
       "mixed-shortened formats, using the default zone.";
   }
   typedef ipv4-prefix {
     type "string" {
       pattern "^(([0-9]|[1-9][0-9]|1[0-9][0-9]|2[0-4][0-9]|25[0-5])\\.){3}([0"+
               "-9]|[1-9][0-9]|1[0-9][0-9]|2[0-4][0-9]|25[0-5])/(([0-9])|([1-2]["+
               "0-9])|(3[0-2]))$";
     }
     description
       "An IPv4 prefix represented in dotted quad notation followed by\na slash "+
       "and a CIDR mask (0 <= mask <= 32).";
   }
   typedef ipv6-prefix {
     type "string" {
       pattern "^(([0-9a-fA-F]{1,4}:){7}[0-9a-fA-F]{1,4}|([0-9a-fA-F]{1,4}:){1,7"+
               "}:|([0-9a-fA-F]{1,4}:){1,6}:[0-9a-fA-F]{1,4}|([0-9a-fA-F]{1,4}:)"+
               "{1,5}(:[0-9a-fA-F]{1,4}){1,2}|([0-9a-fA-F]{1,4}:){1,4}(:[0-9a-fA"+
               "-F]{1,4}){1,3}|([0-9a-fA-F]{1,4}:){1,3}(:[0-9a-fA-F]{1,4}){1,4}|"+
               "([0-9a-fA-F]{1,4}:){1,2}(:[0-9a-fA-F]{1,4}){1,5}|[0-9a-fA-F]{1,4"+
               "}:((:[0-9a-fA-F]{1,4}){1,6})|:((:[0-9a-fA-F]{1,4}){1,7}|:))/(12["+
               "0-8]|1[0-1][0-9]|[1-9][0-9]|[0-9])$";
     }
     description
       "An IPv6 prefix represented in full, shortened, or mixed\nshortened "+
       "format followed by a slash and CIDR mask\n(0 <= mask <= 128).";
   }
   typedef ip-address {
     type "union" {
       type "ipv4-address";
       type "ipv6-address";
     }
     description
       "An IPv4 or IPv6 address with no prefix specified.";
   }
   typedef ip-prefix {
     type "union" {
       type "ipv4-prefix";
       type "ipv6-prefix";
     }
     description
       "An IPv4 or IPv6 prefix.";
   }
   typedef domain-name {
     type "string" {
       length "1..253";
       pattern "((([a-zA-Z0-9_]([a-zA-Z0-9\\-_]){0,61})?[a-zA-Z0-9]\\.)*([a-"+
               "zA-Z0-9_]([a-zA-Z0-9\\-_]){0,61})?[a-zA-Z0-9]\\.?)|\\.";
     }
     description
       "The domain-name type represents a DNS domain name.\nFully quallified "+
       "left to the models which utilize this type.\n\nInternet domain names are"+
       " only loosely specified.  Section\n3.5 of RFC 1034 recommends a syntax "+
       "(modified in Section\n2.1 of RFC 1123).  The pattern above is intended "+
       "to allow\nfor current practice in domain name use, and some possible\nfu"+
       "ture expansion.  It is designed to hold various types of\ndomain names, "+
       "including names used for A or AAAA records\n(host names) and other "+
       "records, such as SRV records.  Note\nthat Internet host names have a "+
       "stricter syntax (described\nin RFC 952) than the DNS recommendations in "+
       "RFCs 1034 and\n1123, and that systems that want to store host names "+
       "in\nschema nodes using the domain-name type are recommended to\nadhere "+
       "to this stricter standard to ensure interoperability.\n\nThe encoding of"+
       " DNS names in the DNS protocol is limited\nto 255 characters.  Since the"+
       " encoding consists of labels\nprefixed by a length bytes and there is a "+
       "trailing NULL\nbyte, only 253 characters can appear in the textual "+
       "dotted\nnotation.\n\nDomain-name values use the US-ASCII encoding.  "+
       "Their canonical\nformat uses lowercase US-ASCII characters.  Internation"+
       "alized\ndomain names MUST be encoded in punycode as described in "+
       "RFC\n3492";
   }
   typedef as-number {
     type "uint32";
     description
       "A numeric identifier for an autonomous system (AS). An AS is a\nsingle "+
       "domain, under common administrative control, which forms\na unit of "+
       "routing policy. Autonomous systems can be assigned a\n2-byte identifier,"+
       " or a 4-byte identifier which may have public\nor private scope. Private"+
       " ASNs are assigned from dedicated\nranges. Public ASNs are assigned from"+
       " ranges allocated by IANA\nto the regional internet registries (RIRs).";
     reference
       "RFC 1930 Guidelines for creation, selection, and registration\n       of"+
       " an Autonomous System (AS)\nRFC 4271 A Border Gateway Protocol 4 "+
       "(BGP-4)";
   }
   typedef dscp {
     type "uint8" {
       range "0..63";
     }
     description
       "A differentiated services code point (DSCP) marking within the\nIP "+
       "header.";
     reference
       "RFC 2474 Definition of the Differentiated Services Field\n        (DS "+
       "Field) in the IPv4 and IPv6 Headers";
   }
 }

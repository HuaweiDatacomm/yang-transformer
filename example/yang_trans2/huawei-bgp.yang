/*
Copyright (C) 2019-2021 Huawei Technologies Co., Ltd. All rights reserved.
*/

 module huawei-bgp {
   namespace "urn:huawei:yang:huawei-bgp";
   prefix "bgp";
   import huawei-extension {
     prefix "ext";
   }
   import ietf-inet-types {
     prefix "inet";
   }
   import ietf-yang-types {
     prefix "yang";
   }
   import huawei-network-instance {
     prefix "ni";
   }
   import huawei-pub-type {
     prefix "pub-type";
   }
   import huawei-routing-policy {
     prefix "rtp";
   }
   import huawei-routing {
     prefix "rt";
   }
   import huawei-ssl {
     prefix "ssl";
   }
   import huawei-tunnel-management {
     prefix "tnlm";
   }
   import huawei-l3vpn {
     prefix "l3vpn";
   }
   import huawei-ifm {
     prefix "ifm";
   }
   import huawei-socket {
     prefix "socket";
   }
   import huawei-xpl {
     prefix "xpl";
   }
   import huawei-acl {
     prefix "acl";
   }
   include huawei-bgp-type;
   include huawei-bgp-common;
   include huawei-bgp-common-multiprotocol;
   organization
     "Huawei Technologies Co., Ltd.";
   contact
     "Huawei Industrial Base\nBantian, Longgang\nShenzhen 518129\nPeople's "+
     "Republic of China\nWebsite: http://www.huawei.com\nEmail: support@huawei.c"+
     "om";
   description
     "Inter-AS routing protocol that exchanges Network Layer Reachability "+
     "Information (NLRI) with other BGP systems.";
   revision "2021-08-11" {
     description
       "The YANG descriptions are modified according to new standards.";
     reference
       "Huawei private.";
   }
   revision "2021-02-03" {
     description
       "Add bgp common multiprotocol submodule.";
     reference
       "Huawei private.";
   }
   revision "2020-02-25" {
     description
       "The YANG descriptions are modified according to new standards.";
     reference
       "Huawei private.";
   }
   revision "2019-03-22" {
     description
       "Initial revision.";
     reference
       "Huawei private.";
   }
   ext:task-name "bgp";
   container bgp {
     description
       "Inter-AS routing protocol that exchanges Network Layer Reachability "+
       "Information (NLRI) with other BGP systems,\nUniversal BGP configurations"+
       " that contain the basic BGP configurations and the query information.";
     container global {
       description
         "Configure the router for BGP globally.";
       leaf yang-enable {
         type "boolean";
         default "false";
         description
           "Enable/disable BGP yang mode. To use NETCONF YANG to manage BGP VPN "+
           "instances in huawei-bgp.yang, enable YANG management for the BGP VPN"+
           " instances on the device or enable the leaf node globally in the "+
           "huawei-bgp.yang file.";
       }
       leaf memory-overload-exception-discard-route {
         type "boolean";
         default "false";
         description
           "Enable/disable BGP to discard routes received from all peers if the "+
           "memory usage of a device is abnormal.";
       }
     }
     container paf-controls {
       description
         "List of PAF-based limiting disabled for some features.";
       list paf-control {
         key "feature-name";
         description
           "Configure PAF-based limiting disabled for some features.";
         leaf feature-name {
           type "paf-control-feature-type";
           description
             "Feature name.";
         }
       }
     }
     container session-car {
       must "pir-value >= cir-value and pbs-value >= cbs-value";
       description
         "Configure session CAR.";
       leaf enable {
         type "boolean";
         default "true";
         description
           "Enable/disable session CAR.";
       }
       leaf cir-value {
         type "uint32" {
           range "12..1200";
         }
         units "kbit/s";
         default "24";
         description
           "Specify the session CAR CIR value.";
       }
       leaf cbs-value {
         type "uint32" {
           range "15000..1500000";
         }
         units "Byte";
         default "15000";
         description
           "Specify the session CAR CBS value.";
       }
       leaf pir-value {
         type "uint32" {
           range "12000..60000";
         }
         units "kbit/s";
         default "48000";
         description
           "Specify the session CAR PIR value.";
       }
       leaf pbs-value {
         type "uint32" {
           range "1500000..7500000";
         }
         units "Byte";
         default "6000000";
         description
           "Specify the session CAR PBS value.";
       }
     }
     container micro-car {
       must "pir-value >= cir-value and pbs-value >= cbs-value";
       description
         "Configure micro CAR.";
       leaf enable {
         type "boolean";
         default "true";
         description
           "Enable/disable micro CAR.";
       }
       leaf cir-value {
         type "uint32" {
           range "12..1200";
         }
         units "kbit/s";
         default "24";
         description
           "Specify the micro CAR CIR value.";
       }
       leaf cbs-value {
         type "uint32" {
           range "15000..1500000";
         }
         units "Byte";
         default "15000";
         description
           "Specify the micro CAR CBS value.";
       }
       leaf pir-value {
         type "uint32" {
           range "12000..60000";
         }
         units "kbit/s";
         default "48000";
         description
           "Specify the micro CAR PIR value.";
       }
       leaf pbs-value {
         type "uint32" {
           range "1500000..7500000";
         }
         units "Byte";
         default "6000000";
         description
           "Specify the micro CAR PBS value.";
       }
     }
     container base-process {
       description
         "Configure the global BGP information, such as the protocol version, AS"+
         " number, and system identifier.";
       leaf enable {
         type "boolean";
         must "(../enable='true' and ../as) or (../enable='false' and not(../as)"+
              ")";
         default "false";
         description
           "Enable/disable BGP function.";
       }
       leaf as {
         when "../enable='true'";
         type "as-number-validate";
         description
           "Local AS number, which can be in either of the two formats:\nThe "+
           "two-byte format is X. X is an integer ranging from 1 to 65535.\nThe "+
           "four-byte format is X.Y and X. When the format is X.Y, X and Y are "+
           "both integers, with the value of X ranging from 1 to 65535, and the "+
           "value of Y ranging from 0 to 65535; when the format is X, X is an "+
           "interger, with the value ranging from 1 to 4294967295.\nAn AS "+
           "consists of multiple routers managed based on the same techniques. "+
           "Interior Gateway Protocol (IGP) and universal routing metric packets"+
           " are used inside an AS, and Exterior Gateway Protocol (EGP) is used "+
           "outside to send packets to other ASs. With the development of this "+
           "definition, one AS usually uses multiple IGPs and metrics. Even "+
           "though multiple IGPs and metrics are used, the routing plan and "+
           "destination reachability of an AS are consistent with those of "+
           "another AS. The local AS number cannot be configured same as the "+
           "confederation sub-ASs. The object cannot be deleted or modified.";
         ext:operation-exclude "update" {
           description
             "The node cannot be modified when BGP is enabled.";
         }
       }
       leaf keep-all-routes {
         when "../enable='true'";
         type "boolean";
         default "false";
         description
           "Enable/disable saving all the updated information about BGP routes "+
           "from a peer or peer group after a BGP connection is established, "+
           "even though these BGP routes fail to match the routing policy on the"+
           " ingress. Save all the updated information about BGP routes from a "+
           "peer or peer group after a BGP connection is established, even "+
           "though these BGP routes fail to match the routing policy on the "+
           "ingress. By default, only the updated information about BGP routes "+
           "from a specified peer is saved on condition that the routes match "+
           "the routing policy on the ingress. If a router supports route "+
           "refreshing, this option is not required.";
       }
       leaf check-first-as {
         when "../enable='true'";
         type "boolean";
         default "true";
         description
           "Enable/disable checking the first AS in the AS_Path of the update "+
           "messages from EBGP peers.";
       }
       leaf router-id-auto-select {
         when "../enable='true'";
         type "boolean";
         default "false";
         description
           "Enable/disable router ID auto select. If a BGP VPN instance is not "+
           "enabled to select a router ID, a router ID can be configured for the"+
           " BGP VPN instance. If no router ID is configured for the BGP VPN "+
           "instance, the BGP VPN instance inherits the router ID of the public "+
           "network instance. If a BGP VPN instance is enabled to select a "+
           "router ID, it uses the address of an interface bound to a VPN as the"+
           " router ID based on the following rules: \n1. If Loopback interfaces"+
           " configured with IP addresses exist, the largest IP address among "+
           "the IP addresses of the Loopback interfaces is selected as the "+
           "router ID. \n2. If there is no Loopback interface configured with an"+
           " IP address, the largest IP address among the IP addresses of other "+
           "interfaces is selected as the router ID, regardless of whether the "+
           "interface is Up.";
       }
       leaf shutdown {
         when "../enable='true'";
         type "boolean";
         default "false";
         description
           "Enable/disable interrupting BGP all neighbour.";
       }
       leaf local-ifnet-mtu {
         when "../enable='true'";
         type "uint16" {
           range "46..65535";
         }
         default "1500";
         description
           "BGP LOCALIFNET MTU.";
       }
       leaf private-4byte-as {
         when "../enable='true'";
         type "boolean";
         default "false";
         description
           "Enable/disable BGP private 4 byte AS. With BGP private-4-byte-as, "+
           "BGP private as is from 64512 to 65535 and from 4200000000 to "+
           "4294967294.";
       }
       leaf local-cross-no-med {
         when "../enable='true'";
         type "boolean";
         default "false";
         description
           "Enable/disable local cross routing non-med.";
       }
       leaf as-path-limit {
         when "../enable='true'";
         type "uint16" {
           range "1..2000";
         }
         description
           "Maximum number of AS numbers in the AS_Path attribute.";
       }
       leaf dynamic-session-limit {
         when "../enable='true'";
         ext:dynamic-default;
         type "uint32" {
           range "1..16000";
         }
         description
           "Upper limit on the number of dynamic peer sessions.";
       }
       leaf route-loop-detect-enable {
         type "boolean";
         default "false";
         description
           "Enable/disable BGP route loop-detect control.";
       }
       container confederation {
         when "../enable='true'";
         description
           "Configure confederation.";
         leaf id {
           type "as-number-validate";
           description
             "Configure the confederation ID.";
         }
         leaf nonstanded {
           type "boolean";
           default "false";
           description
             "Enable/disable nonstanded. Configure the device to be compatible "+
             "with devices in a nonstandard confederation.";
         }
         leaf-list as {
           when "../id";
           type "as-number-validate";
           max-elements "32";
           description
             "Configure the confederation AS number. The confederation AS number"+
             " can be in either of the two formats:\nThe two-byte format is X. X"+
             " is an integer ranging from 1 to 65535.\nThe four-byte format is "+
             "X.Y and X. When the format is X.Y, X and Y are both integers, with"+
             " the value of X ranging from 1 to 65535, and the value of Y "+
             "ranging from 0 to 65535; when the format is X, X is an interger, "+
             "with the value of X ranging from 1 to 4294967295. The confederatio"+
             "n sub-ASs cannot be configured same as the local AS number.";
         }
       }
       container graceful-restart {
         when "../enable='true'";
         description
           "Configure the graceful-restart.";
         leaf enable {
           type "boolean";
           default "false";
           description
             "Enable/disable GR of the BGP speaker in the specified address "+
             "family, peer address, or peer group. When GR is enabled, the BGP "+
             "speaker enabled with GR keeps the forwarding state and sends the "+
             "End-Of-RIB flag during the restart. In this case, however, the BGP"+
             " speaker may not maintain the forwarding table. Enabling or "+
             "disabling GR may delete and re-establish all sessions and "+
             "instances.";
         }
         leaf time-wait-for-rib {
           type "uint32" {
             range "3..3000";
           }
           units "s";
           default "600";
           description
             "Period of waiting for the End-Of-RIB flag. The value is an "+
             "integer. When a BGP session is established or re-established, the "+
             "router enabled with GR should receive the End-Of-RIB flag in this "+
             "period. If the router does not receive the End-Of-RIB flag in this"+
             " period, ensure that the router can exit from the GR process.";
         }
         leaf restart-time {
           type "uint16" {
             range "3..3600";
           }
           units "s";
           default "150";
           description
             "Specifies the maximum time during which a peer waits for a BGP "+
             "session reestablishment.";
         }
         leaf peer-reset {
           type "boolean";
           default "false";
           description
             "Enable/disable peer disconnection through GR.";
         }
       }
       container remote-prefix-sid-states {
         config "false";
         description
           "List of remote prefix SID.";
         list remote-prefix-sid-state {
           key "prefix-sid";
           description
             "Operational state of the remote BGP prefix SID.";
           leaf prefix-sid {
             type "inet:ipv6-address-no-zone";
             description
               "Prefix SID value.";
           }
           leaf locator-sid {
             type "inet:ipv6-address-no-zone";
             description
               "Prefix SID value of the mirrored locator.";
           }
           leaf locator-mask-length {
             type "uint8" {
               range "0..128";
             }
             description
               "Mask length of the SID of the mirrored locator.";
           }
           leaf vpn-name {
             type "string" {
               length "1..31";
             }
             description
               "Name of the VPN instance that contains the prefix SID.";
           }
         }
       }
       container reference-period {
         when "../enable='true'";
         must "hold-interval>suppress-interval";
         must "clear-interval>hold-interval";
         description
           "Configure the reference period.";
         leaf suppress-interval {
           type "uint32" {
             range "1..65535";
           }
           units "s";
           default "60";
           description
             "Specifies the reference period used to add penalty in case of next"+
             " hop flapping.";
         }
         leaf hold-interval {
           type "uint32" {
             range "1..65535";
           }
           units "s";
           default "120";
           description
             "Specifies the reference period used to hold penalty in case of "+
             "next hop flapping.";
         }
         leaf clear-interval {
           type "uint32" {
             range "1..65535";
           }
           units "s";
           default "600";
           description
             "Specifies the reference period used to clear penalty in case of "+
             "next hop flapping.";
         }
       }
       container timer {
         when "../enable='true'";
         description
           "Configure BGP global timer parameters.";
         leaf connect-retry-time {
           type "uint16" {
             range "1..65535";
           }
           units "s";
           default "32";
           description
             "ConnectRetry interval.";
         }
         leaf keep-alive-time {
           type "uint32" {
             range "0..21845";
           }
           units "s";
           must "(../keep-alive-time != 0 and (../hold-time>=../keep-alive-time "+
                "* 3) and ../hold-time != ../keep-alive-time ) or (../hold-time "+
                "= 0 and ../keep-alive-time = 0)";
           default "60";
           description
             "Specify the Keepalive time of a peer or peer group. The value is "+
             "an integer. If the value of a timer changes, the peers need to "+
             "re-negotiate the interval value for the keepalive-time and "+
             "hold-time. This disconnects the BGP peer relationship between the "+
             "routers. Therefore, you need to double check whether it is a must "+
             "to change the value of the timer. Ensure that the hold time is at "+
             "least three times longer than the keepalive time when you "+
             "configure the BGP timer.";
         }
         leaf hold-time {
           type "uint32" {
             range "0 | 3..65535";
           }
           units "s";
           must "(((../hold-time>=../keep-alive-time * 3) and ../hold-time != "+
                "../keep-alive-time ) or (../hold-time = 0 and ../keep-alive-tim"+
                "e = 0)) and ../hold-time>=../min-hold-time";
           default "180";
           description
             "Specify the Hold time of a peer or peer group. When setting the "+
             "timer values of keepalive-time and hold-time, avoid the following "+
             "settings: 1.The interval values of keepalive-time and hold-time "+
             "are both set to 0. This will cause BGP timer to become invalid, "+
             "and BGP will not detect link faults based on the timer.\n2. The "+
             "interval value of hold-time is much greater than that of "+
             "keepalive-time. For example, the interval value of keepalive-time "+
             "is 1, and that of hold-time is 65535. If the interval value of "+
             "hold-time is too large, BGP will not be able to detect link faults"+
             " in time. The priority of the timer configured here is lower than "+
             "that of timer configured with interval values of keepalive-time "+
             "and hold-time of a peer. After a connection is established between"+
             " peers, the interval values of keepalive-time and hold-time are "+
             "negotiated by the peers. The smaller interval value of hold-time "+
             "contained in Open packets of both peers is taken as the interval "+
             "value of hold-time. The smaller interval value of one third of the"+
             " interval value of hold-time and the locally set interval value of"+
             " keepalive-time is taken as the interval value of keepalive-time.";
         }
         leaf min-hold-time {
           type "uint32" {
             range "0 | 20..65535";
           }
           units "s";
           must "../hold-time>=../min-hold-time";
           default "0";
           description
             "The default value of zero means that the minimum hold time check "+
             "does not take effect. If the value is changed, the new value takes"+
             " effect since the next peer relationship establishment. During the"+
             " peer relationship establishment, the local device checks the hold"+
             " time of the remote end. If the hold time is less than the minimum"+
             " hold time, the local device sends an error packet with error code"+
             " 02 and subcode 06, and the peer relationship fails to be "+
             "established.";
         }
       }
       container graceful-restart-status {
         config "false";
         description
           "Statistics of the GR status of a BGP speaker.";
         leaf enable {
           type "boolean";
           description
             "The GR capability of a BGP speaker.";
         }
         leaf restart-timer {
           type "uint32";
           units "s";
           description
             "Period during which a BGP speaker waits for the peer relationship "+
             "reestablishment.";
         }
         leaf eor-timer {
           type "uint32";
           units "s";
           description
             "Period during which a BGP speaker waits for the End-Of-RIB flag.";
         }
         container peers {
           description
             "List of display the GR statistics for a BGP peer.";
           list peer {
             key "vpn-name af address";
             description
               "Statistics of the GR status of a BGP peer.";
             leaf vpn-name {
               type "string" {
                 length "1..31";
               }
               description
                 "VPN name of a BGP instance.";
             }
             leaf af {
               type "string" {
                 length "1..300";
               }
               description
                 "BGP address-family type.";
             }
             leaf address {
               type "inet:ip-address-no-zone";
               description
                 "Address of a peer.";
             }
             leaf peer-capability {
               type "string" {
                 length "1..300";
               }
               description
                 "GR capability of a neighbor.";
             }
             leaf gr-capability-enable {
               type "boolean";
               description
                 "Whether GR capability is negotiated.";
             }
             leaf bgp-peer-state {
               type "bgp:peer-state-type";
               description
                 "Status of the peer.";
             }
             leaf gr-state {
               type "boolean";
               description
                 "GR status of a neighbor.";
             }
             leaf restart-left-timer {
               type "uint32";
               units "s";
               description
                 "Restart left timer.";
             }
             leaf eor-sent {
               type "boolean";
               description
                 "Whether error is sent.";
             }
             leaf stale-route-num {
               type "uint32";
               description
                 "Stale route number.";
             }
           }
         }
       }
       container error-discard-info {
         config "false";
         description
           "Statistics of BGP error message.";
         leaf cluster-id-loop-count {
           type "uint32";
           description
             "Count of routes discarded because cluster IDs are the same.";
         }
         leaf receive-as-over-limit-count {
           type "uint32";
           description
             "Count of received routes discarded because the number of AS "+
             "numbers in the AS_Path exceeds the upper limit.";
         }
         leaf advertise-as-over-limit-count {
           type "uint32";
           description
             "Count of advertised routes discarded because the number of AS "+
             "numbers in the AS_Path exceeds the upper limit.";
         }
         leaf as-loop-count {
           type "uint32";
           description
             "Count of routes discarded because AS numbers are the same.";
         }
         leaf zero-rd-count {
           type "uint32";
           description
             "Count of routes discarded because of the RD 0:0.";
         }
         leaf no-prefix-count {
           type "uint32";
           description
             "Count of routes discarded because no prefix exists.";
         }
         leaf path-attribute-error-count {
           type "uint32";
           description
             "Count of routes with error path attributes.";
         }
         leaf originator-id-loop-count {
           type "uint32";
           description
             "Count of routes with an Originator ID conflict.";
         }
         leaf md5-count {
           type "uint32";
           description
             "MD5 count.";
         }
         container afs {
           description
             "List of BGP routes discarded in the address family.";
           list af {
             key "address-family";
             description
               "Statistics of BGP route discarded in the address family.";
             leaf address-family {
               type "bgp:af-type";
               description
                 "Address family type.";
             }
             leaf cluster-id-loop-count {
               type "uint32";
               description
                 "Count of routes discarded because cluster IDs are the same.";
             }
             leaf receive-as-over-limit-count {
               type "uint32";
               description
                 "Count of received routes discarded because the number of AS "+
                 "numbers in the AS_Path exceeds the upper limit.";
             }
             leaf advertise-as-over-limit-count {
               type "uint32";
               description
                 "Count of advertised routes discarded because the number of AS "+
                 "numbers in the AS_Path exceeds the upper limit.";
             }
             leaf as-loop-count {
               type "uint32";
               description
                 "Count of routes discarded because AS numbers are the same.";
             }
             leaf zero-rd-count {
               type "uint32";
               description
                 "Count of routes discarded because of the RD 0:0.";
             }
             leaf path-attribute-error-count {
               type "uint32";
               description
                 "Count of routes discarded because no prefix exists.";
             }
             leaf originator-id-loop-count {
               type "uint32";
               description
                 "Count of routes with an Originator ID conflict.";
             }
             leaf peer-record-count {
               type "uint32";
               description
                 "Peer record count.";
             }
             container peers {
               description
                 "List of BGP peer error information.";
               list peer {
                 key "vpn-name address";
                 description
                   "Statistics of BGP peer error information. The display error "+
                   "discard command displays statistics about all address "+
                   "families and packets discarded by peers. The NMS supports "+
                   "query based on the following filtering modes: \n(1) "+
                   "Statistics query about the specified address family and "+
                   "statistics about the packets discarded by peers. Such query "+
                   "is not supported by the preceding command.\n(2) Query of the"+
                   " information about the discarded packets filtered based on "+
                   "the specified peer or VPN instance. The query result is "+
                   "different from that in the command output. The command "+
                   "displays the statistics of the address family in which "+
                   "packet loss occurs and the information about the packets "+
                   "discarded by the peer.";
                 leaf vpn-name {
                   type "string" {
                     length "1..31";
                   }
                   description
                     "VPN name.";
                 }
                 leaf address {
                   type "inet:ip-address-no-zone";
                   description
                     "Peer address.";
                 }
                 leaf record-time {
                   type "yang:date-and-time";
                   description
                     "Record time.";
                 }
                 leaf reason {
                   type "string" {
                     length "1..300";
                   }
                   description
                     "Packet loss reason.";
                 }
                 leaf error-data {
                   type "string" {
                     length "1..300";
                   }
                   description
                     "Error data.";
                 }
                 leaf vpn-id {
                   type "uint32";
                   description
                     "VPN index.";
                 }
               }
             }
           }
         }
       }
       container vpn-brief-infos {
         config "false";
         description
           "List of BGP VPN brief informations.";
         list vpn-brief-info {
           key "vpn-name address-family";
           description
             "Statistics of VPN brief information.";
           leaf vpn-name {
             type "leafref" {
               path "/ni:network-instance/ni:instances/ni:instance/ni:name";
             }
             description
               "VPN name of a BGP instance.";
           }
           leaf address-family {
             type "bgp:af-type";
             description
               "Address family type.";
           }
           leaf peer-number {
             type "uint32";
             description
               "Set the number of peers in a specified address family.";
           }
           leaf route-number {
             type "uint32";
             description
               "Set the number of routes in a specified address family.";
           }
           leaf route-distinguisher-number {
             type "uint32";
             description
               "Number of RDs.";
           }
         }
       }
       container default-parameter {
         config "false";
         description
           "Statistics of default parameter of BGP.";
         leaf version {
           type "uint8";
           description
             "BGP protocol version.";
         }
         leaf connect-retry-time {
           type "uint16";
           units "s";
           description
             "Value of connect retry timer.";
         }
         leaf hold-time {
           type "uint32";
           units "s";
           description
             "The holdtime interval.";
         }
         leaf keepalive-time {
           type "uint32";
           units "s";
           description
             "The keepalive interval.";
         }
       }
       container srgbs {
         description
           "List of segment routing global block.";
         list srgb {
           must "lower-bound < upper-bound";
           key "lower-bound";
           max-elements "1";
           description
             "Configure segment routing global block.";
           leaf lower-bound {
             type "uint32" {
               range "16..1048575";
             }
             description
               "SRGB begin value. The range of specific values is dynamic and is"+
               " also affected by paf.";
           }
           leaf upper-bound {
             type "uint32" {
               range "16..1048575";
             }
             mandatory "true";
             description
               "SRGB end value. The range of specific values is dynamic and is "+
               "also affected by paf. The ending value of SRGB must be greater "+
               "than the configured value.";
           }
         }
       }
     }
     container instance-processs {
       description
         "List of the global BGP information for the list of all BGP instances, "+
         "such as the protocol version, AS number, and system identifier.";
       list instance-process {
         key "name";
         max-elements "1";
         description
           "Configure the global BGP information for the BGP instances, such as "+
           "the protocol version, AS number, and system identifier.";
         leaf name {
           type "string" {
             length "1..31";
           }
           must "../name != 'default'";
           description
             "Name of BGP Site.";
         }
         leaf as-number {
           type "as-number-validate";
           mandatory "true";
           description
             "Local AS number, which can be in either of the two formats:\nThe "+
             "two-byte format is X. X is an integer ranging from 1 to 65535.\nTh"+
             "e four-byte format is X.Y and X. When the format is X.Y, X and Y "+
             "are both integers, with the value of X ranging from 1 to 65535, "+
             "and the value of Y ranging from 0 to 65535; when the format is X, "+
             "X is an interger, with the value ranging from 1 to 4294967295.\nAn"+
             " AS consists of instance routers managed based on the same "+
             "techniques. Interior Gateway Protocol (IGP) and universal routing "+
             "metric packets are used inside an AS, and Exterior Gateway "+
             "Protocol (EGP) is used outside to send packets to other ASs. With "+
             "the development of this definition, one AS usually uses instance "+
             "IGPs and metrics. Even though instance IGPs and metrics are used, "+
             "the routing plan and destination reachability of an AS are "+
             "consistent with those of another AS. The local AS number cannot be"+
             " configured same as the confederation sub-ASs.";
           ext:operation-exclude "update" {
             description
               "The node cannot be modified when BGP is enabled.";
           }
         }
         leaf check-first-as {
           type "boolean";
           default "true";
           description
             "Enable/disable checking the first AS in the AS_Path of the update "+
             "messages from EBGP peers.";
         }
         leaf shutdown {
           type "boolean";
           default "false";
           description
             "Enable/disable interrupting BGP all neighbour.";
         }
         leaf private-4byte-as {
           type "boolean";
           default "false";
           description
             "Enable/disable BGP private 4 byte AS. With BGP private-4-byte-as, "+
             "BGP private as is from 64512 to 65535 and from 4200000000 to "+
             "4294967294.";
         }
         container graceful-restart {
           description
             "Configure the graceful-restart.";
           leaf enable {
             type "boolean";
             default "false";
             description
               "Enable/disable GR of the BGP speaker in the specified address "+
               "family, peer address, or peer group. When GR is enabled, the BGP"+
               " speaker enabled with GR keeps the forwarding state and sends "+
               "the End-Of-RIB flag during the restart. In this case, however, "+
               "the BGP speaker may not maintain the forwarding table. Enabling "+
               "or disabling GR may delete and re-establish all sessions and "+
               "instances.";
           }
           leaf time-wait-for-rib {
             type "uint32" {
               range "3..3000";
             }
             units "s";
             default "600";
             description
               "Period of waiting for the End-Of-RIB flag. The value is an "+
               "integer. When a BGP session is established or re-established, "+
               "the router enabled with GR should receive the End-Of-RIB flag in"+
               " this period. If the router does not receive the End-Of-RIB flag"+
               " in this period, ensure that the router can exit from the GR "+
               "process.";
           }
           leaf restart-time {
             type "uint16" {
               range "3..3600";
             }
             units "s";
             default "150";
             description
               "Specifies the maximum time during which a peer waits for a BGP "+
               "session reestablishment.";
           }
           leaf peer-reset {
             type "boolean";
             default "false";
             description
               "Enable/disable peer disconnection through GR.";
           }
         }
         container reference-period {
           must "hold-interval>suppress-interval";
           must "clear-interval>hold-interval";
           description
             "Configure the reference period.";
           leaf suppress-interval {
             type "uint32" {
               range "1..65535";
             }
             units "s";
             default "60";
             description
               "Specifies the reference period used to add penalty in case of "+
               "next hop flapping.";
           }
           leaf hold-interval {
             type "uint32" {
               range "1..65535";
             }
             units "s";
             default "120";
             description
               "Specifies the reference period used to hold penalty in case of "+
               "next hop flapping.";
           }
           leaf clear-interval {
             type "uint32" {
               range "1..65535";
             }
             units "s";
             default "600";
             description
               "Specifies the reference period used to clear penalty in case of "+
               "next hop flapping.";
           }
         }
         container timer {
           description
             "Configure BGP global timer parameters.";
           leaf connect-retry-time {
             type "uint16" {
               range "1..65535";
             }
             units "s";
             default "32";
             description
               "ConnectRetry interval.";
           }
           leaf keep-alive-time {
             type "uint32" {
               range "0..21845";
             }
             units "s";
             must "(../keep-alive-time != 0 and (../hold-time>=../keep-alive-tim"+
                  "e * 3) and ../hold-time != ../keep-alive-time ) or (../hold-t"+
                  "ime = 0 and ../keep-alive-time = 0)";
             default "60";
             description
               "Specify the Keepalive time of a peer or peer group. The value is"+
               " an integer. If the value of a timer changes, the peers need to "+
               "re-negotiate the interval value for the keepalive-time and "+
               "hold-time. This disconnects the BGP peer relationship between "+
               "the routers. Therefore, you need to double check whether it is a"+
               " must to change the value of the timer. Ensure that the hold "+
               "time is at least three times longer than the keepalive time when"+
               " you configure the BGP timer.";
           }
           leaf hold-time {
             type "uint32" {
               range "0 | 3..65535";
             }
             units "s";
             must "(((../hold-time>=../keep-alive-time * 3) and ../hold-time != "+
                  "../keep-alive-time ) or (../hold-time = 0 and ../keep-alive-t"+
                  "ime = 0)) and ../hold-time>=../min-hold-time";
             default "180";
             description
               "Specify the Hold time of a peer or peer group. When setting the "+
               "timer values of keepalive-time and hold-time, avoid the "+
               "following settings: 1.The interval values of keepalive-time and "+
               "hold-time are both set to 0. This will cause BGP timer to become"+
               " invalid, and BGP will not detect link faults based on the "+
               "timer.\n2. The interval value of hold-time is much greater than "+
               "that of keepalive-time. For example, the interval value of "+
               "keepalive-time is 1, and that of hold-time is 65535. If the "+
               "interval value of hold-time is too large, BGP will not be able "+
               "to detect link faults in time. The priority of the timer "+
               "configured here is lower than that of timer configured with "+
               "interval values of keepalive-time and hold-time of a peer. After"+
               " a connection is established between peers, the interval values "+
               "of keepalive-time and hold-time are negotiated by the peers. The"+
               " smaller interval value of hold-time contained in Open packets "+
               "of both peers is taken as the interval value of hold-time. The "+
               "smaller interval value of one third of the interval value of "+
               "hold-time and the locally set interval value of keepalive-time "+
               "is taken as the interval value of keepalive-time.";
           }
           leaf min-hold-time {
             type "uint32" {
               range "0 | 20..65535";
             }
             units "s";
             must "../hold-time>=../min-hold-time";
             default "0";
             description
               "The default value of zero means that the minimum hold time check"+
               " does not take effect. If the value is changed, the new value "+
               "takes effect since the next peer relationship establishment. "+
               "During the peer relationship establishment, the local device "+
               "checks the hold time of the remote end. If the hold time is less"+
               " than the minimum hold time, the local device sends an error "+
               "packet with error code 02 and subcode 06, and the peer "+
               "relationship fails to be established.";
           }
         }
       }
     }
   }
   augment "/ni:network-instance/ni:instances/ni:instance" {
     description
       "BGP network instance configuration.";
     container bgp {
       description
         "Configure BGP network instance. All nodes of private VPN Instance in "+
         "this container can be used only when the value of the global BGP "+
         "enabling node (/bgp:bgp/bgp:global/bgp:yang-enable) is set to true.";
       container base-process {
         when "/bgp:bgp/bgp:base-process/bgp:enable='true'";
         presence "Create vrf session.";
         description
           "Enable/disable BGP instances.";
         ext:generated-by "system" {
           when "../../ni:name = '_public_'";
           description
             "The BGP public instance is generated automatically when BGP is "+
             "enabled.";
         }
         leaf router-id-auto-select {
           when "../../../ni:name!='_public_'";
           type "boolean";
           default "false";
           description
             "Enable/disable router ID auto select. If a BGP VPN instance is not"+
             " enabled to select a router ID, a router ID can be configured for "+
             "the BGP VPN instance. If no router ID is configured for the BGP "+
             "VPN instance, the BGP VPN instance inherits the router ID of the "+
             "public network instance. If a BGP VPN instance is enabled to "+
             "select a router ID, it uses the address of an interface bound to a"+
             " VPN as the router ID based on the following rules:\n\n1. If "+
             "Loopback interfaces configured with IP addresses exist, the "+
             "largest IP address among the IP addresses of the Loopback "+
             "interfaces is selected as the router ID.\n\n2. If there is no "+
             "Loopback interface configured with an IP address, the largest IP "+
             "address among the IP addresses of other interfaces is selected as "+
             "the router ID, regardless of whether the interface is Up.";
         }
         leaf router-id {
           when "not(../router-id-auto-select) or ../router-id-auto-select = "+
                "'false'";
           type "inet:ipv4-address-no-zone";
           description
             "ID of a router that is in IPv4 address format. Certain dynamic "+
             "routing protocols require a router ID. If no router ID is "+
             "specified for a router when these protocols are enabled, the "+
             "router ID in the RM module is used by default. The default router "+
             "ID in the RM module is 0.0.0.0 when the router is not configured "+
             "with any interface. \nThe rules for selecting a router ID are as "+
             "follows:\n1. If a router ID is set through this configuration, the"+
             " set router ID is used. If the router ID is not set, a router ID "+
             "is selected according to the following rules:\n(1) If loopback "+
             "interfaces configured with IP addresses exist, the largest IP "+
             "address among the IP addresses of the loopback interfaces is "+
             "selected as the router ID.\n(2) If no loopback interface "+
             "configured with an IP address exists, the largest IP address among"+
             " the IP addresses of other interfaces is selected as the router "+
             "ID, regardless of whether the interface is Up.\nThe router ID is "+
             "reselected only when the interface address that is selected as the"+
             " router ID is deleted or changed. The router ID is not reselected "+
             "in any of the following cases:\na. The interface is Down.\nb. A "+
             "loopback interface is configured when the IP address of a "+
             "non-loopback interface is selected as the router ID.\nc. A larger "+
             "IP address of an interface is configured.\n2. Each VPN instance "+
             "selects the router ID from the addresses of the interfaces of the "+
             "VPN instance according to the preceding rules.\n3. When both the "+
             "AMB and SMB exist on the router, the system backs up the router ID"+
             " set through the related command and the router ID that is "+
             "selected from IP addresses of the interfaces. After the active/sta"+
             "ndby switchover is performed, the system checks the validity of "+
             "the router ID selected from the interface addresses. If the router"+
             " ID is invalid, the system reselects a router ID.";
         }
         leaf effect-router-id {
           type "inet:ipv4-address-no-zone";
           default "0.0.0.0";
           config "false";
           description
             "Router ID that takes effect.";
         }
         container afs {
           description
             "List of BGP address family instances.";
           list af {
             key "type";
             description
               "Configure BGP address family instance. In public network "+
               "instances, all types of address families can be configured. In "+
               "IPv4 VPN instances, the IPv4 unicast, IPv4 flow, and IPv4 "+
               "labeled unicast address families can be configured. In IPv6 VPN "+
               "instances, the IPv6 unicast and IPv6 flow address families can "+
               "be configured. The IPv4 address family in the BGP _public_ VPN "+
               "instance cannot be deleted.";
             ext:generated-by "system" {
               when "../../../../ni:name = '_public_'";
               ext:filter "type = 'ipv4uni'";
               description
                 "The IPv4 unicast of the BGP public instance is generated "+
                 "automatically when BGP is enabled.";
             }
             leaf type {
               type "enumeration" {
                 enum "ipv4uni" {
                   value "1";
                   description
                     "IPv4 unicast address family.";
                 }
                 enum "ipv4multi" {
                   value "2";
                   description
                     "IPv4 multicast address family.";
                 }
                 enum "ipv4vpn" {
                   value "3";
                   description
                     "IPv4 VPN address family.";
                 }
                 enum "ipv4labeluni" {
                   value "4";
                   description
                     "IPv4 labeled address family.";
                 }
                 enum "ipv6uni" {
                   value "5";
                   description
                     "IPv6 unicast address family.";
                 }
                 enum "ipv6vpn" {
                   value "6";
                   description
                     "IPv6 VPN address family.";
                 }
                 enum "ipv4flow" {
                   value "7";
                   description
                     "IPv4 flow address family.";
                 }
                 enum "l2vpnad" {
                   value "8";
                   description
                     "L2VPN-AD address family.";
                 }
                 enum "evpn" {
                   value "9";
                   description
                     "EVPN address family.";
                 }
                 enum "mvpn" {
                   value "10";
                   description
                     "IPv4 MVPN address family.";
                 }
                 enum "vpntarget" {
                   value "11";
                   description
                     "VPN target address family.";
                 }
                 enum "ipv4vpnmcast" {
                   value "12";
                   description
                     "IPv4 VPN multicast address family.";
                 }
                 enum "ls" {
                   value "13";
                   description
                     "Link-state address family.";
                 }
                 enum "mdt" {
                   value "14";
                   description
                     "IPv4 MDT address family.";
                 }
                 enum "ipv6flow" {
                   value "15";
                   description
                     "IPv6 flow address family.";
                 }
                 enum "mvpnv6" {
                   value "16";
                   description
                     "IPv6 MVPN address family.";
                 }
                 enum "vpnv4flow" {
                   value "17";
                   description
                     "VPNv4 flow address family.";
                 }
                 enum "vpnv6flow" {
                   value "18";
                   description
                     "VPNv6 flow address family.";
                 }
                 enum "rpd" {
                   value "19";
                   description
                     "RPD address family.";
                 }
                 enum "ipv4srpolicy" {
                   value "20";
                   description
                     "IPv4-family SR-Policy address family.";
                 }
                 enum "ipv6srpolicy" {
                   value "21";
                   description
                     "IPv6-family SR-Policy address family.";
                 }
               }
               description
                 "Address family type of a BGP instance.";
             }
             container ipv4-unicast {
               when "../type = 'ipv4uni'";
               must "../../../../../l3vpn:afs/l3vpn:af[l3vpn:type='ipv4-unicast'"+
                    "]";
               description
                 "Configure IPv4 unicast options.";
               container common {
                 description
                   "Configure IPv4 unicast common options.";
                 leaf auto-frr {
                   type "boolean";
                   default "false";
                   description
                     "Enable/disable BGP Auto FRR. If IP FRR, VPN FRR, and Auto "+
                     "FRR are all enabled, IP FRR and VPN FRR take precedence "+
                     "over Auto FRR. If a route fails to match the routing "+
                     "policy of IP FRR or VPN FRR, Auto FRR takes effect.";
                 }
                 leaf tunnel-selector-name {
                   when "../../../../../../../ni:name='_public_'";
                   type "leafref" {
                     path "/rtp:routing-policy/rtp:tunnel-selectors/rtp:tunnel-s"+
                          "elector/rtp:name";
                   }
                   description
                     "Configure a tunnel selector and apply it to the BGP IPv4 "+
                     "unicast, BGP VPNv4 address families and BGP VPNv6 address "+
                     "families so that IPv4,VPNv4 and VPNv6 labeled routes can "+
                     "be iterated to tunnels based on the tunnel selector. By "+
                     "default, no tunnel selector is configured.";
                 }
                 leaf tunnel-selector-all {
                   when "../tunnel-selector-name";
                   type "boolean";
                   default "false";
                   description
                     "Enable/disable tunnel selector for labeled, imported, and "+
                     "network segment routes.";
                 }
                 leaf maximum-load-balancing-ibgp {
                   type "uint16" {
                     range "1..128";
                   }
                   must "not (../maximum-load-balancing>1 or ../maximum-load-bal"+
                        "ancing-eibgp or ../load-balancing-eibgp-enable='true') "+
                        "or ../maximum-load-balancing-ibgp=1";
                   default "1";
                   description
                     "Specify the maximum number of equal-cost IBGP routes. The "+
                     "value range and default value are controlled by the PAF.";
                 }
                 leaf maximum-load-balancing-ebgp {
                   type "uint16" {
                     range "1..128";
                   }
                   must "not (../maximum-load-balancing>1 or ../maximum-load-bal"+
                        "ancing-eibgp or ../load-balancing-eibgp-enable='true') "+
                        "or ../maximum-load-balancing-ebgp=1";
                   default "1";
                   description
                     "Specify the maximum number of equal-cost EBGP routes. The "+
                     "value range and default value are controlled by the PAF.";
                 }
                 leaf nexthop-select-depend-type {
                   when "../../../../../../../ni:name='_public_'";
                   type "select-depend-type";
                   default "depend-ip";
                   description
                     "Specify the route iteration mode: IP or tunnel. In tunnel "+
                     "mode, the labeled BGP IPv4 route can participate in route "+
                     "selection only after its next hop is iterated to an LSP. "+
                     "In IP \nmode, the labeled BGP IPv4 route can participate "+
                     "in route selection only after its next hop is iterated to "+
                     "an IP address. By default, the labeled BGP IPv4 route can "+
                     "participate in route selection \nif its next hop can be "+
                     "iterated to an IP address, regardless of whether the LSP "+
                     "of the next hop exists. This allows the RR that is not "+
                     "enabled with MPLS to forward labeled routes. In non-RR "+
                     "\nnetworking or RR networking where the BGP next hop is "+
                     "changed, BGP needs to check whether there is an LSP "+
                     "destined for the next hop. If such an LSP is not found, "+
                     "BGP needs to establish an LSP in \nadvance. If the default"+
                     " setting is adopted, a labeled BGP IPv4 unicast route may "+
                     "be selected prior to LSP establishment. As a result, "+
                     "services are incorrectly switched before LSP establishment"+
                     " and \nservice stability is affected. Therefore, allow "+
                     "route selection only after the labeled BGP IPv4 route is "+
                     "iterated to an LSP.";
                 }
                 leaf nexthop-inherit-ip-cost {
                   when "../nexthop-select-depend-type='depend-tunnel'";
                   type "boolean";
                   default "false";
                   description
                     "Enable/disable next hop iteration mode to IP. Specify the "+
                     "route iteration mode: IP or tunnel. In tunnel mode, the "+
                     "labeled BGP IPv4 route can participate in route selection "+
                     "only after its next hop is iterated to an LSP.";
                 }
                 leaf nexthop-resolve-aigp {
                   type "boolean";
                   default "false";
                   description
                     "Enable/disable route with AIGP attribute for route "+
                     "selection.";
                 }
                 leaf summary-automatic {
                   type "boolean";
                   default "false";
                   description
                     "Enable/disable automatic summarization for imported "+
                     "routes. Manual summarization takes precedence over "+
                     "automatic summarization. After automatic summarization is "+
                     "enabled, BGP summarizes routes based on the natural "+
                     "network segment (for example, 10.1.1.1/24 and 10.2.1.1/24 "+
                     "are summarized into 10.0.0.0/8, a Class A address), and "+
                     "sends only the summarized route to peers. This reduces the"+
                     " number of routes.";
                 }
                 leaf best-route-bit-error-detection {
                   when "../../../../../../../ni:name!='_public_'";
                   type "boolean";
                   default "false";
                   description
                     "Enable/disable the function to reroute traffic when a bit "+
                     "error event occurs.";
                 }
                 leaf supernet-unicast-advertise {
                   type "boolean";
                   default "false";
                   description
                     "Enable/disable the function to advertise supernet unicast "+
                     "routes.";
                 }
                 leaf supernet-label-advertise {
                   type "boolean";
                   default "true";
                   description
                     "Enable/disable the function to advertise supernet labeled "+
                     "routes.";
                 }
                 leaf lsp-mtu {
                   type "uint16" {
                     range "46..65535";
                   }
                   default "1500";
                   description
                     "BGP LSP MTU.";
                 }
                 leaf label-free-delay {
                   type "uint8" {
                     range "0..180";
                   }
                   units "s";
                   default "0";
                   description
                     "Label Free Delay.";
                 }
                 leaf bestroute-med-confederation {
                   when "../../../../../../../ni:name='_public_'";
                   type "boolean";
                   default "false";
                   description
                     "Enable/disable BGP to compare MED value only within the "+
                     "federation.";
                 }
                 leaf bestroute-as-path-ignore {
                   type "boolean";
                   must "../bestroute-as-path-ignore = 'false' or ../load-balanc"+
                        "-as-path-ignore ='false' or not(../load-balanc-as-path-"+
                        "ignore)";
                   default "false";
                   description
                     "Enable/disable BGP to ignore the AS_Path attribute when "+
                     "selecting the optimal route. By default, BGP uses the "+
                     "AS_Path attribute as one of route selection rules, and a "+
                     "route with a shorter AS_Path is preferred. After "+
                     "bestroute-as-path-ignore is selected, BGP does not compare"+
                     " the AS_Path length.";
                 }
                 leaf determin-med {
                   type "boolean";
                   default "false";
                   description
                     "Enable/disable deterministic MED so that the route "+
                     "selection result is relevant to the sequence in which "+
                     "routes are received.";
                 }
                 leaf best-external {
                   when "../../../../../../../ni:name='_public_'";
                   type "boolean";
                   must "../best-external ='false' or ../determin-med ='false'";
                   default "false";
                   description
                     "Enable/disable best external route selection.";
                 }
                 leaf attribute-set-enable {
                   when "../../../../../../../ni:name!='_public_'";
                   type "boolean";
                   default "false";
                   description
                     "Enable/disable the capability of processing attribute "+
                     "set.";
                 }
                 leaf attribute-set-mode {
                   when "../attribute-set-enable='true'";
                   type "bgp:attribute-set-type";
                   default "both";
                   description
                     "The processing mode of attribute set.";
                 }
                 leaf add-path-select-num {
                   when "../../../../../../../ni:name='_public_'";
                   type "uint8" {
                     range "2..64";
                   }
                   must "../determin-med ='false'";
                   description
                     "Number of Add-Path routes.";
                 }
                 leaf load-balanc-igp-metric-ignore {
                   type "boolean";
                   default "false";
                   description
                     "Enable/disable BGP to ignore the IGP cost of each BGP "+
                     "route to the next hop when selecting routes for load "+
                     "balancing. By default, only the routes with the same IGP "+
                     "cost can participate in load balancing.";
                 }
                 leaf load-balanc-as-path-ignore {
                   type "boolean";
                   must "../load-balanc-as-path-ignore ='false' or (../load-bala"+
                        "nc-as-path-relax ='false' and ../bestroute-as-path-igno"+
                        "re ='false')";
                   default "false";
                   description
                     "Enable/disable BGP to ignore the AS_Path of each BGP route"+
                     " to the next hop when selecting routes for load balancing."+
                     " By default, only the routes with the same AS_Path can "+
                     "participate in load balancing.";
                 }
                 leaf load-balanc-as-path-relax {
                   type "boolean";
                   must "../load-balanc-as-path-relax ='false' or ../load-balanc"+
                        "-as-path-ignore ='false'";
                   default "false";
                   description
                     "Enable/disable BGP to ignore comparison of AS_Path "+
                     "attributes with the same length. By default, only the "+
                     "routes with the same AS_Path can participate in load "+
                     "balancing.";
                 }
                 leaf maximum-load-balancing {
                   type "uint16" {
                     range "1..128";
                   }
                   must "not (../maximum-load-balancing-ibgp>1 or ../maximum-loa"+
                        "d-balancing-ebgp>1 or ../maximum-load-balancing-eibgp) "+
                        "or ../maximum-load-balancing=1";
                   default "1";
                   description
                     "Specify the maximum number of equal-cost routes in the BGP"+
                     " routing table. The value can be 1 or an integer greater "+
                     "than 1. The value depends on the associated license. "+
                     "Equal-cost BGP routes can be generated for load balancing "+
                     "only when the BGP routes meet the first nine rules of the "+
                     "route-selection policy and have the same AS-Path "+
                     "attribute. The value range and default value are "+
                     "controlled by the PAF.";
                 }
                 leaf import-rib-nexthop-invariable {
                   when "../../../../../../../ni:name!='_public_'";
                   type "boolean";
                   default "false";
                   description
                     "Enable/disable the function to advertise the route without"+
                     " modifying the next-hop.";
                 }
                 leaf route-relay-tunnel {
                   type "boolean";
                   must "not(../route-relay-tunnel='true' and /rt:routing/rt:rou"+
                        "ting-manage/rt:relay-tunnel/rt:enable='true')";
                   default "false";
                   description
                     "Enable/disable unicast route recursive-lookup tunnel.";
                 }
                 leaf route-relay-tunnel-selector {
                   when "../route-relay-tunnel='true'";
                   type "leafref" {
                     path "/rtp:routing-policy/rtp:tunnel-selectors/rtp:tunnel-s"+
                          "elector/rtp:name";
                   }
                   description
                     "Unicast route tunnel selector name.";
                 }
                 leaf route-relay-tunnel-v6-selector {
                   when "../../../../../../../ni:name='_public_'";
                   type "leafref" {
                     path "/rtp:routing-policy/rtp:tunnel-selectors/rtp:tunnel-s"+
                          "elector/rtp:name";
                   }
                   description
                     "Enable/disable unicast route recursive-lookup IPv6 tunnel "+
                     "by tunnel selector name.";
                 }
                 leaf bestroute-med-plus-igp {
                   type "boolean";
                   must "not(../bestroute-igp-metric-ignore='true' and "+
                        "../bestroute-med-plus-igp='true')";
                   default "false";
                   description
                     "Enable/disable the function to add the IGP cost to the "+
                     "next-hop destination to the MED before comparing MED "+
                     "values for path selection.";
                 }
                 leaf bestroute-med-multiplier {
                   when "../bestroute-med-plus-igp='true'";
                   type "uint16" {
                     range "1..1000";
                   }
                   default "1";
                   description
                     "Value of med product factor.";
                 }
                 leaf bestroute-igp-multiplier {
                   when "../bestroute-med-plus-igp='true'";
                   type "uint16" {
                     range "1..1000";
                   }
                   default "1";
                   description
                     "Value of IGP cost product factor.";
                 }
                 leaf bestroute-igp-metric-ignore {
                   type "boolean";
                   default "false";
                   description
                     "Enable/disable BGP to ignore the IGP cost of each BGP "+
                     "route to the next hop in route selection. By default, a "+
                     "BGP route with a smaller IGP cost to the next hop is "+
                     "preferred.";
                   must "not(../bestroute-igp-metric-ignore='true' and "+
                        "../bestroute-med-plus-igp='true')";
                 }
                 leaf bestroute-router-id-prior-clusterlist {
                   type "boolean";
                   default "false";
                   description
                     "Enable/disable BGP to compare originator before clusterlis"+
                     "t in route selection.";
                 }
                 leaf bestroute-med-none-as-maximum {
                   type "boolean";
                   default "false";
                   description
                     "Enable/disable BGP considers its MED as the largest MED "+
                     "value (4294967295). If a route does not carry MED, BGP "+
                     "considers its MED as the default value (0) during route "+
                     "selection.";
                 }
                 leaf bestroute-rd-large-first {
                   when "../../../../../../../ni:name!='_public_'";
                   type "boolean";
                   default "false";
                   description
                     "Enable/disable a BGP device to select the route with the "+
                     "largest route distinguisher (RD) during route selection.";
                 }
                 leaf ebgp-ecmp-nexthop-changed {
                   when "../maximum-load-balancing-ebgp and ../maximum-load-bala"+
                        "ncing-ebgp>1";
                   type "boolean";
                   default "false";
                   description
                     "Enable/disable next hop of equal-cost EBGP routes is "+
                     "changed. When equal-cost EBGP routes are load-balancing "+
                     "traffic, the next hop of these routes is changed to a "+
                     "local interface before these routes are advertised. This "+
                     "function can be enabled only when the maximum number of "+
                     "equal-cost EBGP routes is greater than 1.";
                 }
                 leaf ibgp-ecmp-nexthop-changed {
                   when "../maximum-load-balancing-ibgp and ../maximum-load-bala"+
                        "ncing-ibgp>1";
                   type "boolean";
                   default "false";
                   description
                     "Enable/disable next hop of equal-cost IBGP routes is "+
                     "changed. When equal-cost IBGP routes are load-balancing "+
                     "traffic, the next hop of these routes is changed to a "+
                     "local interface before these routes are advertised. This "+
                     "function can be enabled only when the maximum number of "+
                     "equal-cost IBGP routes is greater than 1.";
                 }
                 leaf ecmp-nexthop-changed {
                   when "../maximum-load-balancing and ../maximum-load-balancing"+
                        ">1";
                   type "boolean";
                   default "false";
                   description
                     "Enable/disable next hop of equal-cost routes is changed. "+
                     "When equal-cost BGP routes are load-balancing traffic, the"+
                     " next hop of these routes is changed to a local interface "+
                     "before these routes are advertised. This function can be "+
                     "enabled only when the maximum number of equal-cost BGP "+
                     "routes is greater than 1.";
                 }
                 leaf maximum-load-balancing-eibgp {
                   when "../../../../../../../ni:name!='_public_'";
                   type "uint16" {
                     range "1..128";
                   }
                   must "../maximum-load-balancing-ibgp=1 and ../maximum-load-ba"+
                        "lancing-ebgp=1 and ../maximum-load-balancing=1 and "+
                        "../load-balancing-eibgp-enable='false'";
                   description
                     "Specify the maximum number of equal-cost EBGP routes and "+
                     "IBGP routes. After the attribute is set, load balancing is"+
                     " performed among equal-cost BGP VPN routes, regardless of "+
                     "the route type, EBGP or IBGP. The value range and default "+
                     "value are controlled by the PAF.";
                 }
                 leaf eibgp-ecmp-nexthop-changed {
                   when "../maximum-load-balancing-eibgp";
                   type "boolean";
                   default "false";
                   description
                     "Enable/disable next hop of equal-cost EBGP and IBGP routes"+
                     " is changed. When equal-cost EBGP and IBGP routes are "+
                     "load-balancing traffic, the next hop of these routes is "+
                     "changed to a local interface before these routes are "+
                     "advertised.";
                 }
                 leaf load-balancing-eibgp-enable {
                   when "../../../../../../../ni:name!='_public_'";
                   type "boolean";
                   must "not (../maximum-load-balancing-ibgp>1 or ../maximum-loa"+
                        "d-balancing-ebgp>1 or ../maximum-load-balancing-eibgp) "+
                        "or ../load-balancing-eibgp-enable='false'";
                   default "false";
                   description
                     "Enable/disable EIBGP route load balancing.";
                 }
                 leaf nexthop-priority {
                   type "nexthop-priority-address-type";
                   description
                     "Routes with next-hop IPv4 addresses and routes with "+
                     "next-hop IPv6 addresses coexist. If the next-hop address "+
                     "type is set to IPv4, routes with next-hop IPv4 addresses "+
                     "have a higher priority. If the next-hop address type is "+
                     "set to IPv6, routes with next-hop IPv6 addresses have a "+
                     "higher priority.";
                 }
                 leaf prefix-origin-as-validation {
                   type "boolean";
                   default "false";
                   description
                     "Enable/disable the BGP prefix origin validation.";
                 }
                 leaf bestroute-origin-as-validation {
                   when "../prefix-origin-as-validation='true'";
                   type "boolean";
                   default "false";
                   description
                     "Enable/disable the BGP origin AS validation result.";
                 }
                 leaf bestroute-allow-invalid-as {
                   when "../bestroute-origin-as-validation='true'";
                   type "boolean";
                   default "false";
                   description
                     "Enable/disable routes with BGP origin AS validation result"+
                     " invalid to be selected.";
                 }
                 leaf advertise-route-mode {
                   when "../../../../../../../ni:name!='_public_'";
                   type "bgp-advertise-route-mode";
                   default "all";
                   description
                     "VPN advertise route mode.";
                 }
                 leaf reoriginate-route {
                   when "../../../../../../../ni:name!='_public_'";
                   type "boolean";
                   default "false";
                   description
                     "Enable/disable route reorigination.";
                 }
                 leaf rpd-policy-change-delay {
                   when "../../../../../../../ni:name='_public_'";
                   type "uint16" {
                     range "0..180";
                   }
                   default "30";
                   description
                     "Specify the delay time of RPD policy's change.";
                 }
                 leaf route-select-delay {
                   type "uint16" {
                     range "0..3600";
                   }
                   units "s";
                   default "0";
                   description
                     "Route selection delay.";
                 }
                 choice reflector-type {
                   description
                     "Set IPv4 address or id.";
                   case address {
                     description
                       "IPv4 address.";
                     leaf reflector-cluster-ipv4 {
                       type "inet:ipv4-address-no-zone";
                       description
                         "Set a cluster ID. The value is expressed in the format"+
                         " of an IPv4 address. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                   case id {
                     description
                       "Set value.";
                     leaf reflector-cluster-id {
                       type "uint32" {
                         range "1..4294967295";
                       }
                       description
                         "Set a cluster ID. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                 }
                 leaf reflect-change-path {
                   type "boolean";
                   default "false";
                   description
                     "Enable/disable an RR to use an export policy to change "+
                     "route AS_Path.";
                 }
                 leaf always-compare-med {
                   type "boolean";
                   default "false";
                   description
                     "Enable/disable BGP to compare the MEDs of routes from "+
                     "peers in different ASs in route selection. If \nthere are "+
                     "multiple reachable routes to the same destination, the "+
                     "route with the smallest MED is preferred. Do not use this "+
                     "option unless different ASs use the same IGP and route "+
                     "selection mode.";
                 }
                 leaf default-med {
                   type "uint32";
                   default "0";
                   description
                     "Specify the Multi-Exit-Discriminator (MED) of BGP routes. "+
                     "The value is an integer. This value is valid only for the "+
                     "imported routes and BGP summarized routes on the local "+
                     "router.";
                 }
                 leaf nexthop-third-party {
                   type "boolean";
                   default "false";
                   description
                     "Enable/disable BGP third-party next hop.";
                 }
                 leaf default-local-preference {
                   type "uint32" {
                     range "0..4294967295";
                   }
                   default "100";
                   description
                     "The local preference of BGP routes.";
                 }
                 leaf default-route-import {
                   type "boolean";
                   default "false";
                   description
                     "Enable/disable the function to import default routes into "+
                     "the BGP routing table. Default-route-imported must be used"+
                     " with import-routes so that default routes can be imported"+
                     " to the BGP routing table. If only import-routes is used, "+
                     "no default routes can be added to the BGP routing table. "+
                     "In addition, default-route-imported can only import the "+
                     "default routes in the routing table into the BGP routing "+
                     "table.";
                 }
                 leaf routerid-neglect {
                   type "boolean";
                   default "false";
                   description
                     "Enable/disable BGP to ignore router IDs when selecting the"+
                     " optimal route. Comparing router IDs is the last resort in"+
                     " route selection. This means that if one optimal route "+
                     "must be selected and no other parameters can be used to "+
                     "break the tie, router IDs can be used. If this option is "+
                     "selected, the first received route will be selected as the"+
                     " optimal route, and BGP will ignore the router ID and peer"+
                     " address in route selection.";
                 }
                 leaf reflect-between-client {
                   type "boolean";
                   default "true";
                   description
                     "Enable/disable route reflection between clients. If "+
                     "clients of a route reflector (RR) are fully meshed, you "+
                     "can disable route reflection among clients to reduce the "+
                     "cost.";
                 }
                 leaf ext-community-change {
                   type "boolean";
                   default "false";
                   description
                     "Enable/disable the function to change the extended "+
                     "community attribute.";
                 }
                 leaf active-route-advertise {
                   type "boolean";
                   default "false";
                   description
                     "Enable/disable the function to advertise the optimal "+
                     "routes in the RM module to peers.";
                 }
                 leaf ebgp-interface-sensitive {
                   type "boolean";
                   default "true";
                   description
                     "Enable/disable the function of EBGP interface fast "+
                     "sensing. If this function is enabled, the sessions of "+
                     "directly connected EBGP peers are immediately cleared from"+
                     " the associated interface when the interface becomes "+
                     "down.";
                 }
                 leaf load-balancing-ucmp {
                   when "../../../../../../../ni:name='_public_'";
                   type "boolean";
                   default "false";
                   description
                     "Enable/disable the function of BGP UCMP.";
                 }
               }
               container preference {
                 description
                   "Configure parameters relating to options for BGP routes "+
                   "preference.";
                 choice set-value-or-policy {
                   default "set-value";
                   description
                     "Set BGP routes preference by value or policy.";
                   case set-value {
                     description
                       "Set BGP routes preference by value.";
                     leaf external {
                       type "uint8" {
                         range "1..255";
                       }
                       default "255";
                       description
                         "Set the protocol priority of EBGP routes. The value is"+
                         " an integer. An EBGP route is the optimal route "+
                         "learned from a peer outside the local AS.";
                     }
                     leaf internal {
                       type "uint8" {
                         range "1..255";
                       }
                       default "255";
                       description
                         "Set the protocol priority of IBGP routes. The value is"+
                         " an integer. An IBGP route is a route learned from a "+
                         "peer inside the local AS.";
                     }
                     leaf local {
                       type "uint8" {
                         range "1..255";
                       }
                       default "255";
                       description
                         "Set the protocol priority of a local BGP route. A "+
                         "local route refers to an automatically or manually "+
                         "summarized route.";
                     }
                   }
                   case rtp-ref {
                     description
                       "Set BGP routes preference by route policy.";
                     leaf route-policy {
                       type "leafref" {
                         path "/rtp:routing-policy/rtp:policy-definitions/rtp:po"+
                              "licy-definition/rtp:name";
                       }
                       description
                         "Specify a routing policy to filter routes so that a "+
                         "configured priority is applied to the routes that "+
                         "match the specified policy.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container nexthop-recursive-lookup {
                 description
                   "Configure next hop iteration.";
                 container common {
                   description
                     "Configure next hop iteration common options.";
                   leaf restrain {
                     type "boolean";
                     default "true";
                     description
                       "Enable/disable the function to restrain next hop "+
                       "iteration in case of next hop flapping.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                   leaf default-route {
                     type "boolean";
                     default "false";
                     description
                       "Enable/disable default route.";
                   }
                 }
                 container delay {
                   description
                     "Configure time of next hop change responding delay.";
                   leaf time {
                     type "uint8" {
                       range "1..100";
                     }
                     units "s";
                     description
                       "Specify the delay in responding to the next hop change.";
                   }
                   leaf no-critical-event-time {
                     type "uint8" {
                       range "0..100";
                     }
                     units "s";
                     default "10";
                     description
                       "Specify the delay in responding to the next hop change "+
                       "on non critical relay change event.";
                   }
                 }
               }
               container import-routes {
                 description
                   "List of imported routes.";
                 list import-route {
                   key "protocol process-id";
                   description
                     "Configure route import. Routes of other protocol types can"+
                     " be imported by BGP. By default, BGP does not import "+
                     "routes of other protocol types.";
                   leaf protocol {
                     type "bgp:ipv4-import-route-protocol-type";
                     description
                       "Routing protocol from which routes can be imported.";
                   }
                   leaf process-id {
                     type "uint32" {
                       range "0..4294967295";
                     }
                     description
                       "Process ID of an imported routing protocol. The process "+
                       "ID is 0, if the imported routing protocol is direct "+
                       "routes, static routes, UNRs, or OP-routes. The process "+
                       "ID must be specified range from 1 to 4294967295, if the "+
                       "imported routing protocol is RIP, OSPF, ISIS.";
                     must "((../protocol='ospf' or ../protocol='isis' or "+
                          "../protocol='rip') and ../process-id!=0) or "+
                          "(../protocol!='ospf' and ../protocol!='isis' and "+
                          "../protocol!='rip' and ../process-id=0)";
                   }
                   leaf med {
                     type "uint32";
                     description
                       "Specifies the MED metric of the imported route.";
                   }
                   choice policy-type {
                     description
                       "Set route policy or filter.";
                     case rtp-ref {
                       description
                         "Route policy.";
                       leaf policy-name {
                         type "leafref" {
                           path "/rtp:routing-policy/rtp:policy-definitions/rtp:"+
                                "policy-definition/rtp:name";
                         }
                         description
                           "When routes are imported from other routing "+
                           "protocols, the route-policy filter can be used to "+
                           "filter the routes and change route attributes.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                   leaf non-relay-tunnel {
                     when "../../../../../../../../ni:name='_public_'";
                     type "boolean";
                     default "false";
                     description
                       "Enable/disable imported route relay a tunnel.";
                   }
                 }
               }
               container aggregate-routes {
                 description
                   "List of summarized routes.";
                 list aggregate-route {
                   key "address mask-length";
                   description
                     "Configure a summarized route in the BGP routing table. The"+
                     " local outbound interface of the summarized route is "+
                     "Null0. When another router receives the route, the route "+
                     "adds an outbound interface to the route. If the Origin "+
                     "attributes of the specific routes for the route summarizat"+
                     "ion are different, the Origin attribute of the summarized "+
                     "route is that with the highest priority. Origin attributes"+
                     " are arranged in the priority order of complete > egp > "+
                     "igp. A summarized route carries the community attribute of"+
                     " each specific route.";
                   leaf address {
                     type "inet:ip-address-no-zone";
                     description
                       "Specify the IPv4 address or IPv6 address of a summarized"+
                       " route. Only IPv4 summarized routes can be configured in"+
                       " the IPv4 address family and only IPv6 summarized routes"+
                       " can be configured in the IPv6 address family.";
                     must "not(contains(../address,':'))";
                   }
                   leaf mask-length {
                     type "uint8" {
                       range "1..128";
                     }
                     description
                       "Specify the mask length of a summarized address.";
                     must "../mask-length<=32";
                   }
                   leaf as-set {
                     type "boolean";
                     default "false";
                     description
                       "Enable/disable the generation of routes with the AS-SET "+
                       "attribute. This option can be used to create a "+
                       "summarized route. The AS_Path attribute of the "+
                       "summarized route contains the AS-Path attributes of the "+
                       "specific routes for the route summarization. Exercise "+
                       "caution when using this option if multiple AS_Paths need"+
                       " to be summarized to prevent route flapping.";
                   }
                   leaf detail-suppressed {
                     type "boolean";
                     default "false";
                     description
                       "Enable/disable detail-suppressed. Suppress the "+
                       "advertisement of specific routes for the route "+
                       "summarization. Only the summarized route is advertised.";
                   }
                   choice policy-type {
                     description
                       "Set route policy or filter.";
                     case rtp-ref {
                       description
                         "Route policy.";
                       leaf attribute-policy {
                         type "leafref" {
                           path "/rtp:routing-policy/rtp:policy-definitions/rtp:"+
                                "policy-definition/rtp:name";
                         }
                         description
                           "Specify an attribute of summarized routes. If apply "+
                           "as-path is used to configure the AS_Path attribute "+
                           "that is used in the route Summarization policy, and "+
                           "the as-set keyword is set, the AS_Path attribute in "+
                           "the policy does not take effect. This parameter and "+
                           "any of the following parameters overwrite each "+
                           "other: suppressFilter, originFilter, and attributeFi"+
                           "lter.";
                       }
                       leaf origin-policy {
                         type "leafref" {
                           path "/rtp:routing-policy/rtp:policy-definitions/rtp:"+
                                "policy-definition/rtp:name";
                         }
                         description
                           "Specify the name of a policy for generating "+
                           "summarized routes. Summarized routes are generated "+
                           "only when the routes match route-policy. This "+
                           "parameter and any of the following parameters "+
                           "overwrite each other: suppressFilter, originFilter, "+
                           "and attributeFilter.";
                       }
                       leaf suppress-policy {
                         type "leafref" {
                           path "/rtp:routing-policy/rtp:policy-definitions/rtp:"+
                                "policy-definition/rtp:name";
                         }
                         description
                           "Specify a policy for suppressing the advertisement "+
                           "of specified routes. The routes matching the policy "+
                           "are not advertised, and other routes are advertised."+
                           " This parameter and any of the following parameters "+
                           "overwrite each other: suppressFilter, originFilter, "+
                           "and attributeFilter.";
                       }
                     }
                     case xpl-ref {
                       description
                         "Route filter.";
                       leaf attribute-filter-name {
                         type "leafref" {
                           path "/xpl:xpl/xpl:route-filters/xpl:route-filter/xpl"+
                                ":name";
                         }
                         description
                           "Specify a route-filter name.";
                       }
                       leaf attribute-filter-parameter {
                         when "../attribute-filter-name";
                         type "xpl:filter-parameter-type";
                         description
                           "Specify a route-filter parameter.";
                       }
                       leaf origin-filter-name {
                         type "leafref" {
                           path "/xpl:xpl/xpl:route-filters/xpl:route-filter/xpl"+
                                ":name";
                         }
                         description
                           "Specify a route-filter name.";
                       }
                       leaf origin-filter-parameter {
                         when "../origin-filter-name";
                         type "xpl:filter-parameter-type";
                         description
                           "Specify a route-filter parameter.";
                       }
                       leaf suppress-filter-name {
                         type "leafref" {
                           path "/xpl:xpl/xpl:route-filters/xpl:route-filter/xpl"+
                                ":name";
                         }
                         description
                           "Specify a route-filter name.";
                       }
                       leaf suppress-filter-parameter {
                         when "../suppress-filter-name";
                         type "xpl:filter-parameter-type";
                         description
                           "Specify a route-filter parameter.";
                       }
                     }
                   }
                 }
               }
               container aggregate-default-route {
                 description
                   "Configure aggregate default route.";
                 leaf origin-ip-prefix {
                   type "leafref" {
                     path "/rtp:routing-policy/rtp:ipv4-prefix-filters/rtp:ipv4-"+
                          "prefix-filter/rtp:name";
                   }
                   description
                     "Specify the name of an IPv4 prefix list for a summary "+
                     "default route. Only the name of an IPv4 prefix list can be"+
                     " configured in a BGP IPv4 address family.";
                 }
                 leaf attribute-policy {
                   when "../origin-ip-prefix";
                   type "leafref" {
                     path "/rtp:routing-policy/rtp:policy-definitions/rtp:policy"+
                          "-definition/rtp:name";
                   }
                   description
                     "Specify an attribute policy of a summary default route.";
                 }
               }
               container network-routes {
                 description
                   "List of network routes.";
                 list network-route {
                   key "address mask-length";
                   description
                     "Configure a network route in the BGP routing table.";
                   leaf address {
                     type "inet:ipv4-address-no-zone";
                     description
                       "Specify the IP address advertised by BGP. An IPv4 "+
                       "address can be configured in the IPv4 address family. "+
                       "Note: During the configuration of a network route, the "+
                       "IP address is adjusted based on the mask. It is "+
                       "recommended that you click Synchronize All after "+
                       "creating a network route.";
                   }
                   leaf mask-length {
                     type "uint8" {
                       range "0..32";
                     }
                     description
                       "Specify the mask length of an IP address.";
                   }
                   choice policy-type {
                     description
                       "Specify the route-policy or filter for route advertiseme"+
                       "nt.";
                     case rtp-ref {
                       description
                         "Specify the route policy.";
                       leaf policy-name {
                         type "leafref" {
                           path "/rtp:routing-policy/rtp:policy-definitions/rtp:"+
                                "policy-definition/rtp:name";
                         }
                         description
                           "Specify the route policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                   leaf non-relay-tunnel {
                     when "../../../../../../../../ni:name='_public_'";
                     type "boolean";
                     default "false";
                     description
                       "Enable/disable imported route relay a tunnel.";
                   }
                   leaf label-index {
                     when "../../../../../../../../ni:name='_public_'";
                     type "uint32" {
                       range "0..4294967294";
                     }
                     description
                       "Management label value assigned for imported routes.";
                   }
                 }
               }
               container advertise-route-to-evpns {
                 when "../../../../../../ni:name!='_public_'";
                 description
                   "Configure advertise route protocol.";
                 list advertise-route-to-evpn {
                   key "protocol";
                   description
                     "Configure the advertise route protocol.";
                   leaf protocol {
                     type "enumeration" {
                       enum "all" {
                         value "0";
                         description
                           "Advertise all the types of route protocol.";
                       }
                     }
                     description
                       "Route protocol.";
                   }
                   leaf import-multipath {
                     type "boolean";
                     default "false";
                     description
                       "Enable/disable route import from multiple paths.";
                   }
                   leaf include-local-cross {
                     type "boolean";
                     default "false";
                     description
                       "Enable/disable local cross route to advertise l2vpn "+
                       "evpn.";
                   }
                   leaf advertise-route-mode {
                     type "enumeration" {
                       enum "all" {
                         value "0";
                         description
                           "All:";
                       }
                       enum "best" {
                         value "1";
                         description
                           "Best:";
                       }
                       enum "valid" {
                         value "2";
                         description
                           "Valid:";
                       }
                     }
                     default "all";
                     description
                       "VPN advertise route mode to evrf.";
                   }
                 }
               }
               container import-ribs {
                 description
                   "List of imported RIBs configuration.";
                 list import-rib {
                   key "source-vpn source-address-family";
                   description
                     "Configure imported RIBs.";
                   leaf source-vpn {
                     type "leafref" {
                       path "/ni:network-instance/ni:instances/ni:instance/ni:na"+
                            "me";
                     }
                     must "not(../../../../../../../../ni:name = current() and "+
                          "../source-address-family = 'ipv4uni')";
                     description
                       "Source VPN name.";
                   }
                   leaf source-address-family {
                     type "bgp:import-rib-ipv4-safi-type";
                     description
                       "Source address family type.";
                   }
                   leaf valid-route {
                     type "boolean";
                     default "false";
                     description
                       "Enable/disable imported valid route.";
                   }
                   leaf include-label-route {
                     when "../source-address-family='ipv4uni'";
                     type "boolean";
                     default "false";
                     description
                       "Enable/disable imported include label route.";
                   }
                   choice policy-type {
                     description
                       "Set policy or filter.";
                     case rtp-ref {
                       description
                         "Specify the route policy.";
                       leaf policy-name {
                         type "leafref" {
                           path "/rtp:routing-policy/rtp:policy-definitions/rtp:"+
                                "policy-definition/rtp:name";
                         }
                         description
                           "Specify the route policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container import-filter-policy {
                 description
                   "Configure a filtering policy. It is used to filter the "+
                   "routes received from a peer. By default, routes are not "+
                   "filtered.";
                 choice ipv4-import-filter-protocol-policy-type {
                   description
                     "Set IPv4 filter protocol policy.";
                   case acl-ref {
                     description
                       "ACL Route Policy.";
                     leaf acl-name-or-num {
                       type "leafref" {
                         path "/acl:acl/acl:groups/acl:group/acl:identity";
                       }
                       description
                         "Specify the name or number of an ACL Rule. The number "+
                         "value ranges from 2000 to 2999 and is used by basic "+
                         "ACL rules. The name must start with a letter, and the "+
                         "name is case-sensitive.";
                     }
                   }
                   case ip-prefix-ref {
                     description
                       "IP prefix Policy.";
                     leaf ipv4-prefix-filter {
                       type "leafref" {
                         path "/rtp:routing-policy/rtp:ipv4-prefix-filters/rtp:i"+
                              "pv4-prefix-filter/rtp:name";
                       }
                       description
                         "Specify the IPv4 prefix list name.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container export-filter-policys {
                 description
                   "List of filtering policies.";
                 list export-filter-policy {
                   key "protocol process-id";
                   description
                     "Apply a filtering policy. It is used to filter the routes "+
                     "to be advertised to the peer. By default, routes are not "+
                     "filtered.";
                   leaf protocol {
                     type "bgp:ipv4-export-filter-protocol-type";
                     description
                       "Specify the name of a routing protocol. The routing "+
                       "protocol takes effect only on the routes to be "+
                       "advertised. The IPv4 address family supports the direct,"+
                       " IS-IS, OSPF, RIP, and static routing protocols. The "+
                       "IPv6 unicast address family of a public network instance"+
                       " supports the direct, IS-IS, OSPFv3, RIPng, and static "+
                       "routing protocols. The IPv6 address family of a VPNv6 "+
                       "instance supports the direct, IS-IS, RIPng, and static "+
                       "routing protocols.";
                     must "(../protocol ='op-route' and ../../../../type "+
                          "!='ipv4multi') or (../protocol !='op-route')";
                   }
                   leaf process-id {
                     type "uint32" {
                       range "0..4294967295";
                     }
                     description
                       "Specify the process ID required to be matched. The value"+
                       " is an integer ranging from 0 to 4294967295. If direct "+
                       "or static routes need to be filtered, no process ID is "+
                       "required.";
                     must "((../protocol='ospf' or ../protocol='isis' or "+
                          "../protocol='rip') and ../process-id!=0) or "+
                          "(../protocol!='ospf' and ../protocol!='isis' and "+
                          "../protocol!='rip' and ../process-id=0)";
                   }
                   choice ipv4-filter-protocol-policy-type {
                     mandatory "true";
                     description
                       "Set IPv4 filter protocol policy.";
                     case acl-ref {
                       description
                         "ACL Route Policy.";
                       leaf acl-name-or-num {
                         type "leafref" {
                           path "/acl:acl/acl:groups/acl:group/acl:identity";
                         }
                         description
                           "Specify the name or number of an ACL Rule. The "+
                           "number value ranges from 2000 to 2999 and is used by"+
                           " basic ACL rules. The name must start with a letter,"+
                           " and the name is case-sensitive.";
                       }
                     }
                     case ip-prefix-ref {
                       description
                         "IP prefix Policy.";
                       leaf ipv4-prefix-filter {
                         type "leafref" {
                           path "/rtp:routing-policy/rtp:ipv4-prefix-filters/rtp"+
                                ":ipv4-prefix-filter/rtp:name";
                         }
                         description
                           "Specify the IPv4 prefix list name.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container lsp-options {
                 description
                   "Configure parameters for lsp.";
                 leaf ingress-protect-mode-bgp-frr {
                   type "boolean";
                   must "(../ingress-protect-mode-bgp-frr='false') or (../ingres"+
                        "s-protect-mode-bgp-frr='true' and ../maximum-load-balan"+
                        "cing-ingress=1)";
                   default "false";
                   description
                     "Enable/disable ingress LSP protection mode to FRR.";
                 }
                 leaf maximum-load-balancing-ingress {
                   type "uint16" {
                     range "1..16";
                   }
                   default "1";
                   description
                     "Maximum number of ingress LSPs for load balancing. The "+
                     "default value is 1, indicating that this attribute is not "+
                     "configured. Configuring the number of ingress LSPs for "+
                     "load balancing and configuring BGP FRR of ingress LSPs are"+
                     " mutually exclusive.";
                 }
                 leaf maximum-load-balancing-transit {
                   type "uint16" {
                     range "1..16";
                   }
                   default "1";
                   description
                     "Maximum number of transit LSPs for load balancing.";
                 }
                 leaf unicast-rt-label-advertise {
                   when "../../../../../../../ni:name='_public_'";
                   type "boolean";
                   default "false";
                   description
                     "Enable/disable a device to convert received IPv4 public "+
                     "network unicast routes to labeled routes by allocating one"+
                     " BGP label to each route and advertise the labeled routes "+
                     "to peers with the labeled route exchange capability.";
                 }
                 leaf unicast-rt-label-advertise-popgo {
                   when "../unicast-rt-label-advertise = 'true'";
                   type "boolean";
                   default "false";
                   description
                     "Enable/disable a device to convert received IPv4 public "+
                     "network unicast routes to labeled routes by adding a BGP "+
                     "label to each route and advertise the labeled routes to "+
                     "peers with the labeled route exchange capability. If the "+
                     "IP address of an outbound interface is reachable but no "+
                     "LSP is reachable, traffic is forwarded through the "+
                     "outbound interface and a specific next hop, during which "+
                     "the label POPGO action is performed.";
                 }
                 leaf lsp-operation {
                   when "../../../../../../../ni:name='_public_'";
                   type "lsp-operation-type";
                   default "pop";
                   description
                     "Label operation type.";
                 }
                 choice ingress-trigger-policy {
                   description
                     "Specify the route-policy or filter for ingress LSPs.";
                   case trigger-route-policy-ref {
                     description
                       "Route policy.";
                     leaf trigger-route-policy {
                       type "leafref" {
                         path "/rtp:routing-policy/rtp:policy-definitions/rtp:po"+
                              "licy-definition/rtp:name";
                       }
                       description
                         "Specify the name of a routing policy.";
                     }
                   }
                   case trigger-xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container segment-routing-ipv6 {
                 description
                   "Configure BGP segment-routing IPv6.";
                 leaf srv6-best-effort-enable {
                   type "empty";
                   description
                     "Enable SRv6 BE iteration.";
                 }
                 leaf srv6-traffic-engineer-enable {
                   type "empty";
                   description
                     "Enable SRv6 TE iteration.";
                 }
               }
               container dampening-routes {
                 description
                   "List of route dampening.";
                 list dampening-route {
                   must "reuse < suppress and suppress < ceiling";
                   key "peer-type";
                   description
                     "Configure BGP route dampening or modify various BGP route "+
                     "dampening parameters. If a suppression policy for route "+
                     "dampening is configured, routes are preferentially matched"+
                     " against the suppression parameters defined in the "+
                     "suppression policy. If no parameter is configured, the "+
                     "default value of each parameter is used. The four route "+
                     "dampening parameters are mutually dependent. If you "+
                     "configure one of the parameters, the other parameters also"+
                     " need to be configured. When you configure BGP route "+
                     "dampening, the values of reuse threshold, suppress "+
                     "threshold, and penalty ceiling must meet the inequality of"+
                     " reuse threshold < suppress threshold < penalty ceiling. "+
                     "If Maximum suppression time obtained by using the formula "+
                     "of Maximum suppression time = Half life (of reachable "+
                     "routes) x 60 x (ln (Penalty ceiling/Reuse threshold)/ln(2)"+
                     ") is smaller than 1, suppression cannot be performed. "+
                     "Ensure that the value of the maximum suppression time is "+
                     "equal to or greater than 1. This means that the value of "+
                     "the penalty ceiling/reuse threshold must be great enough.";
                   leaf peer-type {
                     type "dampening-route-peer-type";
                     description
                       "Configure the peer type.";
                   }
                   leaf half-life-time {
                     type "uint16" {
                       range "1..45";
                     }
                     units "min";
                     default "15";
                     description
                       "Configure a half-life for reachable routes.";
                   }
                   leaf reuse {
                     type "uint16" {
                       range "1..20000";
                     }
                     default "750";
                     description
                       "Configure a threshold for a route to be unsuppressed. If"+
                       " the penalty value of the route falls below the "+
                       "threshold, the route is reused.";
                   }
                   leaf suppress {
                     type "uint16" {
                       range "1..20000";
                     }
                     default "2000";
                     description
                       "Configure a threshold for a route to be suppressed. When"+
                       " the penalty value of the route exceeds the suppression "+
                       "threshold, the route is suppressed. The configured "+
                       "suppression threshold must be greater than the reuse "+
                       "threshold.";
                   }
                   leaf ceiling {
                     type "uint16" {
                       range "1001..20000";
                     }
                     default "16000";
                     description
                       "Configure the penalty ceiling. The configured threshold "+
                       "must be greater than the suppression threshold.";
                   }
                   leaf update-standard {
                     type "boolean";
                     default "false";
                     description
                       "Enable/disable update standard.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container slow-peer {
                 description
                   "Configure peer advertising routes slowly.";
                 leaf detection {
                   type "boolean";
                   default "true";
                   description
                     "Enable/disable detect slow peers.";
                 }
                 leaf detection-threshold {
                   type "uint16" {
                     range "120..3600";
                   }
                   units "s";
                   default "300";
                   description
                     "Specify the time in seconds lagging behind average when a "+
                     "peer is determined to be a slow peer.";
                 }
                 leaf absolute-detection {
                   type "boolean";
                   default "true";
                   description
                     "Enable/disable absolute-detect slow peers.";
                 }
                 leaf absolute-detection-threshold {
                   type "uint16" {
                     range "3..3600";
                   }
                   units "s";
                   default "9";
                   description
                     "Specify the packet send delay time in second when a peer "+
                     "is determined to be a slow peer.";
                 }
               }
               container routing-table-rib-only {
                 description
                   "Configure disable route delivery to the IP routing table.";
                 leaf enable {
                   type "boolean";
                   default "false";
                   description
                     "Enable/disable prevent BGP routes from being added to the "+
                     "IP routing table.";
                   must "not (../../common/active-route-advertise = 'true' and "+
                        "../enable = 'true')";
                 }
                 choice policy-type {
                   description
                     "Set route policy or filter.";
                   case rtp-ref {
                     description
                       "Route policy.";
                     leaf policy-name {
                       when "../enable = 'true'";
                       type "leafref" {
                         path "/rtp:routing-policy/rtp:policy-definitions/rtp:po"+
                              "licy-definition/rtp:name";
                       }
                       description
                         "When routes are imported from other routing protocols,"+
                         " the route-policy filter can be used to filter the "+
                         "routes and change route attributes.";
                     }
                   }
                   case xpl-ref {
                     description
                       "Route filter.";
                     leaf filter-name {
                       when "../enable = 'true'";
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container qos {
                 description
                   "Configure QoS.";
                 choice local-id-policy {
                   description
                     "Configure QoS local ID.";
                   case value {
                     description
                       "Specify the QoS local ID value.";
                     leaf local-id {
                       type "uint8" {
                         range "1..255";
                       }
                       description
                         "Specify the QoS local ID value.";
                     }
                   }
                   case rtp-ref {
                     description
                       "Route policy.";
                     leaf local-id-policy-name {
                       type "leafref" {
                         path "/rtp:routing-policy/rtp:policy-definitions/rtp:po"+
                              "licy-definition/rtp:name";
                       }
                       description
                         "Set a routing policy to filter routes so that a "+
                         "configured QoS ID is applied to the routes that match "+
                         "the specified policy.";
                     }
                   }
                   case xpl-ref {
                     description
                       "Route filter.";
                     leaf local-id-filter-name {
                       type "leafref" {
                         path "/xpl:xpl/xpl:route-filters/xpl:route-filter/xpl:n"+
                              "ame";
                       }
                       description
                         "Specify a route-filter name.";
                     }
                     leaf local-id-filter-parameter {
                       when "../local-id-filter-name";
                       type "xpl:filter-parameter-type";
                       description
                         "Specify a route-filter parameter.";
                     }
                   }
                 }
               }
               container region-validation {
                 presence "Enable the BGP region validation.";
                 description
                   "Configure BGP region validation.";
                 leaf region-confederation-check-strict {
                   type "boolean";
                   default "false";
                   description
                     "Enable/disable strict check on BGP region confederation "+
                     "routes.";
                 }
                 leaf bestroute {
                   type "region-validation-bestroute-type";
                   description
                     "BGP region validation result applied to route selection.";
                 }
               }
             }
             container ipv6-unicast {
               when "../type = 'ipv6uni'";
               must "../../../../../l3vpn:afs/l3vpn:af[l3vpn:type='ipv6-unicast'"+
                    "]";
               description
                 "Configure IPv6 unicast options.";
               container common {
                 description
                   "Configure IPv6 unicast common options.";
                 leaf router-id-auto-select {
                   when "../../../../../../../ni:name!='_public_'";
                   type "boolean";
                   default "false";
                   description
                     "Enable/disable router ID auto select. If a BGP VPN "+
                     "instance is not enabled to select a router ID, a router ID"+
                     " can be configured for the BGP VPN instance. If no router "+
                     "ID is configured for the BGP VPN instance, the BGP VPN "+
                     "instance inherits the router ID of the public network "+
                     "instance. If a BGP VPN instance is enabled to select a "+
                     "router ID, it uses the address of an interface bound to a "+
                     "VPN as the router ID based on the following rules:\n\n1. "+
                     "If Loopback interfaces configured with IP addresses exist,"+
                     " the largest IP address among the IP addresses of the "+
                     "Loopback interfaces is selected as the router ID.\n\n2. If"+
                     " there is no Loopback interface configured with an IP "+
                     "address, the largest IP address among the IP addresses of "+
                     "other interfaces is selected as the router ID, regardless "+
                     "of whether the interface is Up.";
                 }
                 leaf router-id {
                   when "../../../../../../../ni:name!='_public_' and ../router-"+
                        "id-auto-select = 'false'";
                   type "inet:ipv4-address-no-zone";
                   description
                     "ID of a router that is in IPv4 address format. Certain "+
                     "dynamic routing protocols require a router ID. If no "+
                     "router ID is specified for a router when these protocols "+
                     "are enabled, the router ID in the RM module is used by "+
                     "default. The default router ID in the RM module is 0.0.0.0"+
                     " when the router is not configured with any interface. "+
                     "\nThe rules for selecting a router ID are as follows:\n1. "+
                     "If a router ID is set through this configuration, the set "+
                     "router ID is used. If the router ID is not set, a router "+
                     "ID is selected according to the following rules:\n(1) If "+
                     "loopback interfaces configured with IP addresses exist, "+
                     "the largest IP address among the IP addresses of the "+
                     "loopback interfaces is selected as the router ID.\n(2) If "+
                     "no loopback interface configured with an IP address "+
                     "exists, the largest IP address among the IP addresses of "+
                     "other interfaces is selected as the router ID, regardless "+
                     "of whether the interface is Up.\nThe router ID is "+
                     "reselected only when the interface address that is "+
                     "selected as the router ID is deleted or changed. The "+
                     "router ID is not reselected in any of the following "+
                     "cases:\na. The interface is Down.\nb. A loopback interface"+
                     " is configured when the IP address of a non-loopback "+
                     "interface is selected as the router ID.\nc. A larger IP "+
                     "address of an interface is configured.\n2. Each VPN "+
                     "instance selects the router ID from the addresses of the "+
                     "interfaces of the VPN instance according to the preceding "+
                     "rules.\n3. When both the AMB and SMB exist on the router, "+
                     "the system backs up the router ID set through the related "+
                     "command and the router ID that is selected from IP "+
                     "addresses of the interfaces. After the active/standby "+
                     "switchover is performed, the system checks the validity of"+
                     " the router ID selected from the interface addresses. If "+
                     "the router ID is invalid, the system reselects a router "+
                     "ID.";
                 }
                 leaf auto-frr {
                   type "boolean";
                   default "false";
                   description
                     "Enable/disable BGP auto FRR. If IP FRR, VPN FRR, and Auto "+
                     "FRR are all enabled, IP FRR and VPN FRR take precedence "+
                     "over Auto FRR. If a route fails to match the routing "+
                     "policy of IP FRR or VPN FRR, Auto FRR takes effect.";
                 }
                 leaf maximum-load-balancing-ibgp {
                   type "uint16" {
                     range "1..128";
                   }
                   default "1";
                   description
                     "Specify the maximum number of equal-cost IBGP routes. The "+
                     "value range and default value are controlled by the PAF.";
                   must "not (../maximum-load-balancing>1 or ../maximum-load-bal"+
                        "ancing-eibgp or ../load-balancing-eibgp-enable='true') "+
                        "or ../maximum-load-balancing-ibgp=1";
                 }
                 leaf maximum-load-balancing-ebgp {
                   type "uint16" {
                     range "1..128";
                   }
                   default "1";
                   description
                     "Specify the maximum number of equal-cost EBGP routes. The "+
                     "value range and default value are controlled by the PAF.";
                   must "not (../maximum-load-balancing>1 or ../maximum-load-bal"+
                        "ancing-eibgp or ../load-balancing-eibgp-enable='true') "+
                        "or ../maximum-load-balancing-ebgp=1";
                 }
                 leaf explicit-null {
                   when "../../../../../../../ni:name='_public_'";
                   type "boolean";
                   must "not(../lsp-operation='pop-go' and ../explicit-null='tru"+
                        "e')";
                   default "false";
                   description
                     "Enable/disable the function to explicit null. After 6PE "+
                     "routes are enabled to share a single label, all routes "+
                     "share the explicit-null label 2 when the 6PE sends IPv6 "+
                     "routes to its 6PE peer. This can save label resources on "+
                     "the 6PE. Therefore, when there are a large number of IPv6 "+
                     "routes that need to be sent, the problem that the IPv6 "+
                     "routes cannot be forwarded due to the shortage of labels "+
                     "can be avoided.";
                 }
                 leaf lsp-operation {
                   when "../../../../../../../ni:name='_public_'";
                   type "lsp-operation-type";
                   must "not(../lsp-operation='pop-go' and ../explicit-null='tru"+
                        "e')";
                   default "pop";
                   description
                     "Label operation mode.";
                 }
                 leaf nexthop-select-depend-type {
                   when "../../../../../../../ni:name='_public_'";
                   type "select-depend-type";
                   default "depend-tunnel";
                   description
                     "Specify the route iteration mode: IP or tunnel. In tunnel "+
                     "mode, the labeled BGP IPv4 route can participate in route "+
                     "selection only after its next hop is iterated to an LSP. "+
                     "In IP \nmode, the labeled BGP IPv4 route can participate "+
                     "in route selection only after its next hop is iterated to "+
                     "an IP address. By default, the labeled BGP IPv4 route can "+
                     "participate in route selection \nif its next hop can be "+
                     "iterated to an IP address, regardless of whether the LSP "+
                     "of the next hop exists. This allows the RR that is not "+
                     "enabled with MPLS to forward labeled routes. In non-RR "+
                     "\nnetworking or RR networking where the BGP next hop is "+
                     "changed, BGP needs to check whether there is an LSP "+
                     "destined for the next hop. If such an LSP is not found, "+
                     "BGP needs to establish an LSP in \nadvance. If the default"+
                     " setting is adopted, a labeled BGP IPv4 unicast route may "+
                     "be selected prior to LSP establishment. As a result, "+
                     "services are incorrectly switched before LSP establishment"+
                     " and \nservice stability is affected. Therefore, allow "+
                     "route selection only after the labeled BGP IPv4 route is "+
                     "iterated to an LSP.";
                 }
                 leaf nexthop-inherit-ip-cost {
                   when "../nexthop-select-depend-type='depend-tunnel'";
                   type "boolean";
                   default "false";
                   description
                     "Enable/disable next hop iteration mode to IP. Specify the "+
                     "route iteration mode: IP or tunnel. In tunnel mode, the "+
                     "labeled BGP IPv4 route can participate in route selection "+
                     "only after its next hop is iterated to an LSP.";
                 }
                 leaf nexthop-resolve-aigp {
                   type "boolean";
                   default "false";
                   description
                     "Enable/disable route with AIGP attribute for route "+
                     "selection.";
                 }
                 leaf supernet-unicast-advertise {
                   type "boolean";
                   default "false";
                   description
                     "Enable/disable advertise supernet unicast routes.";
                 }
                 leaf bestroute-med-confederation {
                   when "../../../../../../../ni:name='_public_'";
                   type "boolean";
                   default "false";
                   description
                     "Enable/disable BGP to compare Med value only within the "+
                     "federation.";
                 }
                 leaf bestroute-as-path-ignore {
                   type "boolean";
                   must "../bestroute-as-path-ignore = 'false' or ../load-balanc"+
                        "-as-path-ignore ='false' or not(../load-balanc-as-path-"+
                        "ignore)";
                   default "false";
                   description
                     "Enable/disable BGP to ignore the AS_Path attribute when "+
                     "selecting the optimal route. By default, BGP uses the "+
                     "AS_Path attribute as one of route selection rules, and a "+
                     "route with a shorter AS_Path is preferred. After "+
                     "bestroute-as-path-ignore is selected, BGP does not compare"+
                     " the AS_Path length.";
                 }
                 leaf determin-med {
                   type "boolean";
                   default "false";
                   description
                     "Enable/disable deterministic MED so that the route "+
                     "selection result is relevant to the sequence in which "+
                     "routes are received.";
                 }
                 leaf best-external {
                   when "../../../../../../../ni:name='_public_'";
                   type "boolean";
                   must "../best-external ='false' or ../determin-med ='false'";
                   default "false";
                   description
                     "Enable/disable best external route selection.";
                 }
                 leaf attribute-set-enable {
                   when "../../../../../../../ni:name!='_public_'";
                   type "boolean";
                   default "false";
                   description
                     "Enable/disable the capability of processing attribute "+
                     "set.";
                 }
                 leaf attribute-set-mode {
                   when "../attribute-set-enable='true'";
                   type "bgp:attribute-set-type";
                   default "both";
                   description
                     "The processing mode of attribute set.";
                 }
                 leaf add-path-select-num {
                   when "../../../../../../../ni:name='_public_'";
                   type "uint8" {
                     range "2..64";
                   }
                   must "../determin-med ='false'";
                   description
                     "Number of add-path routes.";
                 }
                 leaf load-balanc-igp-metric-ignore {
                   type "boolean";
                   default "false";
                   description
                     "Enable/disable BGP to ignore the IGP cost of each BGP "+
                     "route to the next hop when selecting routes for load "+
                     "balancing. By default, only the routes with the same IGP "+
                     "cost can participate in load balancing.";
                 }
                 leaf load-balanc-as-path-ignore {
                   type "boolean";
                   must "../load-balanc-as-path-ignore ='false' or (../load-bala"+
                        "nc-as-path-relax ='false' and ../bestroute-as-path-igno"+
                        "re ='false')";
                   default "false";
                   description
                     "Enable/disable BGP to ignore the AS_Path of each BGP route"+
                     " to the next hop when selecting routes for load balancing."+
                     " By default, only the routes with the same AS_Path can "+
                     "participate in load balancing.";
                 }
                 leaf load-balanc-as-path-relax {
                   type "boolean";
                   must "../load-balanc-as-path-relax ='false' or ../load-balanc"+
                        "-as-path-ignore ='false'";
                   default "false";
                   description
                     "Enable/disable BGP to ignore comparison of AS_Path "+
                     "attributes with the same length. By default, only the "+
                     "routes with the same AS_Path can participate in load "+
                     "balancing.";
                 }
                 leaf maximum-load-balancing {
                   type "uint16" {
                     range "1..128";
                   }
                   default "1";
                   description
                     "Specify the maximum number of equal-cost routes in the BGP"+
                     " routing table. The value depends on the associated "+
                     "license. Equal-cost BGP routes can be generated for load "+
                     "balancing only when the BGP routes meet the first nine "+
                     "rules of the route-selection policy and have the same "+
                     "AS-Path attribute. The value range and default value are "+
                     "controlled by the PAF.";
                   must "not (../maximum-load-balancing-ibgp>1 or ../maximum-loa"+
                        "d-balancing-ebgp>1 or ../maximum-load-balancing-eibgp) "+
                        "or ../maximum-load-balancing=1";
                 }
                 leaf best-route-bit-error-detection {
                   when "../../../../../../../ni:name!='_public_'";
                   type "boolean";
                   default "false";
                   description
                     "Enable/disable the function to reroute traffic when a bit "+
                     "error event occurs.";
                 }
                 leaf import-rib-nexthop-invariable {
                   when "../../../../../../../ni:name!='_public_'";
                   type "boolean";
                   default "false";
                   description
                     "Enable/disable advertise the route without modifying the "+
                     "next-hop.";
                 }
                 leaf route-relay-tunnel-v4 {
                   type "boolean";
                   default "false";
                   description
                     "Enable/disable unicast-route recursive-lookup tunnel.";
                 }
                 leaf route-relay-tunnel-v4-selector {
                   when "../route-relay-tunnel-v4='true'";
                   type "leafref" {
                     path "/rtp:routing-policy/rtp:tunnel-selectors/rtp:tunnel-s"+
                          "elector/rtp:name";
                   }
                   description
                     "Unicast route tunnel selector name.";
                 }
                 leaf route-relay-tunnel-v6-selector {
                   when "../../../../../../../ni:name='_public_'";
                   type "leafref" {
                     path "/rtp:routing-policy/rtp:tunnel-selectors/rtp:tunnel-s"+
                          "elector/rtp:name";
                   }
                   description
                     "Enable/disable unicast route recursive-lookup IPv6 tunnel "+
                     "by tunnel selector name.";
                 }
                 leaf bestroute-med-plus-igp {
                   type "boolean";
                   must "not(../bestroute-igp-metric-ignore='true' and "+
                        "../bestroute-med-plus-igp='true')";
                   default "false";
                   description
                     "Enable/disable the function to add the IGP cost to the "+
                     "next-hop destination to the MED before comparing MED "+
                     "values for path selection.";
                 }
                 leaf bestroute-med-multiplier {
                   when "../bestroute-med-plus-igp='true'";
                   type "uint16" {
                     range "1..1000";
                   }
                   default "1";
                   description
                     "Value of med product factor.";
                 }
                 leaf bestroute-igp-multiplier {
                   when "../bestroute-med-plus-igp='true'";
                   type "uint16" {
                     range "1..1000";
                   }
                   default "1";
                   description
                     "Value of IGP cost product factor.";
                 }
                 leaf bestroute-igp-metric-ignore {
                   type "boolean";
                   default "false";
                   description
                     "Enable/disable BGP to ignore the IGP cost of each BGP "+
                     "route to the next hop in route selection. By default, a "+
                     "BGP route with a smaller IGP cost to the next hop is "+
                     "preferred.";
                   must "not(../bestroute-igp-metric-ignore='true' and "+
                        "../bestroute-med-plus-igp='true')";
                 }
                 leaf bestroute-router-id-prior-clusterlist {
                   type "boolean";
                   default "false";
                   description
                     "Enable/disable BGP to compare originator before clusterlis"+
                     "t in route selection.";
                 }
                 leaf bestroute-med-none-as-maximum {
                   type "boolean";
                   default "false";
                   description
                     "Enable/disable BGP considers its MED as the largest MED "+
                     "value (4294967295). If a route does not carry MED, BGP "+
                     "considers its MED as the default value (0) during route "+
                     "selection.";
                 }
                 leaf bestroute-rd-large-first {
                   when "../../../../../../../ni:name!='_public_'";
                   type "boolean";
                   default "false";
                   description
                     "Enable/disable a BGP device to select the route with the "+
                     "largest route distinguisher (RD) during route selection.";
                 }
                 leaf nexthop-priority {
                   when "../../../../../../../ni:name!='_public_'";
                   type "nexthop-priority-address-type";
                   description
                     "In the VRF instance, routes with next-hop IPv4 addresses "+
                     "and routes with next-hop IPv6 addresses coexist. If the "+
                     "next-hop address type is set to IPv4, routes with next-hop"+
                     " IPv4 addresses have a higher priority. If the next-hop "+
                     "address type is set to IPv6, routes with next-hop IPv6 "+
                     "addresses have a higher priority.";
                 }
                 leaf ebgp-ecmp-nexthop-changed {
                   when "../maximum-load-balancing-ebgp and ../maximum-load-bala"+
                        "ncing-ebgp>1";
                   type "boolean";
                   default "false";
                   description
                     "Enable/disable next hop of equal-cost EBGP routes is "+
                     "changed. Enable/disable next hop of equal-cost EBGP routes"+
                     " is changed. When equal-cost EBGP routes are load-balancin"+
                     "g traffic, the next hop of these routes is changed to a "+
                     "local interface before these routes are advertised. This "+
                     "function can be enabled only when the maximum number of "+
                     "equal-cost EBGP routes is greater than 1.";
                 }
                 leaf ibgp-ecmp-nexthop-changed {
                   when "../maximum-load-balancing-ibgp and ../maximum-load-bala"+
                        "ncing-ibgp>1";
                   type "boolean";
                   default "false";
                   description
                     "Enable/disable next hop of equal-cost IBGP routes is "+
                     "changed. When equal-cost IBGP routes are load-balancing "+
                     "traffic, the next hop of these routes is changed to a "+
                     "local interface before these routes are advertised. This "+
                     "function can be enabled only when the maximum number of "+
                     "equal-cost IBGP routes is greater than 1.";
                 }
                 leaf ecmp-nexthop-changed {
                   when "../maximum-load-balancing and ../maximum-load-balancing"+
                        ">1";
                   type "boolean";
                   default "false";
                   description
                     "Enable/disable next hop of equal-cost routes is changed. "+
                     "When equal-cost BGP routes are load-balancing traffic, the"+
                     " next hop of these routes is changed to a local interface "+
                     "before these routes are advertised. This function can be "+
                     "enabled only when the maximum number of equal-cost BGP "+
                     "routes is greater than 1.";
                 }
                 leaf maximum-load-balancing-eibgp {
                   when "../../../../../../../ni:name!='_public_'";
                   type "uint16" {
                     range "1..128";
                   }
                   must "../maximum-load-balancing-ibgp=1 and ../maximum-load-ba"+
                        "lancing-ebgp=1 and ../maximum-load-balancing=1 and "+
                        "../load-balancing-eibgp-enable='false'";
                   description
                     "Specify the maximum number of equal-cost EBGP routes and "+
                     "IBGP routes. After the attribute is set, load balancing is"+
                     " performed among equal-cost BGP VPN routes, regardless of "+
                     "the route type, EBGP or IBGP. The value range and default "+
                     "value are controlled by the PAF.";
                 }
                 leaf eibgp-ecmp-nexthop-changed {
                   when "../maximum-load-balancing-eibgp";
                   type "boolean";
                   default "false";
                   description
                     "Enable/disable next hop of equal-cost EBGP and IBGP routes"+
                     " is changed. When equal-cost EBGP and IBGP routes are "+
                     "load-balancing traffic, the next hop of these routes is "+
                     "changed to a local interface before these routes are "+
                     "advertised.";
                 }
                 leaf load-balancing-eibgp-enable {
                   when "../../../../../../../ni:name!='_public_'";
                   type "boolean";
                   must "not (../maximum-load-balancing-ibgp>1 or ../maximum-loa"+
                        "d-balancing-ebgp>1 or ../maximum-load-balancing-eibgp) "+
                        "or ../load-balancing-eibgp-enable='false'";
                   default "false";
                   description
                     "Enable/disable EIBGP route load balancing.";
                 }
                 leaf prefix-origin-as-validation {
                   type "boolean";
                   default "false";
                   description
                     "Enable/disable the BGP prefix origin validation.";
                 }
                 leaf bestroute-origin-as-validation {
                   when "../prefix-origin-as-validation='true'";
                   type "boolean";
                   default "false";
                   description
                     "Enable/disable the BGP origin AS validation result.";
                 }
                 leaf bestroute-allow-invalid-as {
                   when "../bestroute-origin-as-validation='true'";
                   type "boolean";
                   default "false";
                   description
                     "Enable/disable routes with BGP origin AS validation result"+
                     " invalid to be selected.";
                 }
                 leaf advertise-route-mode {
                   when "../../../../../../../ni:name!='_public_'";
                   type "bgp-advertise-route-mode";
                   default "all";
                   description
                     "VPN advertise route mode.";
                 }
                 leaf route-select-delay {
                   type "uint16" {
                     range "0..3600";
                   }
                   units "s";
                   default "0";
                   description
                     "Route selection delay.";
                 }
                 choice reflector-type {
                   description
                     "Set IPv4 address or id.";
                   case address {
                     description
                       "IPv4 address.";
                     leaf reflector-cluster-ipv4 {
                       type "inet:ipv4-address-no-zone";
                       description
                         "Set a cluster ID. The value is expressed in the format"+
                         " of an IPv4 address. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                   case id {
                     description
                       "Set value.";
                     leaf reflector-cluster-id {
                       type "uint32" {
                         range "1..4294967295";
                       }
                       description
                         "Set a cluster ID. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                 }
                 leaf reflect-change-path {
                   type "boolean";
                   default "false";
                   description
                     "Enable/disable an RR to use an export policy to change "+
                     "route AS_Path.";
                 }
                 leaf always-compare-med {
                   type "boolean";
                   default "false";
                   description
                     "Enable/disable BGP to compare the MEDs of routes from "+
                     "peers in different ASs in route selection. If \nthere are "+
                     "multiple reachable routes to the same destination, the "+
                     "route with the smallest MED is preferred. Do not use this "+
                     "option unless different ASs use the same IGP and route "+
                     "selection mode.";
                 }
                 leaf default-med {
                   type "uint32";
                   default "0";
                   description
                     "Specify the Multi-Exit-Discriminator (MED) of BGP routes. "+
                     "The value is an integer. This value is valid only for the "+
                     "imported routes and BGP summarized routes on the local "+
                     "router.";
                 }
                 leaf nexthop-third-party {
                   type "boolean";
                   default "false";
                   description
                     "Enable/disable BGP third-party next hop.";
                 }
                 leaf default-local-preference {
                   type "uint32" {
                     range "0..4294967295";
                   }
                   default "100";
                   description
                     "The local preference of BGP routes.";
                 }
                 leaf default-route-import {
                   type "boolean";
                   default "false";
                   description
                     "Enable/disable the function to import default routes into "+
                     "the BGP routing table. Default-route-imported must be used"+
                     " with import-routes so that default routes can be imported"+
                     " to the BGP routing table. If only import-routes is used, "+
                     "no default routes can be added to the BGP routing table. "+
                     "In addition, default-route-imported can only import the "+
                     "default routes in the routing table into the BGP routing "+
                     "table.";
                 }
                 leaf routerid-neglect {
                   type "boolean";
                   default "false";
                   description
                     "Enable/disable BGP to ignore router IDs when selecting the"+
                     " optimal route. Comparing router IDs is the last resort in"+
                     " route selection. This means that if one optimal route "+
                     "must be selected and no other parameters can be used to "+
                     "break the tie, router IDs can be used. If this option is "+
                     "selected, the first received route will be selected as the"+
                     " optimal route, and BGP will ignore the router ID and peer"+
                     " address in route selection.";
                 }
                 leaf reflect-between-client {
                   type "boolean";
                   default "true";
                   description
                     "Enable/disable route reflection between clients. If "+
                     "clients of a route reflector (RR) are fully meshed, you "+
                     "can disable route reflection among clients to reduce the "+
                     "cost.";
                 }
                 leaf ext-community-change {
                   type "boolean";
                   default "false";
                   description
                     "Enable/disable the function to change the extended "+
                     "community attribute.";
                 }
                 leaf active-route-advertise {
                   type "boolean";
                   default "false";
                   description
                     "Enable/disable the function to advertise the optimal "+
                     "routes in the RM module to peers.";
                 }
                 leaf ebgp-interface-sensitive {
                   type "boolean";
                   default "true";
                   description
                     "Enable/disable the function of EBGP interface fast "+
                     "sensing. If this function is enabled, the sessions of "+
                     "directly connected EBGP peers are immediately cleared from"+
                     " the associated interface when the interface becomes "+
                     "down.";
                 }
                 leaf load-balancing-ucmp {
                   when "../../../../../../../ni:name='_public_'";
                   type "boolean";
                   default "false";
                   description
                     "Enable/disable the function of BGP UCMP.";
                 }
               }
               container preference {
                 description
                   "Configure parameters relating to options for BGP routes "+
                   "preference.";
                 choice set-value-or-policy {
                   default "set-value";
                   description
                     "Set BGP routes preference by value or policy.";
                   case set-value {
                     description
                       "Set BGP routes preference by value.";
                     leaf external {
                       type "uint8" {
                         range "1..255";
                       }
                       default "255";
                       description
                         "Set the protocol priority of EBGP routes. The value is"+
                         " an integer. An EBGP route is the optimal route "+
                         "learned from a peer outside the local AS.";
                     }
                     leaf internal {
                       type "uint8" {
                         range "1..255";
                       }
                       default "255";
                       description
                         "Set the protocol priority of IBGP routes. The value is"+
                         " an integer. An IBGP route is a route learned from a "+
                         "peer inside the local AS.";
                     }
                     leaf local {
                       type "uint8" {
                         range "1..255";
                       }
                       default "255";
                       description
                         "Set the protocol priority of a local BGP route. A "+
                         "local route refers to an automatically or manually "+
                         "summarized route.";
                     }
                   }
                   case rtp-ref {
                     description
                       "Set BGP routes preference by route policy.";
                     leaf route-policy {
                       type "leafref" {
                         path "/rtp:routing-policy/rtp:policy-definitions/rtp:po"+
                              "licy-definition/rtp:name";
                       }
                       description
                         "Specify a routing policy to filter routes so that a "+
                         "configured priority is applied to the routes that "+
                         "match the specified policy.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container nexthop-recursive-lookup {
                 description
                   "Configure next hop iteration.";
                 container common {
                   description
                     "Configure next hop iteration common options.";
                   leaf restrain {
                     type "boolean";
                     default "true";
                     description
                       "Enable/disable the function to restrain next hop "+
                       "iteration in case of next hop flapping.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                   leaf default-route {
                     type "boolean";
                     default "false";
                     description
                       "Enable/disable default route.";
                   }
                 }
                 container delay {
                   description
                     "Configure time of next hop change responding delay.";
                   leaf time {
                     type "uint8" {
                       range "1..100";
                     }
                     units "s";
                     description
                       "Specify the delay in responding to the next hop change.";
                   }
                   leaf no-critical-event-time {
                     type "uint8" {
                       range "0..100";
                     }
                     units "s";
                     default "10";
                     description
                       "Specify the delay in responding to the next hop change "+
                       "on non critical relay change event.";
                   }
                 }
               }
               container import-routes {
                 description
                   "List of imported routes.";
                 list import-route {
                   key "protocol process-id";
                   description
                     "Configure route import. Routes of other protocol types can"+
                     " be imported by BGP. By default, BGP does not import "+
                     "routes of other protocol types.";
                   leaf protocol {
                     type "bgp:ipv6-import-route-protocol-type";
                     description
                       "Routing protocol from which routes can be imported.";
                   }
                   leaf process-id {
                     type "uint32" {
                       range "0..4294967295";
                     }
                     description
                       "Process ID of an imported routing protocol. The process "+
                       "ID is 0, if the imported routing protocol is direct "+
                       "routes, static routes, UNRs, or OP-routes. The process "+
                       "ID must be specified range from 1 to 4294967295, if the "+
                       "imported routing protocol is ISIS, RIPng, or OSPFv3.";
                     must "((../protocol='ospfv3' or ../protocol='isis' or "+
                          "../protocol='ripng') and ../process-id!=0) or "+
                          "(../protocol!='ospfv3' and ../protocol!='isis' and "+
                          "../protocol!='ripng' and ../process-id=0)";
                   }
                   leaf med {
                     type "uint32";
                     description
                       "Specifies the MED metric of the imported route.";
                   }
                   choice policy-type {
                     description
                       "Set route policy or filter.";
                     case rtp-ref {
                       description
                         "Route policy.";
                       leaf policy-name {
                         type "leafref" {
                           path "/rtp:routing-policy/rtp:policy-definitions/rtp:"+
                                "policy-definition/rtp:name";
                         }
                         description
                           "When routes are imported from other routing "+
                           "protocols, the route-policy filter can be used to "+
                           "filter the routes and change route attributes.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container aggregate-routes {
                 description
                   "List of summarized routes.";
                 list aggregate-route {
                   key "address mask-length";
                   description
                     "Configure a summarized route in the BGP routing table. The"+
                     " local outbound interface of the summarized route is "+
                     "Null0. When another router receives the route, the route "+
                     "adds an outbound interface to the route. By default, route"+
                     " summarization is not performed. If the Origin attributes "+
                     "of the specific routes for the route summarization are "+
                     "different, the Origin attribute of the summarized route is"+
                     " that with the highest priority. Origin attributes are "+
                     "arranged in the priority order of complete > egp > igp. A "+
                     "summarized route carries the community attribute of each "+
                     "specific route.";
                   leaf address {
                     type "inet:ip-address-no-zone";
                     description
                       "Specify the IPv4 address or IPv6 address of a summarized"+
                       " route. Only IPv4 summarized routes can be configured in"+
                       " the IPv4 address family and only IPv6 summarized routes"+
                       " can be configured in the IPv6 address family.";
                     must "contains(../address,':')";
                   }
                   leaf mask-length {
                     type "uint8" {
                       range "1..128";
                     }
                     description
                       "Specify the mask length of a summarized address.";
                     must "../mask-length<=128";
                   }
                   leaf as-set {
                     type "boolean";
                     default "false";
                     description
                       "Enable/disable the generation of routes with the AS-SET "+
                       "attribute. This option can be used to create a "+
                       "summarized route. The AS_Path attribute of the "+
                       "summarized route contains the AS-Path attributes of the "+
                       "specific routes for the route summarization. Exercise "+
                       "caution when using this option if multiple AS_Paths need"+
                       " to be summarized to prevent route flapping.";
                   }
                   leaf detail-suppressed {
                     type "boolean";
                     default "false";
                     description
                       "Enable/disable detail-suppressed. Suppress the "+
                       "advertisement of specific routes for the route "+
                       "summarization. Only the summarized route is advertised.";
                   }
                   choice policy-type {
                     description
                       "Set route policy or filter.";
                     case rtp-ref {
                       description
                         "Route policy.";
                       leaf attribute-policy {
                         type "leafref" {
                           path "/rtp:routing-policy/rtp:policy-definitions/rtp:"+
                                "policy-definition/rtp:name";
                         }
                         description
                           "Specify an attribute of summarized routes. If apply "+
                           "as-path is used to configure the AS_Path attribute "+
                           "that is used in the route Summarization policy, and "+
                           "the as-set keyword is set, the AS_Path attribute in "+
                           "the policy does not take effect. This parameter and "+
                           "any of the following parameters overwrite each "+
                           "other: suppressFilter, originFilter, and attributeFi"+
                           "lter.";
                       }
                       leaf origin-policy {
                         type "leafref" {
                           path "/rtp:routing-policy/rtp:policy-definitions/rtp:"+
                                "policy-definition/rtp:name";
                         }
                         description
                           "Specify the name of a policy for generating "+
                           "summarized routes. Summarized routes are generated "+
                           "only when the routes match route-policy. This "+
                           "parameter and any of the following parameters "+
                           "overwrite each other: suppressFilter, originFilter, "+
                           "and attributeFilter.";
                       }
                       leaf suppress-policy {
                         type "leafref" {
                           path "/rtp:routing-policy/rtp:policy-definitions/rtp:"+
                                "policy-definition/rtp:name";
                         }
                         description
                           "Specify a policy for suppressing the advertisement "+
                           "of specified routes. The routes matching the policy "+
                           "are not advertised, and other routes are advertised."+
                           " This parameter and any of the following parameters "+
                           "overwrite each other: suppressFilter, originFilter, "+
                           "and attributeFilter.";
                       }
                     }
                     case xpl-ref {
                       description
                         "Route filter.";
                       leaf attribute-filter-name {
                         type "leafref" {
                           path "/xpl:xpl/xpl:route-filters/xpl:route-filter/xpl"+
                                ":name";
                         }
                         description
                           "Specify a route-filter name.";
                       }
                       leaf attribute-filter-parameter {
                         when "../attribute-filter-name";
                         type "xpl:filter-parameter-type";
                         description
                           "Specify a route-filter parameter.";
                       }
                       leaf origin-filter-name {
                         type "leafref" {
                           path "/xpl:xpl/xpl:route-filters/xpl:route-filter/xpl"+
                                ":name";
                         }
                         description
                           "Specify a route-filter name.";
                       }
                       leaf origin-filter-parameter {
                         when "../origin-filter-name";
                         type "xpl:filter-parameter-type";
                         description
                           "Specify a route-filter parameter.";
                       }
                       leaf suppress-filter-name {
                         type "leafref" {
                           path "/xpl:xpl/xpl:route-filters/xpl:route-filter/xpl"+
                                ":name";
                         }
                         description
                           "Specify a route-filter name.";
                       }
                       leaf suppress-filter-parameter {
                         when "../suppress-filter-name";
                         type "xpl:filter-parameter-type";
                         description
                           "Specify a route-filter parameter.";
                       }
                     }
                   }
                 }
               }
               container aggregate-default-route {
                 description
                   "Configure aggregate default route.";
                 leaf origin-ipv6-prefix {
                   type "leafref" {
                     path "/rtp:routing-policy/rtp:ipv6-prefix-filters/rtp:ipv6-"+
                          "prefix-filter/rtp:name";
                   }
                   description
                     "Specify the name of an IPv6 prefix list for a summary "+
                     "default route. Only the name of an IPv6 prefix list can be"+
                     " configured in a BGP IPv6 address family.";
                 }
                 leaf attribute-policy {
                   when "../origin-ipv6-prefix";
                   type "leafref" {
                     path "/rtp:routing-policy/rtp:policy-definitions/rtp:policy"+
                          "-definition/rtp:name";
                   }
                   description
                     "Specify an attribute policy of a summary default route.";
                 }
               }
               container network-routes {
                 description
                   "List of network routes.";
                 list network-route {
                   key "address mask-length";
                   description
                     "Configure a network route in the BGP routing table.";
                   leaf address {
                     type "inet:ipv6-address-no-zone";
                     description
                       "Specify the IP address advertised by BGP. An IPv6 routes"+
                       " can be configured in the IPv6 address family. Note: "+
                       "During the configuration of a network route, the IP "+
                       "address is adjusted based on the mask. It is recommended"+
                       " that you click Synchronize All after creating a network"+
                       " route.";
                   }
                   leaf mask-length {
                     type "uint8" {
                       range "0..128";
                     }
                     description
                       "Specify the mask length of an IP address.";
                   }
                   choice policy-type {
                     description
                       "Specify the route-policy or filter for route advertiseme"+
                       "nt.";
                     case rtp-ref {
                       description
                         "Specify the route policy.";
                       leaf policy-name {
                         type "leafref" {
                           path "/rtp:routing-policy/rtp:policy-definitions/rtp:"+
                                "policy-definition/rtp:name";
                         }
                         description
                           "Specify the route policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container advertise-route-to-evpns {
                 when "../../../../../../ni:name!='_public_'";
                 description
                   "Configure advertise route protocol.";
                 list advertise-route-to-evpn {
                   key "protocol";
                   description
                     "Configure the advertise route protocol.";
                   leaf protocol {
                     type "enumeration" {
                       enum "all" {
                         value "0";
                         description
                           "Advertise all the types of route protocol.";
                       }
                     }
                     description
                       "Route protocol.";
                   }
                   leaf import-multipath {
                     type "boolean";
                     default "false";
                     description
                       "Enable/disable route import from multiple paths.";
                   }
                   leaf include-local-cross {
                     type "boolean";
                     default "false";
                     description
                       "Enable/disable local cross route to advertise l2vpn "+
                       "evpn.";
                   }
                   leaf advertise-route-mode {
                     type "enumeration" {
                       enum "all" {
                         value "0";
                         description
                           "All:";
                       }
                       enum "best" {
                         value "1";
                         description
                           "Best:";
                       }
                       enum "valid" {
                         value "2";
                         description
                           "Valid:";
                       }
                     }
                     default "all";
                     description
                       "VPN advertise route mode to evrf.";
                   }
                 }
               }
               container import-ribs {
                 description
                   "List of imported RIBs configuration.";
                 list import-rib {
                   key "source-vpn source-address-family";
                   description
                     "Configure imported RIBs.";
                   leaf source-vpn {
                     type "leafref" {
                       path "/ni:network-instance/ni:instances/ni:instance/ni:na"+
                            "me";
                     }
                     must "../../../../../../../../ni:name != current()";
                     description
                       "Source VPN name for imported RIBs.";
                   }
                   leaf source-address-family {
                     type "bgp:import-rib-ipv6-safi-type";
                     description
                       "Source address family type for imported RIBs.";
                   }
                   leaf valid-route {
                     type "boolean";
                     default "false";
                     description
                       "Enable/disable imported valid route.";
                   }
                   leaf include-label-route {
                     type "boolean";
                     default "false";
                     description
                       "Enable/disable imported include label route.";
                   }
                   choice policy-type {
                     description
                       "Set policy or filter.";
                     case rtp-ref {
                       description
                         "Specify the route policy.";
                       leaf policy-name {
                         type "leafref" {
                           path "/rtp:routing-policy/rtp:policy-definitions/rtp:"+
                                "policy-definition/rtp:name";
                         }
                         description
                           "Specify the route policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container segment-routing-ipv6 {
                 description
                   "Configure BGP segment-routing IPv6.";
                 leaf srv6-best-effort-enable {
                   type "empty";
                   description
                     "Enable SRv6 BE iteration.";
                 }
                 leaf srv6-traffic-engineer-enable {
                   type "empty";
                   description
                     "Enable SRv6 TE iteration.";
                 }
               }
               container dampening-routes {
                 description
                   "List of route dampening.";
                 list dampening-route {
                   must "reuse < suppress and suppress < ceiling";
                   key "peer-type";
                   description
                     "Configure BGP route dampening or modify various BGP route "+
                     "dampening parameters. If a suppression policy for route "+
                     "dampening is configured, routes are preferentially matched"+
                     " against the suppression parameters defined in the "+
                     "suppression policy. If no parameter is configured, the "+
                     "default value of each parameter is used. The four route "+
                     "dampening parameters are mutually dependent. If you "+
                     "configure one of the parameters, the other parameters also"+
                     " need to be configured. When you configure BGP route "+
                     "dampening, the values of reuse threshold, suppress "+
                     "threshold, and penalty ceiling must meet the inequality of"+
                     " reuse threshold < suppress threshold < penalty ceiling. "+
                     "If Maximum suppression time obtained by using the formula "+
                     "of Maximum suppression time = Half life (of reachable "+
                     "routes) x 60 x (ln (Penalty ceiling/Reuse threshold)/ln(2)"+
                     ") is smaller than 1, suppression cannot be performed. "+
                     "Ensure that the value of the maximum suppression time is "+
                     "equal to or greater than 1. This means that the value of "+
                     "the penalty ceiling/reuse threshold must be great enough.";
                   leaf peer-type {
                     type "dampening-route-peer-type";
                     description
                       "Configure the peer type.";
                   }
                   leaf half-life-time {
                     type "uint16" {
                       range "1..45";
                     }
                     units "min";
                     default "15";
                     description
                       "Configure a half-life for reachable routes.";
                   }
                   leaf reuse {
                     type "uint16" {
                       range "1..20000";
                     }
                     default "750";
                     description
                       "Configure a threshold for a route to be unsuppressed. If"+
                       " the penalty value of the route falls below the "+
                       "threshold, the route is reused.";
                   }
                   leaf suppress {
                     type "uint16" {
                       range "1..20000";
                     }
                     default "2000";
                     description
                       "Configure a threshold for a route to be suppressed. When"+
                       " the penalty value of the route exceeds the suppression "+
                       "threshold, the route is suppressed. The configured "+
                       "suppression threshold must be greater than the reuse "+
                       "threshold.";
                   }
                   leaf ceiling {
                     type "uint16" {
                       range "1001..20000";
                     }
                     default "16000";
                     description
                       "Configure the penalty ceiling. The configured threshold "+
                       "must be greater than the suppression threshold.";
                   }
                   leaf update-standard {
                     type "boolean";
                     default "false";
                     description
                       "Enable/disable update standard.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container import-filter-policy {
                 description
                   "Configure a filtering policy. It is used to filter the "+
                   "routes received from a peer. By default, routes are not "+
                   "filtered.";
                 choice ipv6-import-filter-protocol-policy-type {
                   description
                     "Set IPv6 filter protocol policy.";
                   case acl6-ref {
                     description
                       "ACL route policy.";
                     leaf acl6-name-or-num {
                       type "leafref" {
                         path "/acl:acl/acl:group6s/acl:group6/acl:identity";
                       }
                       description
                         "Specify the name or number of an ACL6 Rule. The number"+
                         " value ranges from 2000 to 2999 and is used by basic "+
                         "ACL6 rules. The name must start with a letter, and the"+
                         " name is case-sensitive.";
                     }
                   }
                   case ipv6-prefix-ref {
                     description
                       "IPv6 prefix Policy.";
                     leaf ipv6-prefix-filter {
                       type "leafref" {
                         path "/rtp:routing-policy/rtp:ipv6-prefix-filters/rtp:i"+
                              "pv6-prefix-filter/rtp:name";
                       }
                       description
                         "Specify the IPv6 prefix list name.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container export-filter-policys {
                 description
                   "List of filtering policies.";
                 list export-filter-policy {
                   key "protocol process-id";
                   description
                     "Apply a filtering policy. It is used to filter the routes "+
                     "to be advertised to the peer. By default, routes are not "+
                     "filtered.";
                   leaf protocol {
                     type "bgp:ipv6-export-filter-protocol-type";
                     description
                       "Specify the name of a routing protocol. The routing "+
                       "protocol takes effect only on the routes to be "+
                       "advertised. The IPv4 address family supports the direct,"+
                       " IS-IS, OSPF, RIP, and static routing protocols. The "+
                       "IPv6 unicast address family of a public network instance"+
                       " supports the direct, IS-IS, OSPFv3, RIPng, and static "+
                       "routing protocols. The IPv6 address family of a VPNv6 "+
                       "instance supports the direct, IS-IS, RIPng, and static "+
                       "routing protocols.";
                   }
                   leaf process-id {
                     type "uint32" {
                       range "0..4294967295";
                     }
                     description
                       "Specify the process ID required to be matched. The value"+
                       " is an integer ranging from 0 to 4294967295. If direct "+
                       "or static routes need to be filtered, no process ID is "+
                       "required.";
                     must "((../protocol='ospfv3' or ../protocol='ripng' or "+
                          "../protocol='isis') and ../process-id!=0) or "+
                          "((../protocol!='ospfv3' and ../protocol!='ripng' and "+
                          "../protocol!='isis') and ../process-id=0)";
                   }
                   choice ipv6-filter-protocol-policy-type {
                     mandatory "true";
                     description
                       "Set IPv6 filter protocol policy.";
                     case acl6-ref {
                       description
                         "The ACL Route Policy.";
                       leaf acl6-name-or-num {
                         type "leafref" {
                           path "/acl:acl/acl:group6s/acl:group6/acl:identity";
                         }
                         description
                           "Specify the name or number of an ACL6 Rule. The "+
                           "number value ranges from 2000 to 2999 and is used by"+
                           " basic ACL6 rules. The name must start with a "+
                           "letter, and the name is case-sensitive.";
                       }
                     }
                     case ipv6-prefix-ref {
                       description
                         "IPv6 prefix Policy.";
                       leaf ipv6-prefix-filter {
                         type "leafref" {
                           path "/rtp:routing-policy/rtp:ipv6-prefix-filters/rtp"+
                                ":ipv6-prefix-filter/rtp:name";
                         }
                         description
                           "Specify the IPv6 prefix list name.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container slow-peer {
                 description
                   "Configure peer advertising routes slowly.";
                 leaf detection {
                   type "boolean";
                   default "true";
                   description
                     "Enable/disable detect slow peers.";
                 }
                 leaf detection-threshold {
                   type "uint16" {
                     range "120..3600";
                   }
                   units "s";
                   default "300";
                   description
                     "Specify the time in seconds lagging behind average when a "+
                     "peer is determined to be a slow peer.";
                 }
                 leaf absolute-detection {
                   type "boolean";
                   default "true";
                   description
                     "Enable/disable absolute-detect slow peers.";
                 }
                 leaf absolute-detection-threshold {
                   type "uint16" {
                     range "3..3600";
                   }
                   units "s";
                   default "9";
                   description
                     "Specify the packet send delay time in second when a peer "+
                     "is determined to be a slow peer.";
                 }
               }
               container routing-table-rib-only {
                 description
                   "Configure disable route delivery to the IP routing table.";
                 leaf enable {
                   type "boolean";
                   default "false";
                   description
                     "Enable/disable prevent BGP routes from being added to the "+
                     "IP routing table.";
                   must "not (../../common/active-route-advertise = 'true' and "+
                        "../enable = 'true')";
                 }
                 choice policy-type {
                   description
                     "Set route policy or filter.";
                   case rtp-ref {
                     description
                       "Route policy.";
                     leaf policy-name {
                       when "../enable = 'true'";
                       type "leafref" {
                         path "/rtp:routing-policy/rtp:policy-definitions/rtp:po"+
                              "licy-definition/rtp:name";
                       }
                       description
                         "When routes are imported from other routing protocols,"+
                         " the route-policy filter can be used to filter the "+
                         "routes and change route attributes.";
                     }
                   }
                   case xpl-ref {
                     description
                       "Route filter.";
                     leaf filter-name {
                       when "../enable = 'true'";
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container qos {
                 description
                   "Configure QoS.";
                 choice local-id-policy {
                   description
                     "Configure QoS local ID.";
                   case value {
                     description
                       "Specify the QoS local ID value.";
                     leaf local-id {
                       type "uint8" {
                         range "1..255";
                       }
                       description
                         "Specify the QoS local ID value.";
                     }
                   }
                   case rtp-ref {
                     description
                       "Route policy.";
                     leaf local-id-policy-name {
                       type "leafref" {
                         path "/rtp:routing-policy/rtp:policy-definitions/rtp:po"+
                              "licy-definition/rtp:name";
                       }
                       description
                         "Set a routing policy to filter routes so that a "+
                         "configured QoS ID is applied to the routes that match "+
                         "the specified policy.";
                     }
                   }
                   case xpl-ref {
                     description
                       "Route filter.";
                     leaf local-id-filter-name {
                       type "leafref" {
                         path "/xpl:xpl/xpl:route-filters/xpl:route-filter/xpl:n"+
                              "ame";
                       }
                       description
                         "Specify a route-filter name.";
                     }
                     leaf local-id-filter-parameter {
                       when "../local-id-filter-name";
                       type "xpl:filter-parameter-type";
                       description
                         "Specify a route-filter parameter.";
                     }
                   }
                 }
                 leaf ipv6-qppb {
                   type "boolean";
                   default "false";
                   description
                     "Enable/disable IPv6 QPPB for BGP.";
                 }
               }
               container region-validation {
                 presence "Enable the BGP region validation.";
                 description
                   "Configure BGP region validation.";
                 leaf region-confederation-check-strict {
                   type "boolean";
                   default "false";
                   description
                     "Enable/disable strict check on BGP region confederation "+
                     "routes.";
                 }
                 leaf bestroute {
                   type "region-validation-bestroute-type";
                   description
                     "BGP region validation result applied to route selection.";
                 }
               }
             }
             container ipv4-vpn {
               when "../type = 'ipv4vpn'";
               description
                 "Configure IPv4 VPNv4 options.";
               leaf policy-vpntarget {
                 type "boolean";
                 default "true";
                 description
                   "Enable/disable VPN target-based filtering for the received "+
                   "VPN routes. Only the VPN route whose Export RT attribute "+
                   "matches the local Import RT attribute can be added to the "+
                   "routing table. This option can be used in the inter-AS VPN "+
                   "Option B solution and the ASBR MP-EBGP inter-AS L2VPN "+
                   "solution in Kompella mode.";
               }
               choice reflector-type {
                 description
                   "Set IPv4 address or id.";
                 case address {
                   description
                     "IPv4 address.";
                   leaf reflector-cluster-ipv4 {
                     type "inet:ipv4-address-no-zone";
                     description
                       "Set a cluster ID. The value is expressed in the format "+
                       "of an IPv4 address. Configuring multiple RRs in a "+
                       "cluster can enhance the stability of the network. If a "+
                       "cluster has more than one RR, select this option to set "+
                       "the same cluster ID for all the RRs to avoid routing "+
                       "loops. To allow clients to receive routes from RRs, "+
                       "ensure that the cluster ID of the RRs is different from "+
                       "the router ID of any client. If the cluster ID of the "+
                       "RRs is the same as the router ID of a client, the client"+
                       " will discard received routes.";
                   }
                 }
                 case id {
                   description
                     "Set value.";
                   leaf reflector-cluster-id {
                     type "uint32" {
                       range "1..4294967295";
                     }
                     description
                       "Set a cluster ID. Configuring multiple RRs in a cluster "+
                       "can enhance the stability of the network. If a cluster "+
                       "has more than one RR, select this option to set the same"+
                       " cluster ID for all the RRs to avoid routing loops. To "+
                       "allow clients to receive routes from RRs, ensure that "+
                       "the cluster ID of the RRs is different from the router "+
                       "ID of any client. If the cluster ID of the RRs is the "+
                       "same as the router ID of a client, the client will "+
                       "discard received routes.";
                   }
                 }
               }
               leaf reflect-change-path {
                 type "boolean";
                 default "false";
                 description
                   "Enable/disable an RR to use an export policy to change route"+
                   " AS_Path.";
               }
               leaf auto-frr {
                 type "boolean";
                 default "false";
                 description
                   "Enable/disable BGP Auto FRR. If IP FRR, VPN FRR, and Auto "+
                   "FRR are all enabled, IP FRR and VPN FRR take precedence over"+
                   " Auto FRR. If a route fails to match the routing policy of "+
                   "IP FRR or VPN FRR, Auto FRR takes effect.";
               }
               leaf tunnel-selector-name {
                 type "leafref" {
                   path "/rtp:routing-policy/rtp:tunnel-selectors/rtp:tunnel-sel"+
                        "ector/rtp:name";
                 }
                 description
                   "Configure a tunnel selector and apply it to the BGP IPv4 "+
                   "unicast, BGP VPNv4 address families and BGP VPNv6 address "+
                   "families so that IPv4,VPNv4 and VPNv6 labeled routes can be "+
                   "iterated to tunnels based on the tunnel selector.";
               }
               leaf route-select-delay {
                 type "uint16" {
                   range "0..3600";
                 }
                 units "s";
                 default "0";
                 description
                   "Route selection delay.";
               }
               leaf apply-label-mode {
                 type "apply-label-type";
                 default "per-route";
                 description
                   "Method of distributing labels to VPNV4 and VPNV6 routes. The"+
                   " way which assigns the label depends on the paf value. If "+
                   "there are a large number of routes, assign a label for the "+
                   "routes that have same nexthop and out-label. This allows all"+
                   " routes which have same nexthop and out-label to use one "+
                   "label.";
               }
               leaf nexthop-select-depend-type {
                 type "select-depend-type-ext";
                 default "depend-ip";
                 description
                   "In none mode, route selection does not depend on whether the"+
                   " next hop is reachable. In tunnel mode, the labeled BGP IPv4"+
                   " route can participate in route selection only after its "+
                   "next hop is iterated to an LSP. In IP \nmode, the labeled "+
                   "BGP IPv4 route can participate in route selection only after"+
                   " its next hop is iterated to an IP address. By default, the "+
                   "labeled BGP IPv4 route can participate in route selection "+
                   "\nif its next hop can be iterated to an IP address, "+
                   "regardless of whether the LSP of the next hop exists. This "+
                   "allows the RR that is not enabled with MPLS to forward "+
                   "labeled routes. In non-RR \nnetworking or RR networking "+
                   "where the BGP next hop is changed, BGP needs to check "+
                   "whether there is an LSP destined for the next hop. If such "+
                   "an LSP is not found, BGP needs to establish an LSP in "+
                   "\nadvance. If the default setting is adopted, a labeled BGP "+
                   "IPv4 unicast route may be selected prior to LSP establishmen"+
                   "t. As a result, services are incorrectly switched before LSP"+
                   " establishment and \nservice stability is affected. "+
                   "Therefore, allow route selection only after the labeled BGP "+
                   "IPv4 route is iterated to an LSP.";
               }
               leaf default-med {
                 type "uint32";
                 default "0";
                 description
                   "Specify the Multi-Exit-Discriminator (MED) of BGP routes. "+
                   "The value is an integer. This value is valid only for the "+
                   "imported routes and BGP summarized routes on the local "+
                   "router.";
               }
               leaf best-external {
                 when "../../../../../../ni:name='_public_'";
                 type "boolean";
                 default "false";
                 description
                   "Enable/disable best external route selection.";
               }
               leaf label-free-delay {
                 type "uint8" {
                   range "0..180";
                 }
                 units "s";
                 default "0";
                 description
                   "Label free delay.";
               }
               leaf add-path-select-num {
                 when "../../../../../../ni:name='_public_'";
                 type "uint8" {
                   range "2..64";
                 }
                 description
                   "Number of Add-Path routes.";
               }
               leaf default-local-preference {
                 type "uint32" {
                   range "0..4294967295";
                 }
                 default "100";
                 description
                   "The local preference of BGP routes.";
               }
               leaf bestroute-med-plus-igp {
                 type "boolean";
                 must "not(../bestroute-igp-metric-ignore='true' and ../bestrout"+
                      "e-med-plus-igp='true')";
                 default "false";
                 description
                   "Enable/disable the function to add the IGP cost to the "+
                   "next-hop destination to the MED before comparing MED values "+
                   "for path selection.";
               }
               leaf bestroute-med-multiplier {
                 when "../bestroute-med-plus-igp='true'";
                 type "uint16" {
                   range "1..1000";
                 }
                 default "1";
                 description
                   "Value of med product factor.";
               }
               leaf bestroute-igp-multiplier {
                 when "../bestroute-med-plus-igp='true'";
                 type "uint16" {
                   range "1..1000";
                 }
                 default "1";
                 description
                   "Value of IGP cost product factor.";
               }
               leaf bestroute-igp-metric-ignore {
                 type "boolean";
                 default "false";
                 description
                   "Enable/disable BGP to ignore the IGP cost of each BGP route "+
                   "to the next hop in route selection. By default, a BGP route "+
                   "with a smaller IGP cost to the next hop is preferred.";
                 must "not(../bestroute-igp-metric-ignore='true' and ../bestrout"+
                      "e-med-plus-igp='true')";
               }
               leaf bestroute-router-id-prior-clusterlist {
                 type "boolean";
                 default "false";
                 description
                   "Enable/disable BGP to compare originator before clusterlist "+
                   "in route selection.";
               }
               leaf reflect-between-client {
                 type "boolean";
                 default "true";
                 description
                   "Enable/disable route reflection between clients. If clients "+
                   "of a route reflector (RR) are fully meshed, you can disable "+
                   "route reflection among clients to reduce the cost.";
               }
               leaf activate-route-tag {
                 type "boolean";
                 default "false";
                 description
                   "Enable/disable tag-based filtering.";
               }
               leaf route-reflector-ext-community-filter {
                 type "leafref" {
                   path "/rtp:routing-policy/rtp:ext-community-filters/rtp:ext-c"+
                        "ommunity-filter/rtp:name";
                 }
                 description
                   "Set the name of the extended community filter supported by "+
                   "an RR group. For the purpose of load balancing, only the "+
                   "IBGP route whose route-target extended community attribute "+
                   "meets the matching rules can be reflected.";
               }
               leaf load-balancing-eibgp-enable {
                 type "boolean";
                 default "false";
                 description
                   "Enable/disable EIBGP route load balancing.";
               }
               leaf load-balanc-igp-metric-ignore {
                 type "boolean";
                 default "false";
                 description
                   "Enable/disable BGP to ignore the IGP cost of each BGP route "+
                   "to the next hop when selecting routes for load balancing. By"+
                   " default, only the routes with the same IGP cost can "+
                   "participate in load balancing.";
               }
               leaf load-balanc-as-path-ignore {
                 type "boolean";
                 must "../load-balanc-as-path-ignore ='false' or ../load-balanc-"+
                      "as-path-relax ='false'";
                 default "false";
                 description
                   "Enable/disable BGP to ignore the AS_Path of each BGP route "+
                   "to the next hop when selecting routes for load balancing. By"+
                   " default, only the routes with the same AS_Path can "+
                   "participate in load balancing.";
               }
               leaf load-balanc-as-path-relax {
                 type "boolean";
                 must "../load-balanc-as-path-relax ='false' or ../load-balanc-a"+
                      "s-path-ignore ='false'";
                 default "false";
                 description
                   "Enable/disable BGP to ignore comparison of AS_Path "+
                   "attributes with the same length. By default, only the routes"+
                   " with the same AS_Path can participate in load balancing.";
               }
               container dampening-routes {
                 description
                   "List of route dampening.";
                 list dampening-route {
                   must "reuse < suppress and suppress < ceiling";
                   key "peer-type";
                   description
                     "Configure BGP route dampening or modify various BGP route "+
                     "dampening parameters. If a suppression policy for route "+
                     "dampening is configured, routes are preferentially matched"+
                     " against the suppression parameters defined in the "+
                     "suppression policy. If no parameter is configured, the "+
                     "default value of each parameter is used. The four route "+
                     "dampening parameters are mutually dependent. If you "+
                     "configure one of the parameters, the other parameters also"+
                     " need to be configured. When you configure BGP route "+
                     "dampening, the values of reuse threshold, suppress "+
                     "threshold, and penalty ceiling must meet the inequality of"+
                     " reuse threshold < suppress threshold < penalty ceiling. "+
                     "If Maximum suppression time obtained by using the formula "+
                     "of Maximum suppression time = Half life (of reachable "+
                     "routes) x 60 x (ln (Penalty ceiling/Reuse threshold)/ln(2)"+
                     ") is smaller than 1, suppression cannot be performed. "+
                     "Ensure that the value of the maximum suppression time is "+
                     "equal to or greater than 1. This means that the value of "+
                     "the penalty ceiling/reuse threshold must be great enough.";
                   leaf peer-type {
                     type "bgp:dampening-route-ext-peer-type";
                     description
                       "Configure the peer type.";
                   }
                   leaf half-life-time {
                     type "uint16" {
                       range "1..45";
                     }
                     units "min";
                     default "15";
                     description
                       "Configure a half-life for reachable routes.";
                   }
                   leaf reuse {
                     type "uint16" {
                       range "1..20000";
                     }
                     default "750";
                     description
                       "Configure a threshold for a route to be unsuppressed. If"+
                       " the penalty value of the route falls below the "+
                       "threshold, the route is reused.";
                   }
                   leaf suppress {
                     type "uint16" {
                       range "1..20000";
                     }
                     default "2000";
                     description
                       "Configure a threshold for a route to be suppressed. When"+
                       " the penalty value of the route exceeds the suppression "+
                       "threshold, the route is suppressed. The configured "+
                       "suppression threshold must be greater than the reuse "+
                       "threshold.";
                   }
                   leaf ceiling {
                     type "uint16" {
                       range "1001..20000";
                     }
                     default "16000";
                     description
                       "Configure the penalty ceiling. The configured threshold "+
                       "must be greater than the suppression threshold.";
                   }
                   leaf update-standard {
                     type "boolean";
                     default "false";
                     description
                       "Enable/disable update standard.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container nexthop-recursive-lookup {
                 description
                   "Configure next hop iteration.";
                 container common {
                   description
                     "Configure next hop iteration common options.";
                   leaf restrain {
                     type "boolean";
                     default "true";
                     description
                       "Enable/disable the function to restrain next hop "+
                       "iteration in case of next hop flapping.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                   leaf default-route {
                     type "boolean";
                     default "false";
                     description
                       "Enable/disable default route.";
                   }
                 }
                 container delay {
                   description
                     "Configure time of next hop change responding delay.";
                   leaf time {
                     type "uint8" {
                       range "1..100";
                     }
                     units "s";
                     description
                       "Specify the delay in responding to the next hop change.";
                   }
                   leaf no-critical-event-time {
                     type "uint8" {
                       range "0..100";
                     }
                     units "s";
                     default "10";
                     description
                       "Specify the delay in responding to the next hop change "+
                       "on non critical relay change event.";
                   }
                 }
                 container bit-error-detection {
                   description
                     "Configure BGP bit-error detection parameters.";
                   leaf enable {
                     type "boolean";
                     must "(../enable='false') or (../enable='true' and (../med "+
                          "or ../local-preference))";
                     default "false";
                     description
                       "Enable/disable association between bit error events and "+
                       "the adjustment of route attributes.";
                   }
                   leaf med {
                     when "../enable='true'";
                     type "uint32" {
                       range "1..4294967295";
                     }
                     description
                       "Specify the MED adjustment for BGP routes used when a "+
                       "bit error event occurs.";
                   }
                   leaf local-preference {
                     when "../enable='true'";
                     type "uint32" {
                       range "1..4294967295";
                     }
                     description
                       "Specify the local preference adjustment for BGP routes "+
                       "used when a bit error event occurs.";
                   }
                   choice policy-type {
                     when "enable='true'";
                     description
                       "Set route-policy or route-filter for bit-error-triggered"+
                       " protection switching.";
                     case rtp-ref {
                       description
                         "Route policy.";
                       leaf route-policy {
                         type "leafref" {
                           path "/rtp:routing-policy/rtp:policy-definitions/rtp:"+
                                "policy-definition/rtp:name";
                         }
                         description
                           "Specify the name of route-policy for bit-error-trigg"+
                           "ered protection switching. The MED or local "+
                           "preference of only the routes that match the "+
                           "route-policy is adjusted.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container import-filter-policy {
                 description
                   "Configure a filtering policy. It is used to filter the "+
                   "routes received from a peer. By default, routes are not "+
                   "filtered.";
                 choice ipv4-import-filter-protocol-policy-type {
                   description
                     "Set IPv4 filter protocol policy.";
                   case acl-ref {
                     description
                       "ACL Route Policy.";
                     leaf acl-name-or-num {
                       type "leafref" {
                         path "/acl:acl/acl:groups/acl:group/acl:identity";
                       }
                       description
                         "Specify the name or number of an ACL Rule. The number "+
                         "value ranges from 2000 to 2999 and is used by basic "+
                         "ACL rules. The name must start with a letter, and the "+
                         "name is case-sensitive.";
                     }
                   }
                   case ip-prefix-ref {
                     description
                       "IP prefix Policy.";
                     leaf ipv4-prefix-filter {
                       type "leafref" {
                         path "/rtp:routing-policy/rtp:ipv4-prefix-filters/rtp:i"+
                              "pv4-prefix-filter/rtp:name";
                       }
                       description
                         "Specify the IPv4 prefix list name.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container export-filter-policy {
                 description
                   "Configure a filtering policy. It is used to filter the "+
                   "routes received from a peer. By default, routes are not "+
                   "filtered.";
                 choice ipv4-import-filter-protocol-policy-type {
                   description
                     "Set IPv4 filter protocol policy.";
                   case acl-ref {
                     description
                       "ACL Route Policy.";
                     leaf acl-name-or-num {
                       type "leafref" {
                         path "/acl:acl/acl:groups/acl:group/acl:identity";
                       }
                       description
                         "Specify the name or number of an ACL Rule. The number "+
                         "value ranges from 2000 to 2999 and is used by basic "+
                         "ACL rules. The name must start with a letter, and the "+
                         "name is case-sensitive.";
                     }
                   }
                   case ip-prefix-ref {
                     description
                       "IP prefix Policy.";
                     leaf ipv4-prefix-filter {
                       type "leafref" {
                         path "/rtp:routing-policy/rtp:ipv4-prefix-filters/rtp:i"+
                              "pv4-prefix-filter/rtp:name";
                       }
                       description
                         "Specify the IPv4 prefix list name.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container slow-peer {
                 description
                   "Configure peer advertising routes slowly.";
                 leaf detection {
                   type "boolean";
                   default "true";
                   description
                     "Enable/disable detect slow peers.";
                 }
                 leaf detection-threshold {
                   type "uint16" {
                     range "120..3600";
                   }
                   units "s";
                   default "300";
                   description
                     "Specify the time in seconds lagging behind average when a "+
                     "peer is determined to be a slow peer.";
                 }
                 leaf absolute-detection {
                   type "boolean";
                   default "true";
                   description
                     "Enable/disable absolute-detect slow peers.";
                 }
                 leaf absolute-detection-threshold {
                   type "uint16" {
                     range "3..3600";
                   }
                   units "s";
                   default "9";
                   description
                     "Specify the packet send delay time in second when a peer "+
                     "is determined to be a slow peer.";
                 }
               }
             }
             container ipv6-vpn {
               when "../type = 'ipv6vpn'";
               description
                 "Configure IPv6 VPNv6 options.";
               leaf policy-vpntarget {
                 type "boolean";
                 default "true";
                 description
                   "Enable/disable VPN target-based filtering for the received "+
                   "VPN routes. Only the VPN route whose Export RT attribute "+
                   "matches the local Import RT attribute can be added to the "+
                   "routing table. This option can be used in the inter-AS VPN "+
                   "Option B solution and the ASBR MP-EBGP inter-AS L2VPN "+
                   "solution in Kompella mode.";
               }
               choice reflector-type {
                 description
                   "Set IPv4 address or id.";
                 case address {
                   description
                     "IPv4 address.";
                   leaf reflector-cluster-ipv4 {
                     type "inet:ipv4-address-no-zone";
                     description
                       "Set a cluster ID. The value is expressed in the format "+
                       "of an IPv4 address. Configuring multiple RRs in a "+
                       "cluster can enhance the stability of the network. If a "+
                       "cluster has more than one RR, select this option to set "+
                       "the same cluster ID for all the RRs to avoid routing "+
                       "loops. To allow clients to receive routes from RRs, "+
                       "ensure that the cluster ID of the RRs is different from "+
                       "the router ID of any client. If the cluster ID of the "+
                       "RRs is the same as the router ID of a client, the client"+
                       " will discard received routes.";
                   }
                 }
                 case id {
                   description
                     "Set value.";
                   leaf reflector-cluster-id {
                     type "uint32" {
                       range "1..4294967295";
                     }
                     description
                       "Set a cluster ID. Configuring multiple RRs in a cluster "+
                       "can enhance the stability of the network. If a cluster "+
                       "has more than one RR, select this option to set the same"+
                       " cluster ID for all the RRs to avoid routing loops. To "+
                       "allow clients to receive routes from RRs, ensure that "+
                       "the cluster ID of the RRs is different from the router "+
                       "ID of any client. If the cluster ID of the RRs is the "+
                       "same as the router ID of a client, the client will "+
                       "discard received routes.";
                   }
                 }
               }
               leaf reflect-change-path {
                 type "boolean";
                 default "false";
                 description
                   "Enable/disable an RR to use an export policy to change route"+
                   " AS_Path.";
               }
               leaf auto-frr {
                 type "boolean";
                 default "false";
                 description
                   "Enable/disable BGP Auto FRR. If IP FRR, VPN FRR, and Auto "+
                   "FRR are all enabled, IP FRR and VPN FRR take precedence over"+
                   " Auto FRR. If a route fails to match the routing policy of "+
                   "IP FRR or VPN FRR, Auto FRR takes effect.";
               }
               leaf tunnel-selector-name {
                 type "leafref" {
                   path "/rtp:routing-policy/rtp:tunnel-selectors/rtp:tunnel-sel"+
                        "ector/rtp:name";
                 }
                 description
                   "Configure a tunnel selector and apply it to the BGP IPv4 "+
                   "unicast, BGP VPNv4 address families and BGP VPNv6 address "+
                   "families so that IPv4,VPNv4 and VPNv6 labeled routes can be "+
                   "iterated to tunnels based on the tunnel selector. By "+
                   "default, no tunnel selector is configured.";
               }
               leaf route-select-delay {
                 type "uint16" {
                   range "0..3600";
                 }
                 units "s";
                 default "0";
                 description
                   "Route selection delay.";
               }
               leaf apply-label-mode {
                 type "apply-label-type";
                 default "per-route";
                 description
                   "Method of distributing labels to VPNV4 and VPNV6 routes. The"+
                   " way which assigns the label depends on the paf value. If "+
                   "there are a large number of routes, assign a label for the "+
                   "routes that have same nexthop and out-label. This allows all"+
                   " routes which have same nexthop and out-label to use one "+
                   "label.";
               }
               leaf nexthop-select-depend-type {
                 type "select-depend-type-ext";
                 default "depend-ip";
                 description
                   "In none mode, route selection does not depend on whether the"+
                   " next hop is reachable. In tunnel mode, the labeled BGP IPv4"+
                   " route can participate in route selection only after its "+
                   "next hop is iterated to an LSP. In IP \nmode, the labeled "+
                   "BGP IPv4 route can participate in route selection only after"+
                   " its next hop is iterated to an IP address. By default, the "+
                   "labeled BGP IPv4 route can participate in route selection "+
                   "\nif its next hop can be iterated to an IP address, "+
                   "regardless of whether the LSP of the next hop exists. This "+
                   "allows the RR that is not enabled with MPLS to forward "+
                   "labeled routes. In non-RR \nnetworking or RR networking "+
                   "where the BGP next hop is changed, BGP needs to check "+
                   "whether there is an LSP destined for the next hop. If such "+
                   "an LSP is not found, BGP needs to establish an LSP in "+
                   "\nadvance. If the default setting is adopted, a labeled BGP "+
                   "IPv4 unicast route may be selected prior to LSP establishmen"+
                   "t. As a result, services are incorrectly switched before LSP"+
                   " establishment and \nservice stability is affected. "+
                   "Therefore, allow route selection only after the labeled BGP "+
                   "IPv4 route is iterated to an LSP.";
               }
               leaf default-med {
                 type "uint32";
                 default "0";
                 description
                   "Specify the Multi-Exit-Discriminator (MED) of BGP routes. "+
                   "The value is an integer. This value is valid only for the "+
                   "imported routes and BGP summarized routes on the local "+
                   "router.";
               }
               leaf best-external {
                 when "../../../../../../ni:name='_public_'";
                 type "boolean";
                 default "false";
                 description
                   "Enable/disable best external route selection.";
               }
               leaf add-path-select-num {
                 when "../../../../../../ni:name='_public_'";
                 type "uint8" {
                   range "2..64";
                 }
                 description
                   "Number of add-path routes.";
               }
               leaf default-local-preference {
                 type "uint32" {
                   range "0..4294967295";
                 }
                 default "100";
                 description
                   "The local preference of BGP routes.";
               }
               leaf bestroute-med-plus-igp {
                 type "boolean";
                 must "not(../bestroute-igp-metric-ignore='true' and ../bestrout"+
                      "e-med-plus-igp='true')";
                 default "false";
                 description
                   "Enable/disable the function to add the IGP cost to the "+
                   "next-hop destination to the MED before comparing MED values "+
                   "for path selection.";
               }
               leaf bestroute-med-multiplier {
                 when "../bestroute-med-plus-igp='true'";
                 type "uint16" {
                   range "1..1000";
                 }
                 default "1";
                 description
                   "Value of med product factor.";
               }
               leaf bestroute-igp-multiplier {
                 when "../bestroute-med-plus-igp='true'";
                 type "uint16" {
                   range "1..1000";
                 }
                 default "1";
                 description
                   "Value of IGP cost product factor.";
               }
               leaf bestroute-igp-metric-ignore {
                 type "boolean";
                 default "false";
                 description
                   "Enable/disable BGP to ignore the IGP cost of each BGP route "+
                   "to the next hop in route selection. By default, a BGP route "+
                   "with a smaller IGP cost to the next hop is preferred.";
                 must "not(../bestroute-igp-metric-ignore='true' and ../bestrout"+
                      "e-med-plus-igp='true')";
               }
               leaf bestroute-router-id-prior-clusterlist {
                 type "boolean";
                 default "false";
                 description
                   "Enable/disable BGP to compare originator before clusterlist "+
                   "in route selection.";
               }
               leaf reflect-between-client {
                 type "boolean";
                 default "true";
                 description
                   "Enable/disable route reflection between clients. If clients "+
                   "of a route reflector (RR) are fully meshed, you can disable "+
                   "route reflection among clients to reduce the cost.";
               }
               leaf label-free-delay {
                 type "uint8" {
                   range "0..180";
                 }
                 units "s";
                 default "0";
                 description
                   "Label free delay.";
               }
               leaf route-reflector-ext-community-filter {
                 type "leafref" {
                   path "/rtp:routing-policy/rtp:ext-community-filters/rtp:ext-c"+
                        "ommunity-filter/rtp:name";
                 }
                 description
                   "Set the name of the extended community filter supported by "+
                   "an RR group. For the purpose of load balancing, only the "+
                   "IBGP route whose route-target extended community attribute "+
                   "meets the matching rules can be reflected.";
               }
               leaf load-balancing-eibgp-enable {
                 type "boolean";
                 default "false";
                 description
                   "Enable/disable EIBGP route load balancing.";
               }
               leaf load-balanc-igp-metric-ignore {
                 type "boolean";
                 default "false";
                 description
                   "Enable/disable BGP to ignore the IGP cost of each BGP route "+
                   "to the next hop when selecting routes for load balancing. By"+
                   " default, only the routes with the same IGP cost can "+
                   "participate in load balancing.";
               }
               leaf load-balanc-as-path-ignore {
                 type "boolean";
                 must "../load-balanc-as-path-ignore ='false' or ../load-balanc-"+
                      "as-path-relax ='false'";
                 default "false";
                 description
                   "Enable/disable BGP to ignore the AS_Path of each BGP route "+
                   "to the next hop when selecting routes for load balancing. By"+
                   " default, only the routes with the same AS_Path can "+
                   "participate in load balancing.";
               }
               leaf load-balanc-as-path-relax {
                 type "boolean";
                 must "../load-balanc-as-path-relax ='false' or ../load-balanc-a"+
                      "s-path-ignore ='false'";
                 default "false";
                 description
                   "Enable/disable BGP to ignore comparison of AS_Path "+
                   "attributes with the same length. By default, only the routes"+
                   " with the same AS_Path can participate in load balancing.";
               }
               container nexthop-recursive-lookup {
                 description
                   "Configure next hop iteration.";
                 container common {
                   description
                     "Configure next hop iteration common options.";
                   leaf restrain {
                     type "boolean";
                     default "true";
                     description
                       "Enable/disable the function to restrain next hop "+
                       "iteration in case of next hop flapping.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                   leaf default-route {
                     type "boolean";
                     default "false";
                     description
                       "Enable/disable default route.";
                   }
                 }
                 container delay {
                   description
                     "Configure time of next hop change responding delay.";
                   leaf time {
                     type "uint8" {
                       range "1..100";
                     }
                     units "s";
                     description
                       "Specify the delay in responding to the next hop change.";
                   }
                   leaf no-critical-event-time {
                     type "uint8" {
                       range "0..100";
                     }
                     units "s";
                     default "10";
                     description
                       "Specify the delay in responding to the next hop change "+
                       "on non critical relay change event.";
                   }
                 }
                 container bit-error-detection {
                   description
                     "Configure BGP bit-error detection parameters.";
                   leaf enable {
                     type "boolean";
                     must "(../enable='false') or (../enable='true' and (../med "+
                          "or ../local-preference))";
                     default "false";
                     description
                       "Enable/disable association between bit error events and "+
                       "the adjustment of route attributes.";
                   }
                   leaf med {
                     when "../enable='true'";
                     type "uint32" {
                       range "1..4294967295";
                     }
                     description
                       "Specify the MED adjustment for BGP routes used when a "+
                       "bit error event occurs.";
                   }
                   leaf local-preference {
                     when "../enable='true'";
                     type "uint32" {
                       range "1..4294967295";
                     }
                     description
                       "Specify the local preference adjustment for BGP routes "+
                       "used when a bit error event occurs.";
                   }
                   choice policy-type {
                     when "enable='true'";
                     description
                       "Set route-policy or route-filter for bit-error-triggered"+
                       " protection switching.";
                     case rtp-ref {
                       description
                         "Route policy.";
                       leaf route-policy {
                         type "leafref" {
                           path "/rtp:routing-policy/rtp:policy-definitions/rtp:"+
                                "policy-definition/rtp:name";
                         }
                         description
                           "Specify the name of route-policy for bit-error-trigg"+
                           "ered protection switching. The MED or local "+
                           "preference of only the routes that match the "+
                           "route-policy is adjusted.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container import-filter-policy {
                 description
                   "Configure a filtering policy. It is used to filter the "+
                   "routes received from a peer. By default, routes are not "+
                   "filtered.";
                 choice ipv6-import-filter-protocol-policy-type {
                   description
                     "Set IPv6 filter protocol policy.";
                   case acl6-ref {
                     description
                       "ACL route policy.";
                     leaf acl6-name-or-num {
                       type "leafref" {
                         path "/acl:acl/acl:group6s/acl:group6/acl:identity";
                       }
                       description
                         "Specify the name or number of an ACL6 Rule. The number"+
                         " value ranges from 2000 to 2999 and is used by basic "+
                         "ACL6 rules. The name must start with a letter, and the"+
                         " name is case-sensitive.";
                     }
                   }
                   case ipv6-prefix-ref {
                     description
                       "IPv6 prefix Policy.";
                     leaf ipv6-prefix-filter {
                       type "leafref" {
                         path "/rtp:routing-policy/rtp:ipv6-prefix-filters/rtp:i"+
                              "pv6-prefix-filter/rtp:name";
                       }
                       description
                         "Specify the IPv6 prefix list name.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container export-filter-policy {
                 description
                   "Configure a filtering policy. It is used to filter the "+
                   "routes received from a peer. By default, routes are not "+
                   "filtered.";
                 choice ipv6-import-filter-protocol-policy-type {
                   description
                     "Set IPv6 filter protocol policy.";
                   case acl6-ref {
                     description
                       "ACL route policy.";
                     leaf acl6-name-or-num {
                       type "leafref" {
                         path "/acl:acl/acl:group6s/acl:group6/acl:identity";
                       }
                       description
                         "Specify the name or number of an ACL6 Rule. The number"+
                         " value ranges from 2000 to 2999 and is used by basic "+
                         "ACL6 rules. The name must start with a letter, and the"+
                         " name is case-sensitive.";
                     }
                   }
                   case ipv6-prefix-ref {
                     description
                       "IPv6 prefix Policy.";
                     leaf ipv6-prefix-filter {
                       type "leafref" {
                         path "/rtp:routing-policy/rtp:ipv6-prefix-filters/rtp:i"+
                              "pv6-prefix-filter/rtp:name";
                       }
                       description
                         "Specify the IPv6 prefix list name.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container slow-peer {
                 description
                   "Configure peer advertising routes slowly.";
                 leaf detection {
                   type "boolean";
                   default "true";
                   description
                     "Enable/disable detect slow peers.";
                 }
                 leaf detection-threshold {
                   type "uint16" {
                     range "120..3600";
                   }
                   units "s";
                   default "300";
                   description
                     "Specify the time in seconds lagging behind average when a "+
                     "peer is determined to be a slow peer.";
                 }
                 leaf absolute-detection {
                   type "boolean";
                   default "true";
                   description
                     "Enable/disable absolute-detect slow peers.";
                 }
                 leaf absolute-detection-threshold {
                   type "uint16" {
                     range "3..3600";
                   }
                   units "s";
                   default "9";
                   description
                     "Specify the packet send delay time in second when a peer "+
                     "is determined to be a slow peer.";
                 }
               }
               container dampening-routes {
                 description
                   "List of route dampening.";
                 list dampening-route {
                   must "reuse < suppress and suppress < ceiling";
                   key "peer-type";
                   description
                     "Configure BGP route dampening or modify various BGP route "+
                     "dampening parameters. If a suppression policy for route "+
                     "dampening is configured, routes are preferentially matched"+
                     " against the suppression parameters defined in the "+
                     "suppression policy. If no parameter is configured, the "+
                     "default value of each parameter is used. The four route "+
                     "dampening parameters are mutually dependent. If you "+
                     "configure one of the parameters, the other parameters also"+
                     " need to be configured. When you configure BGP route "+
                     "dampening, the values of reuse threshold, suppress "+
                     "threshold, and penalty ceiling must meet the inequality of"+
                     " reuse threshold < suppress threshold < penalty ceiling. "+
                     "If Maximum suppression time obtained by using the formula "+
                     "of Maximum suppression time = Half life (of reachable "+
                     "routes) x 60 x (ln (Penalty ceiling/Reuse threshold)/ln(2)"+
                     ") is smaller than 1, suppression cannot be performed. "+
                     "Ensure that the value of the maximum suppression time is "+
                     "equal to or greater than 1. This means that the value of "+
                     "the penalty ceiling/reuse threshold must be great enough.";
                   leaf peer-type {
                     type "bgp:dampening-route-ext-peer-type";
                     description
                       "Configure the peer type.";
                   }
                   leaf half-life-time {
                     type "uint16" {
                       range "1..45";
                     }
                     units "min";
                     default "15";
                     description
                       "Configure a half-life for reachable routes.";
                   }
                   leaf reuse {
                     type "uint16" {
                       range "1..20000";
                     }
                     default "750";
                     description
                       "Configure a threshold for a route to be unsuppressed. If"+
                       " the penalty value of the route falls below the "+
                       "threshold, the route is reused.";
                   }
                   leaf suppress {
                     type "uint16" {
                       range "1..20000";
                     }
                     default "2000";
                     description
                       "Configure a threshold for a route to be suppressed. When"+
                       " the penalty value of the route exceeds the suppression "+
                       "threshold, the route is suppressed. The configured "+
                       "suppression threshold must be greater than the reuse "+
                       "threshold.";
                   }
                   leaf ceiling {
                     type "uint16" {
                       range "1001..20000";
                     }
                     default "16000";
                     description
                       "Configure the penalty ceiling. The configured threshold "+
                       "must be greater than the suppression threshold.";
                   }
                   leaf update-standard {
                     type "boolean";
                     default "false";
                     description
                       "Enable/disable update standard.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
             }
             container ipv4-labeluni {
               when "../type = 'ipv4labeluni'";
               must "../../../../../l3vpn:afs/l3vpn:af[l3vpn:type='ipv4-unicast'"+
                    "]";
               description
                 "Configure IPv4 label unicast options.";
               container common {
                 description
                   "Configure IPv4 label unicast common options.";
                 leaf auto-frr {
                   type "boolean";
                   default "false";
                   description
                     "Enable/disable BGP Auto FRR. If IP FRR, VPN FRR, and Auto "+
                     "FRR are all enabled, IP FRR and VPN FRR take precedence "+
                     "over Auto FRR. If a route fails to match the routing "+
                     "policy of IP FRR or VPN FRR, Auto FRR takes effect.";
                 }
                 leaf tunnel-selector-name {
                   when "../../../../../../../ni:name='_public_'";
                   type "leafref" {
                     path "/rtp:routing-policy/rtp:tunnel-selectors/rtp:tunnel-s"+
                          "elector/rtp:name";
                   }
                   description
                     "Configure a tunnel selector and apply it to the BGP IPv4 "+
                     "unicast, BGP VPNv4 address families and BGP VPNv6 address "+
                     "families so that IPv4,VPNv4 and VPNv6 labeled routes can "+
                     "be iterated to tunnels based on the tunnel selector. By "+
                     "default, no tunnel selector is configured.";
                 }
                 leaf tunnel-selector-all {
                   when "../tunnel-selector-name";
                   type "boolean";
                   default "false";
                   description
                     "Enable/disable tunnel selector for labeled, imported, and "+
                     "network segment routes.";
                 }
                 leaf nexthop-select-depend-type {
                   when "../../../../../../../ni:name='_public_'";
                   type "select-depend-type";
                   default "depend-tunnel";
                   description
                     "Specify the route iteration mode: IP or tunnel. In tunnel "+
                     "mode, the labeled BGP IPv4 route can participate in route "+
                     "selection only after its next hop is iterated to an LSP. "+
                     "In IP \nmode, the labeled BGP IPv4 route can participate "+
                     "in route selection only after its next hop is iterated to "+
                     "an IP address. By default, the labeled BGP IPv4 route can "+
                     "participate in route selection \nif its next hop can be "+
                     "iterated to an IP address, regardless of whether the LSP "+
                     "of the next hop exists. This allows the RR that is not "+
                     "enabled with MPLS to forward labeled routes. In non-RR "+
                     "\nnetworking or RR networking where the BGP next hop is "+
                     "changed, BGP needs to check whether there is an LSP "+
                     "destined for the next hop. If such an LSP is not found, "+
                     "BGP needs to establish an LSP in \nadvance. If the default"+
                     " setting is adopted, a labeled BGP IPv4 unicast route may "+
                     "be selected prior to LSP establishment. As a result, "+
                     "services are incorrectly switched before LSP establishment"+
                     " and \nservice stability is affected. Therefore, allow "+
                     "route selection only after the labeled BGP IPv4 route is "+
                     "iterated to an LSP.";
                 }
                 leaf nexthop-inherit-ip-cost {
                   when "../nexthop-select-depend-type='depend-tunnel'";
                   type "boolean";
                   default "false";
                   description
                     "Enable/disable next hop iteration mode to IP. Specify the "+
                     "route iteration mode: IP or tunnel. In tunnel mode, the "+
                     "labeled BGP IPv4 route can participate in route selection "+
                     "only after its next hop is iterated to an LSP.";
                 }
                 leaf always-compare-med {
                   type "boolean";
                   default "false";
                   description
                     "Enable/disable BGP to compare the MEDs of routes from "+
                     "peers in different ASs in route selection. If \nthere are "+
                     "multiple reachable routes to the same destination, the "+
                     "route with the smallest MED is preferred. Do not use this "+
                     "option unless different ASs use the same IGP and route "+
                     "selection mode.";
                 }
                 leaf default-med {
                   type "uint32";
                   default "0";
                   description
                     "Specify the Multi-Exit-Discriminator (MED) of BGP routes. "+
                     "The value is an integer. This value is valid only for the "+
                     "imported routes and BGP summarized routes on the local "+
                     "router.";
                 }
                 leaf best-route-bit-error-detection {
                   when "../../../../../../../ni:name!='_public_'";
                   type "boolean";
                   default "false";
                   description
                     "Enable/disable the function to reroute traffic when a bit "+
                     "error event occurs.";
                 }
                 leaf supernet-label-advertise {
                   type "boolean";
                   default "true";
                   description
                     "Enable/disable the function to advertise supernet labeled "+
                     "routes.";
                 }
                 leaf lsp-mtu {
                   type "uint16" {
                     range "46..65535";
                   }
                   default "1500";
                   description
                     "BGP LSP MTU.";
                 }
                 leaf label-free-delay {
                   type "uint8" {
                     range "0..180";
                   }
                   units "s";
                   default "0";
                   description
                     "Label free delay.";
                 }
                 leaf bestroute-med-confederation {
                   when "../../../../../../../ni:name='_public_'";
                   type "boolean";
                   default "false";
                   description
                     "Enable/disable BGP to compare Med value only within the "+
                     "federation.";
                 }
                 leaf bestroute-as-path-ignore {
                   type "boolean";
                   must "../bestroute-as-path-ignore = 'false' or ../load-balanc"+
                        "-as-path-ignore ='false' or not(../load-balanc-as-path-"+
                        "ignore)";
                   default "false";
                   description
                     "Enable/disable BGP to ignore the AS_Path attribute when "+
                     "selecting the optimal route. By default, BGP uses the "+
                     "AS_Path attribute as one of route selection rules, and a "+
                     "route with a shorter AS_Path is preferred. After "+
                     "bestroute-as-path-ignore is selected, BGP does not compare"+
                     " the AS_Path length.";
                 }
                 leaf determin-med {
                   type "boolean";
                   must "../determin-med ='false' or (not(../add-path-select-num"+
                        ") and (../best-external ='false' or not(../best-externa"+
                        "l)))";
                   default "false";
                   description
                     "Enable/disable deterministic MED so that the route "+
                     "selection result is relevant to the sequence in which "+
                     "routes are received.";
                 }
                 leaf best-external {
                   when "../../../../../../../ni:name='_public_'";
                   type "boolean";
                   must "../best-external ='false' or ../determin-med ='false'";
                   default "false";
                   description
                     "Enable/disable best external route selection.";
                 }
                 leaf add-path-select-num {
                   when "../../../../../../../ni:name='_public_'";
                   type "uint8" {
                     range "2..64";
                   }
                   must "../determin-med ='false'";
                   description
                     "Number of add-path routes.";
                 }
                 leaf load-balanc-igp-metric-ignore {
                   when "../../../../../../../ni:name='_public_'";
                   type "boolean";
                   default "false";
                   description
                     "Enable/disable BGP to ignore the IGP cost of each BGP "+
                     "route to the next hop when selecting routes for load "+
                     "balancing. By default, only the routes with the same IGP "+
                     "cost can participate in load balancing.";
                 }
                 leaf load-balanc-as-path-ignore {
                   when "../../../../../../../ni:name='_public_'";
                   type "boolean";
                   must "../load-balanc-as-path-ignore ='false' or (../load-bala"+
                        "nc-as-path-relax ='false' and ../bestroute-as-path-igno"+
                        "re ='false')";
                   default "false";
                   description
                     "Enable/disable BGP to ignore the AS_Path of each BGP route"+
                     " to the next hop when selecting routes for load balancing."+
                     " By default, only the routes with the same AS_Path can "+
                     "participate in load balancing.";
                 }
                 leaf load-balanc-as-path-relax {
                   when "../../../../../../../ni:name='_public_'";
                   type "boolean";
                   must "../load-balanc-as-path-relax ='false' or ../load-balanc"+
                        "-as-path-ignore ='false'";
                   default "false";
                   description
                     "Enable/disable BGP to ignore comparison of AS_Path "+
                     "attributes with the same length. By default, only the "+
                     "routes with the same AS_Path can participate in load "+
                     "balancing.";
                 }
                 leaf default-local-preference {
                   type "uint32" {
                     range "0..4294967295";
                   }
                   default "100";
                   description
                     "The local preference of BGP routes.";
                 }
                 leaf default-route-import {
                   type "boolean";
                   default "false";
                   description
                     "Enable/disable the function to import default routes into "+
                     "the BGP routing table. Default-route-imported must be used"+
                     " with import-routes so that default routes can be imported"+
                     " to the BGP routing table. If only import-routes is used, "+
                     "no default routes can be added to the BGP routing table. "+
                     "In addition, default-route-imported can only import the "+
                     "default routes in the routing table into the BGP routing "+
                     "table.";
                 }
                 leaf routerid-neglect {
                   type "boolean";
                   default "false";
                   description
                     "Enable/disable BGP to ignore router IDs when selecting the"+
                     " optimal route. Comparing router IDs is the last resort in"+
                     " route selection. This means that if one optimal route "+
                     "must be selected and no other parameters can be used to "+
                     "break the tie, router IDs can be used. If this option is "+
                     "selected, the first received route will be selected as the"+
                     " optimal route, and BGP will ignore the router ID and peer"+
                     " address in route selection.";
                 }
                 leaf route-select-delay {
                   type "uint16" {
                     range "0..3600";
                   }
                   units "s";
                   default "0";
                   description
                     "Route selection delay.";
                 }
                 leaf import-rib-nexthop-invariable {
                   when "../../../../../../../ni:name!='_public_'";
                   type "boolean";
                   default "false";
                   description
                     "Enable/disable the command to enable advertise the route "+
                     "without modifying the next-hop.";
                 }
                 leaf reflect-change-path {
                   type "boolean";
                   default "false";
                   description
                     "Enable/disable an RR to use an export policy to change "+
                     "route AS_Path.";
                 }
                 choice reflector-type {
                   description
                     "Set IPv4 address or id.";
                   case address {
                     description
                       "IPv4 address.";
                     leaf reflector-cluster-ipv4 {
                       type "inet:ipv4-address-no-zone";
                       description
                         "Set a cluster ID. The value is expressed in the format"+
                         " of an IPv4 address. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                   case id {
                     description
                       "Set value.";
                     leaf reflector-cluster-id {
                       type "uint32" {
                         range "1..4294967295";
                       }
                       description
                         "Set a cluster ID. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                 }
                 leaf reflect-between-client {
                   type "boolean";
                   default "true";
                   description
                     "Enable/disable route reflection between clients. If "+
                     "clients of a route reflector (RR) are fully meshed, you "+
                     "can disable route reflection among clients to reduce the "+
                     "cost.";
                 }
                 leaf bestroute-med-plus-igp {
                   type "boolean";
                   must "not(../bestroute-igp-metric-ignore='true' and "+
                        "../bestroute-med-plus-igp='true')";
                   default "false";
                   description
                     "Enable/disable the function to add the IGP cost to the "+
                     "next-hop destination to the MED before comparing MED "+
                     "values for path selection.";
                 }
                 leaf bestroute-med-multiplier {
                   when "../bestroute-med-plus-igp='true'";
                   type "uint16" {
                     range "1..1000";
                   }
                   default "1";
                   description
                     "Value of med product factor.";
                 }
                 leaf bestroute-igp-multiplier {
                   when "../bestroute-med-plus-igp='true'";
                   type "uint16" {
                     range "1..1000";
                   }
                   default "1";
                   description
                     "Value of IGP cost product factor.";
                 }
                 leaf bestroute-igp-metric-ignore {
                   type "boolean";
                   default "false";
                   description
                     "Enable/disable BGP to ignore the IGP cost of each BGP "+
                     "route to the next hop in route selection. By default, a "+
                     "BGP route with a smaller IGP cost to the next hop is "+
                     "preferred.";
                   must "not(../bestroute-igp-metric-ignore='true' and "+
                        "../bestroute-med-plus-igp='true')";
                 }
                 leaf bestroute-router-id-prior-clusterlist {
                   type "boolean";
                   default "false";
                   description
                     "Enable/disable BGP to compare originator before clusterlis"+
                     "t in route selection.";
                 }
                 leaf bestroute-med-none-as-maximum {
                   type "boolean";
                   default "false";
                   description
                     "Enable/disable BGP considers its MED as the largest MED "+
                     "value (4294967295). If a route does not carry MED, BGP "+
                     "considers its MED as the default value (0) during route "+
                     "selection.";
                 }
                 leaf ext-community-change {
                   type "boolean";
                   default "false";
                   description
                     "Enable/disable the function to change the extended "+
                     "community attribute.";
                 }
               }
               container nexthop-recursive-lookup {
                 description
                   "Configure next hop iteration.";
                 container common {
                   description
                     "Configure next hop iteration common options.";
                   leaf restrain {
                     type "boolean";
                     default "true";
                     description
                       "Enable/disable the function to restrain next hop "+
                       "iteration in case of next hop flapping.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container import-routes {
                 description
                   "List of imported routes.";
                 list import-route {
                   key "protocol process-id";
                   description
                     "Apply route import policy. Routes of other protocol types "+
                     "can be imported by BGP. By default, BGP does not import "+
                     "routes of other protocol types.";
                   leaf protocol {
                     type "bgp:ipv4-import-route-protocol-type";
                     description
                       "Routing protocol from which routes can be imported.";
                   }
                   leaf process-id {
                     type "uint32" {
                       range "0..4294967295";
                     }
                     must "((../protocol='ospf' or ../protocol='isis' or "+
                          "../protocol='rip') and ../process-id!=0) or "+
                          "(../protocol!='ospf' and ../protocol!='isis' and "+
                          "../protocol!='rip' and ../process-id=0)";
                     description
                       "Process ID of an imported routing protocol. The process "+
                       "ID is 0, if the imported routing protocol is direct "+
                       "routes, static routes, UNRs, or OP-routes. The process "+
                       "ID must be specified range from 1 to 4294967295, if the "+
                       "imported routing protocol is RIP, OSPF, ISIS.";
                   }
                   leaf med {
                     type "uint32";
                     description
                       "Specifies the MED metric of the imported route.";
                   }
                   choice policy-type {
                     description
                       "Set route policy or filter.";
                     case rtp-ref {
                       description
                         "Route policy.";
                       leaf policy-name {
                         type "leafref" {
                           path "/rtp:routing-policy/rtp:policy-definitions/rtp:"+
                                "policy-definition/rtp:name";
                         }
                         description
                           "When routes are imported from other routing "+
                           "protocols, the route-policy filter can be used to "+
                           "filter the routes and change route attributes.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                   leaf non-relay-tunnel {
                     when "../../../../../../../../ni:name='_public_'";
                     type "boolean";
                     default "false";
                     description
                       "Enable/disable imported route relay a tunnel.";
                   }
                 }
               }
               container network-routes {
                 description
                   "List of network routes.";
                 list network-route {
                   key "address mask-length";
                   description
                     "Configure a network route in the BGP routing table.";
                   leaf address {
                     type "inet:ipv4-address-no-zone";
                     description
                       "Specify the IP address advertised by BGP. An IPv4 "+
                       "address can be configured in the IPv4 address family. "+
                       "Note: During the configuration of a network route, the "+
                       "IP address is adjusted based on the mask. It is "+
                       "recommended that you click Synchronize All after "+
                       "creating a network route.";
                   }
                   leaf mask-length {
                     type "uint8" {
                       range "0..32";
                     }
                     description
                       "Specify the mask length of an IP address.";
                   }
                   choice policy-type {
                     description
                       "Specify the route-policy or filter for route advertiseme"+
                       "nt.";
                     case rtp-ref {
                       description
                         "Specify the route policy.";
                       leaf policy-name {
                         type "leafref" {
                           path "/rtp:routing-policy/rtp:policy-definitions/rtp:"+
                                "policy-definition/rtp:name";
                         }
                         description
                           "Specify the route policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                   leaf non-relay-tunnel {
                     when "../../../../../../../../ni:name='_public_'";
                     type "boolean";
                     default "false";
                     description
                       "Enable/disable imported route relay a tunnel.";
                   }
                   leaf label-index {
                     when "../../../../../../../../ni:name='_public_'";
                     type "uint32" {
                       range "0..4294967294";
                     }
                     description
                       "Management label value assigned for imported routes.";
                   }
                 }
               }
               container import-ribs {
                 description
                   "List of imported RIBs configuration.";
                 list import-rib {
                   key "source-vpn source-address-family";
                   description
                     "Configure imported RIBs.";
                   leaf source-vpn {
                     type "leafref" {
                       path "/ni:network-instance/ni:instances/ni:instance/ni:na"+
                            "me";
                     }
                     must "not(../../../../../../../../ni:name = current() and "+
                          "../source-address-family = 'ipv4labeluni')";
                     description
                       "Source VPN name.";
                   }
                   leaf source-address-family {
                     type "bgp:import-rib-ipv4-safi-type";
                     description
                       "Source address family type.";
                   }
                   leaf valid-route {
                     type "boolean";
                     default "false";
                     description
                       "Enable/disable imported valid route.";
                   }
                   leaf include-label-route {
                     when "../source-address-family='ipv4uni'";
                     type "boolean";
                     default "false";
                     description
                       "Enable/disable imported include label route.";
                   }
                   choice policy-type {
                     description
                       "Set policy or filter.";
                     case rtp-ref {
                       description
                         "Specify the route policy.";
                       leaf policy-name {
                         type "leafref" {
                           path "/rtp:routing-policy/rtp:policy-definitions/rtp:"+
                                "policy-definition/rtp:name";
                         }
                         description
                           "Specify the route policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container lsp-options {
                 description
                   "Configure BGP ingress-lsp.";
                 leaf ingress-protect-mode-bgp-frr {
                   type "boolean";
                   must "(../ingress-protect-mode-bgp-frr='false') or (../ingres"+
                        "s-protect-mode-bgp-frr='true' and ../maximum-load-balan"+
                        "cing-ingress=1)";
                   default "false";
                   description
                     "Enable/disable ingress LSP protection mode to FRR.";
                 }
                 leaf maximum-load-balancing-ingress {
                   type "uint16" {
                     range "1..16";
                   }
                   default "1";
                   description
                     "Maximum number of ingress LSPs for load balancing. The "+
                     "default value is 1, indicating that this attribute is not "+
                     "configured. Configuring the number of ingress LSPs for "+
                     "load balancing and configuring BGP FRR of ingress LSPs are"+
                     " mutually exclusive.";
                 }
                 leaf maximum-load-balancing-transit {
                   type "uint16" {
                     range "1..16";
                   }
                   default "1";
                   description
                     "Maximum number of transit LSPs for load balancing.";
                 }
                 leaf unicast-rt-label-advertise-popgo {
                   when "../../../../../../../ni:name='_public_'";
                   type "boolean";
                   default "false";
                   description
                     "Enable/disable a device to convert received IPv4 public "+
                     "network unicast routes to labeled routes by adding a BGP "+
                     "label to each route and advertise the labeled routes to "+
                     "peers with the labeled route exchange capability. If the "+
                     "IP address of an outbound interface is reachable but no "+
                     "LSP is reachable, traffic is forwarded through the "+
                     "outbound interface and a specific next hop, during which "+
                     "the label POPGO action is performed.";
                 }
                 leaf lsp-operation {
                   when "../../../../../../../ni:name='_public_'";
                   type "lsp-operation-type";
                   default "pop";
                   description
                     "Label operation type.";
                 }
                 choice ingress-trigger-policy {
                   description
                     "Specify the route-policy or filter for ingress LSPs.";
                   case trigger-route-policy-ref {
                     description
                       "Route policy.";
                     leaf trigger-route-policy {
                       type "leafref" {
                         path "/rtp:routing-policy/rtp:policy-definitions/rtp:po"+
                              "licy-definition/rtp:name";
                       }
                       description
                         "Specify the name of a routing policy.";
                     }
                   }
                   case trigger-xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container dampening-routes {
                 description
                   "List of route dampening.";
                 list dampening-route {
                   must "reuse < suppress and suppress < ceiling";
                   key "peer-type";
                   description
                     "Configure BGP route dampening or modify various BGP route "+
                     "dampening parameters. If a suppression policy for route "+
                     "dampening is configured, routes are preferentially matched"+
                     " against the suppression parameters defined in the "+
                     "suppression policy. If no parameter is configured, the "+
                     "default value of each parameter is used. The four route "+
                     "dampening parameters are mutually dependent. If you "+
                     "configure one of the parameters, the other parameters also"+
                     " need to be configured. When you configure BGP route "+
                     "dampening, the values of reuse threshold, suppress "+
                     "threshold, and penalty ceiling must meet the inequality of"+
                     " reuse threshold < suppress threshold < penalty ceiling. "+
                     "If Maximum suppression time obtained by using the formula "+
                     "of Maximum suppression time = Half life (of reachable "+
                     "routes) x 60 x (ln (Penalty ceiling/Reuse threshold)/ln(2)"+
                     ") is smaller than 1, suppression cannot be performed. "+
                     "Ensure that the value of the maximum suppression time is "+
                     "equal to or greater than 1. This means that the value of "+
                     "the penalty ceiling/reuse threshold must be great enough.";
                   leaf peer-type {
                     type "dampening-route-peer-type";
                     description
                       "Configure the peer type.";
                   }
                   leaf half-life-time {
                     type "uint16" {
                       range "1..45";
                     }
                     units "min";
                     default "15";
                     description
                       "Configure a half-life for reachable routes.";
                   }
                   leaf reuse {
                     type "uint16" {
                       range "1..20000";
                     }
                     default "750";
                     description
                       "Configure a threshold for a route to be unsuppressed. If"+
                       " the penalty value of the route falls below the "+
                       "threshold, the route is reused.";
                   }
                   leaf suppress {
                     type "uint16" {
                       range "1..20000";
                     }
                     default "2000";
                     description
                       "Configure a threshold for a route to be suppressed. When"+
                       " the penalty value of the route exceeds the suppression "+
                       "threshold, the route is suppressed. The configured "+
                       "suppression threshold must be greater than the reuse "+
                       "threshold.";
                   }
                   leaf ceiling {
                     type "uint16" {
                       range "1001..20000";
                     }
                     default "16000";
                     description
                       "Configure the penalty ceiling. The configured threshold "+
                       "must be greater than the suppression threshold.";
                   }
                   leaf update-standard {
                     type "boolean";
                     default "false";
                     description
                       "Enable/disable update standard.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container slow-peer {
                 description
                   "Configure peer advertising routes slowly.";
                 leaf detection {
                   type "boolean";
                   default "true";
                   description
                     "Enable/disable detect slow peers.";
                 }
                 leaf detection-threshold {
                   type "uint16" {
                     range "120..3600";
                   }
                   units "s";
                   default "300";
                   description
                     "Specify the time in seconds lagging behind average when a "+
                     "peer is determined to be a slow peer.";
                 }
                 leaf absolute-detection {
                   type "boolean";
                   default "true";
                   description
                     "Enable/disable absolute-detect slow peers.";
                 }
                 leaf absolute-detection-threshold {
                   type "uint16" {
                     range "3..3600";
                   }
                   units "s";
                   default "9";
                   description
                     "Specify the packet send delay time in second when a peer "+
                     "is determined to be a slow peer.";
                 }
               }
             }
             container ipv4-multicast {
               when "../type='ipv4multi'";
               description
                 "Configure IPv4 multicast options.";
               container common {
                 description
                   "Configure BGP IPv4-multicast address family options.";
                 leaf always-compare-med {
                   type "boolean";
                   default "false";
                   description
                     "Enable/disable BGP to compare the MEDs of routes from "+
                     "peers in different ASs in route selection. If \nthere are "+
                     "multiple reachable routes to the same destination, the "+
                     "route with the smallest MED is preferred. Do not use this "+
                     "option unless different ASs use the same IGP and route "+
                     "selection mode.";
                 }
                 leaf default-med {
                   type "uint32";
                   default "0";
                   description
                     "Specify the Multi-Exit-Discriminator (MED) of BGP routes. "+
                     "The value is an integer. This value is valid only for the "+
                     "imported routes and BGP summarized routes on the local "+
                     "router.";
                 }
                 leaf summary-automatic {
                   type "boolean";
                   default "false";
                   description
                     "Enable/disable automatic summarization for imported "+
                     "routes. Manual summarization takes precedence over "+
                     "automatic summarization. After automatic summarization is "+
                     "enabled, BGP summarizes routes based on the natural "+
                     "network segment (for example, 10.1.1.1/24 and 10.2.1.1/24 "+
                     "are summarized into 10.0.0.0/8, a Class A address), and "+
                     "sends only the summarized route to peers. This reduces the"+
                     " number of routes.";
                 }
                 leaf bestroute-med-confederation {
                   type "boolean";
                   default "false";
                   description
                     "Enable/disable BGP to compare Med value only within the "+
                     "federation.";
                 }
                 leaf default-local-preference {
                   type "uint32" {
                     range "0..4294967295";
                   }
                   default "100";
                   description
                     "The local preference of BGP routes.";
                 }
                 leaf default-route-import {
                   type "boolean";
                   default "false";
                   description
                     "Enable/disable the function to import default routes into "+
                     "the BGP routing table. Default-route-imported must be used"+
                     " with import-routes so that default routes can be imported"+
                     " to the BGP routing table. If only import-routes is used, "+
                     "no default routes can be added to the BGP routing table. "+
                     "In addition, default-route-imported can only import the "+
                     "default routes in the routing table into the BGP routing "+
                     "table.";
                 }
                 leaf routerid-neglect {
                   type "boolean";
                   default "false";
                   description
                     "Enable/disable BGP to ignore router IDs when selecting the"+
                     " optimal route. Comparing router IDs is the last resort in"+
                     " route selection. This means that if one optimal route "+
                     "must be selected and no other parameters can be used to "+
                     "break the tie, router IDs can be used. If this option is "+
                     "selected, the first received route will be selected as the"+
                     " optimal route, and BGP will ignore the router ID and peer"+
                     " address in route selection.";
                 }
                 leaf route-select-delay {
                   type "uint16" {
                     range "0..3600";
                   }
                   units "s";
                   default "0";
                   description
                     "Route selection delay.";
                 }
                 leaf reflect-change-path {
                   type "boolean";
                   default "false";
                   description
                     "Enable/disable an RR to use an export policy to change "+
                     "route AS_Path.";
                 }
                 choice reflector-type {
                   description
                     "Set IPv4 address or id.";
                   case address {
                     description
                       "IPv4 address.";
                     leaf reflector-cluster-ipv4 {
                       type "inet:ipv4-address-no-zone";
                       description
                         "Set a cluster ID. The value is expressed in the format"+
                         " of an IPv4 address. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                   case id {
                     description
                       "Set value.";
                     leaf reflector-cluster-id {
                       type "uint32" {
                         range "1..4294967295";
                       }
                       description
                         "Set a cluster ID. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                 }
                 leaf reflect-between-client {
                   type "boolean";
                   default "true";
                   description
                     "Enable/disable route reflection between clients. If "+
                     "clients of a route reflector (RR) are fully meshed, you "+
                     "can disable route reflection among clients to reduce the "+
                     "cost.";
                 }
                 leaf determin-med {
                   type "boolean";
                   default "false";
                   description
                     "Enable/disable deterministic MED so that the route "+
                     "selection result is relevant to the sequence in which "+
                     "routes are received.";
                 }
                 leaf bestroute-med-plus-igp {
                   type "boolean";
                   must "not(../bestroute-igp-metric-ignore='true' and "+
                        "../bestroute-med-plus-igp='true')";
                   default "false";
                   description
                     "Enable/disable the function to add the IGP cost to the "+
                     "next-hop destination to the MED before comparing MED "+
                     "values for path selection.";
                 }
                 leaf bestroute-med-multiplier {
                   when "../bestroute-med-plus-igp='true'";
                   type "uint16" {
                     range "1..1000";
                   }
                   default "1";
                   description
                     "Value of med product factor.";
                 }
                 leaf bestroute-igp-multiplier {
                   when "../bestroute-med-plus-igp='true'";
                   type "uint16" {
                     range "1..1000";
                   }
                   default "1";
                   description
                     "Value of IGP cost product factor.";
                 }
                 leaf bestroute-igp-metric-ignore {
                   type "boolean";
                   default "false";
                   description
                     "Enable/disable BGP to ignore the IGP cost of each BGP "+
                     "route to the next hop in route selection. By default, a "+
                     "BGP route with a smaller IGP cost to the next hop is "+
                     "preferred.";
                   must "not(../bestroute-igp-metric-ignore='true' and "+
                        "../bestroute-med-plus-igp='true')";
                 }
                 leaf bestroute-router-id-prior-clusterlist {
                   type "boolean";
                   default "false";
                   description
                     "Enable/disable BGP to compare originator before clusterlis"+
                     "t in route selection.";
                 }
                 leaf bestroute-as-path-ignore {
                   type "boolean";
                   default "false";
                   description
                     "Enable/disable BGP to ignore the AS_Path attribute when "+
                     "selecting the optimal route. By default, BGP uses the "+
                     "AS_Path attribute as one of route selection rules, and a "+
                     "route with a shorter AS_Path is preferred. After "+
                     "bestroute-as-path-ignore is selected, BGP does not compare"+
                     " the AS_Path length.";
                 }
                 leaf bestroute-med-none-as-maximum {
                   type "boolean";
                   default "false";
                   description
                     "Enable/disable BGP considers its MED as the largest MED "+
                     "value (4294967295). If a route does not carry MED, BGP "+
                     "considers its MED as the default value (0) during route "+
                     "selection.";
                 }
                 leaf maximum-load-balancing {
                   type "uint16" {
                     range "1..128";
                   }
                   must "not (../maximum-load-balancing-ibgp>1 or ../maximum-loa"+
                        "d-balancing-ebgp>1) or ../maximum-load-balancing=1";
                   default "1";
                   description
                     "Specify the maximum number of equal-cost routes in the BGP"+
                     " routing table. The value can be 1 or an integer greater "+
                     "than 1. The value depends on the associated license. By "+
                     "default, the maximum number of equal-cost routes is 1. "+
                     "Equal-cost BGP routes can be generated for load balancing "+
                     "only when the BGP routes meet the first nine rules of the "+
                     "route-selection policy and have the same AS-Path "+
                     "attribute. The value range and default value are "+
                     "controlled by the PAF.";
                 }
                 leaf maximum-load-balancing-ibgp {
                   type "uint16" {
                     range "1..128";
                   }
                   must "not (../maximum-load-balancing>1) or ../maximum-load-ba"+
                        "lancing-ibgp=1";
                   default "1";
                   description
                     "Specify the maximum number of equal-cost IBGP routes. The "+
                     "value range and default value are controlled by the PAF.";
                 }
                 leaf maximum-load-balancing-ebgp {
                   type "uint16" {
                     range "1..128";
                   }
                   must "not (../maximum-load-balancing>1) or ../maximum-load-ba"+
                        "lancing-ebgp=1";
                   default "1";
                   description
                     "Specify the maximum number of equal-cost EBGP routes. The "+
                     "value range and default value are controlled by the PAF.";
                 }
                 leaf ext-community-change {
                   type "boolean";
                   default "false";
                   description
                     "Enable/disable the function to change the extended "+
                     "community attribute.";
                 }
               }
               container nexthop-recursive-lookup {
                 description
                   "Configure next hop iteration.";
                 container common {
                   description
                     "Configure next hop iteration common options.";
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
                 container delay {
                   description
                     "Configure time of next hop change responding delay.";
                   leaf time {
                     type "uint8" {
                       range "1..100";
                     }
                     units "s";
                     description
                       "Specify the delay in responding to the next hop change.";
                   }
                   leaf no-critical-event-time {
                     type "uint8" {
                       range "0..100";
                     }
                     units "s";
                     default "10";
                     description
                       "Specify the delay in responding to the next hop change "+
                       "on non critical relay change event.";
                   }
                 }
               }
               container preference {
                 description
                   "Configure parameters relating to options for BGP routes "+
                   "preference.";
                 choice set-value-or-policy {
                   default "set-value";
                   description
                     "Set BGP routes preference by value or policy.";
                   case set-value {
                     description
                       "Set BGP routes preference by value.";
                     leaf external {
                       type "uint8" {
                         range "1..255";
                       }
                       default "255";
                       description
                         "Set the protocol priority of EBGP routes. The value is"+
                         " an integer. An EBGP route is the optimal route "+
                         "learned from a peer outside the local AS.";
                     }
                     leaf internal {
                       type "uint8" {
                         range "1..255";
                       }
                       default "255";
                       description
                         "Set the protocol priority of IBGP routes. The value is"+
                         " an integer. An IBGP route is a route learned from a "+
                         "peer inside the local AS.";
                     }
                     leaf local {
                       type "uint8" {
                         range "1..255";
                       }
                       default "255";
                       description
                         "Set the protocol priority of a local BGP route. A "+
                         "local route refers to an automatically or manually "+
                         "summarized route.";
                     }
                   }
                   case rtp-ref {
                     description
                       "Set BGP routes preference by route policy.";
                     leaf route-policy {
                       type "leafref" {
                         path "/rtp:routing-policy/rtp:policy-definitions/rtp:po"+
                              "licy-definition/rtp:name";
                       }
                       description
                         "Specify a routing policy to filter routes so that a "+
                         "configured priority is applied to the routes that "+
                         "match the specified policy.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container dampening-routes {
                 description
                   "List of route dampening.";
                 list dampening-route {
                   must "reuse < suppress and suppress < ceiling";
                   key "peer-type";
                   description
                     "Configure BGP route dampening or modify various BGP route "+
                     "dampening parameters. If a suppression policy for route "+
                     "dampening is configured, routes are preferentially matched"+
                     " against the suppression parameters defined in the "+
                     "suppression policy. If no parameter is configured, the "+
                     "default value of each parameter is used. The four route "+
                     "dampening parameters are mutually dependent. If you "+
                     "configure one of the parameters, the other parameters also"+
                     " need to be configured. When you configure BGP route "+
                     "dampening, the values of reuse threshold, suppress "+
                     "threshold, and penalty ceiling must meet the inequality of"+
                     " reuse threshold < suppress threshold < penalty ceiling. "+
                     "If Maximum suppression time obtained by using the formula "+
                     "of Maximum suppression time = Half life (of reachable "+
                     "routes) x 60 x (ln (Penalty ceiling/Reuse threshold)/ln(2)"+
                     ") is smaller than 1, suppression cannot be performed. "+
                     "Ensure that the value of the maximum suppression time is "+
                     "equal to or greater than 1. This means that the value of "+
                     "the penalty ceiling/reuse threshold must be great enough.";
                   leaf peer-type {
                     type "dampening-route-peer-type";
                     description
                       "Configure the peer type.";
                   }
                   leaf half-life-time {
                     type "uint16" {
                       range "1..45";
                     }
                     units "min";
                     default "15";
                     description
                       "Configure a half-life for reachable routes.";
                   }
                   leaf reuse {
                     type "uint16" {
                       range "1..20000";
                     }
                     default "750";
                     description
                       "Configure a threshold for a route to be unsuppressed. If"+
                       " the penalty value of the route falls below the "+
                       "threshold, the route is reused.";
                   }
                   leaf suppress {
                     type "uint16" {
                       range "1..20000";
                     }
                     default "2000";
                     description
                       "Configure a threshold for a route to be suppressed. When"+
                       " the penalty value of the route exceeds the suppression "+
                       "threshold, the route is suppressed. The configured "+
                       "suppression threshold must be greater than the reuse "+
                       "threshold.";
                   }
                   leaf ceiling {
                     type "uint16" {
                       range "1001..20000";
                     }
                     default "16000";
                     description
                       "Configure the penalty ceiling. The configured threshold "+
                       "must be greater than the suppression threshold.";
                   }
                   leaf update-standard {
                     type "boolean";
                     default "false";
                     description
                       "Enable/disable update standard.";
                   }
                   choice policy-type {
                     description
                       "Set route-policy or route-filter.";
                     case rtp-ref {
                       description
                         "Route policy.";
                       leaf route-policy {
                         type "leafref" {
                           path "/rtp:routing-policy/rtp:policy-definitions/rtp:"+
                                "policy-definition/rtp:name";
                         }
                         description
                           "Specify the name of a routing policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container network-routes {
                 description
                   "List of network routes.";
                 list network-route {
                   key "address mask-length";
                   description
                     "Configure a network route in the BGP routing table.";
                   leaf address {
                     type "inet:ipv4-address-no-zone";
                     description
                       "Specify the IP address advertised by BGP. An IPv4 "+
                       "address can be configured in the IPv4 address family. "+
                       "Note: During the configuration of a network route, the "+
                       "IP address is adjusted based on the mask. It is "+
                       "recommended that you click Synchronize All after "+
                       "creating a network route.";
                   }
                   leaf mask-length {
                     type "uint8" {
                       range "0..32";
                     }
                     description
                       "Specify the mask length of an IP address.";
                   }
                   choice policy-type {
                     description
                       "Specify the route-policy or filter for route advertiseme"+
                       "nt.";
                     case rtp-ref {
                       description
                         "Specify the route policy.";
                       leaf policy-name {
                         type "leafref" {
                           path "/rtp:routing-policy/rtp:policy-definitions/rtp:"+
                                "policy-definition/rtp:name";
                         }
                         description
                           "Specify the route policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container import-routes {
                 description
                   "List of imported routes.";
                 list import-route {
                   key "protocol process-id";
                   description
                     "Configure route import. Routes of other protocol types can"+
                     " be imported by BGP. By default, BGP does not import "+
                     "routes of other protocol types.";
                   leaf protocol {
                     type "bgp:ipv4multi-import-route-protocol-type";
                     description
                       "Routing protocol from which routes can be imported.";
                   }
                   leaf process-id {
                     type "uint32" {
                       range "0..4294967295";
                     }
                     must "((../protocol='ospf' or ../protocol='isis' or "+
                          "../protocol='rip') and ../process-id!=0) or "+
                          "(../protocol!='ospf' and ../protocol!='isis' and "+
                          "../protocol!='rip' and ../process-id=0)";
                     description
                       "Process ID of an imported routing protocol. The process "+
                       "ID is 0, if the imported routing protocol is direct "+
                       "routes, static routes, UNRs, or OP-routes. The process "+
                       "ID must be specified range from 1 to 4294967295, if the "+
                       "imported routing protocol is RIP, OSPF, ISIS.";
                   }
                   leaf med {
                     type "uint32";
                     description
                       "Specifies the MED metric of the imported route.";
                   }
                   choice policy-type {
                     description
                       "Set route policy or filter.";
                     case rtp-ref {
                       description
                         "Route policy.";
                       leaf policy-name {
                         type "leafref" {
                           path "/rtp:routing-policy/rtp:policy-definitions/rtp:"+
                                "policy-definition/rtp:name";
                         }
                         description
                           "When routes are imported from other routing "+
                           "protocols, the route-policy filter can be used to "+
                           "filter the routes and change route attributes.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container aggregate-routes {
                 description
                   "List of summarized routes.";
                 list aggregate-route {
                   key "address mask-length";
                   description
                     "Configure a summarized route in the BGP routing table. The"+
                     " local outbound interface of the summarized route is "+
                     "Null0. When another router receives the route, the route "+
                     "adds an outbound interface to the route. By default, route"+
                     " summarization is not performed. If the Origin attributes "+
                     "of the specific routes for the route summarization are "+
                     "different, the Origin attribute of the summarized route is"+
                     " that with the highest priority. Origin attributes are "+
                     "arranged in the priority order of complete > egp > igp. A "+
                     "summarized route carries the community attribute of each "+
                     "specific route.";
                   leaf address {
                     type "inet:ip-address-no-zone";
                     description
                       "Specify the IPv4 address or IPv6 address of a summarized"+
                       " route. Only IPv4 summarized routes can be configured in"+
                       " the IPv4 address family and only IPv6 summarized routes"+
                       " can be configured in the IPv6 address family.";
                     must "not(contains(../address,':'))";
                   }
                   leaf mask-length {
                     type "uint8" {
                       range "1..128";
                     }
                     description
                       "Specify the mask length of a summarized address.";
                     must "../mask-length<=32";
                   }
                   leaf as-set {
                     type "boolean";
                     default "false";
                     description
                       "Enable/disable the generation of routes with the AS-SET "+
                       "attribute. This option can be used to create a "+
                       "summarized route. The AS_Path attribute of the "+
                       "summarized route contains the AS-Path attributes of the "+
                       "specific routes for the route summarization. Exercise "+
                       "caution when using this option if multiple AS_Paths need"+
                       " to be summarized to prevent route flapping.";
                   }
                   leaf detail-suppressed {
                     type "boolean";
                     default "false";
                     description
                       "Enable/disable detail-suppressed. Suppress the "+
                       "advertisement of specific routes for the route "+
                       "summarization. Only the summarized route is advertised.";
                   }
                   choice policy-type {
                     description
                       "Set route policy or filter.";
                     case rtp-ref {
                       description
                         "Route policy.";
                       leaf attribute-policy {
                         type "leafref" {
                           path "/rtp:routing-policy/rtp:policy-definitions/rtp:"+
                                "policy-definition/rtp:name";
                         }
                         description
                           "Specify an attribute of summarized routes. If apply "+
                           "as-path is used to configure the AS_Path attribute "+
                           "that is used in the route Summarization policy, and "+
                           "the as-set keyword is set, the AS_Path attribute in "+
                           "the policy does not take effect. This parameter and "+
                           "any of the following parameters overwrite each "+
                           "other: suppressFilter, originFilter, and attributeFi"+
                           "lter.";
                       }
                       leaf origin-policy {
                         type "leafref" {
                           path "/rtp:routing-policy/rtp:policy-definitions/rtp:"+
                                "policy-definition/rtp:name";
                         }
                         description
                           "Specify the name of a policy for generating "+
                           "summarized routes. Summarized routes are generated "+
                           "only when the routes match route-policy. This "+
                           "parameter and any of the following parameters "+
                           "overwrite each other: suppressFilter, originFilter, "+
                           "and attributeFilter.";
                       }
                       leaf suppress-policy {
                         type "leafref" {
                           path "/rtp:routing-policy/rtp:policy-definitions/rtp:"+
                                "policy-definition/rtp:name";
                         }
                         description
                           "Specify a policy for suppressing the advertisement "+
                           "of specified routes. The routes matching the policy "+
                           "are not advertised, and other routes are advertised."+
                           " This parameter and any of the following parameters "+
                           "overwrite each other: suppressFilter, originFilter, "+
                           "and attributeFilter.";
                       }
                     }
                     case xpl-ref {
                       description
                         "Route filter.";
                       leaf attribute-filter-name {
                         type "leafref" {
                           path "/xpl:xpl/xpl:route-filters/xpl:route-filter/xpl"+
                                ":name";
                         }
                         description
                           "Specify a route-filter name.";
                       }
                       leaf attribute-filter-parameter {
                         when "../attribute-filter-name";
                         type "xpl:filter-parameter-type";
                         description
                           "Specify a route-filter parameter.";
                       }
                       leaf origin-filter-name {
                         type "leafref" {
                           path "/xpl:xpl/xpl:route-filters/xpl:route-filter/xpl"+
                                ":name";
                         }
                         description
                           "Specify a route-filter name.";
                       }
                       leaf origin-filter-parameter {
                         when "../origin-filter-name";
                         type "xpl:filter-parameter-type";
                         description
                           "Specify a route-filter parameter.";
                       }
                       leaf suppress-filter-name {
                         type "leafref" {
                           path "/xpl:xpl/xpl:route-filters/xpl:route-filter/xpl"+
                                ":name";
                         }
                         description
                           "Specify a route-filter name.";
                       }
                       leaf suppress-filter-parameter {
                         when "../suppress-filter-name";
                         type "xpl:filter-parameter-type";
                         description
                           "Specify a route-filter parameter.";
                       }
                     }
                   }
                 }
               }
               container import-filter-policy {
                 description
                   "Configure a filtering policy. It is used to filter the "+
                   "routes received from a peer. By default, routes are not "+
                   "filtered.";
                 choice ipv4-import-filter-protocol-policy-type {
                   description
                     "Set IPv4 filter protocol policy.";
                   case acl-ref {
                     description
                       "ACL Route Policy.";
                     leaf acl-name-or-num {
                       type "leafref" {
                         path "/acl:acl/acl:groups/acl:group/acl:identity";
                       }
                       description
                         "Specify the name or number of an ACL Rule. The number "+
                         "value ranges from 2000 to 2999 and is used by basic "+
                         "ACL rules. The name must start with a letter, and the "+
                         "name is case-sensitive.";
                     }
                   }
                   case ip-prefix-ref {
                     description
                       "IP prefix Policy.";
                     leaf ipv4-prefix-filter {
                       type "leafref" {
                         path "/rtp:routing-policy/rtp:ipv4-prefix-filters/rtp:i"+
                              "pv4-prefix-filter/rtp:name";
                       }
                       description
                         "Specify the IPv4 prefix list name.";
                     }
                   }
                   case xpl-ref {
                     description
                       "Route filter.";
                     leaf filter-name {
                       type "leafref" {
                         path "/xpl:xpl/xpl:route-filters/xpl:route-filter/xpl:n"+
                              "ame";
                       }
                       description
                         "Specify a route-filter name.";
                     }
                     leaf filter-parameter {
                       when "../filter-name";
                       type "xpl:filter-parameter-type";
                       description
                         "Specify a route-filter parameter.";
                     }
                   }
                 }
               }
               container export-filter-policys {
                 description
                   "List of filtering policies.";
                 list export-filter-policy {
                   key "protocol process-id";
                   description
                     "Apply a filtering policy. It is used to filter the routes "+
                     "to be advertised to the peer. By default, routes are not "+
                     "filtered.";
                   leaf protocol {
                     type "bgp:ipv4-export-filter-protocol-type";
                     description
                       "Specify the name of a routing protocol. The routing "+
                       "protocol takes effect only on the routes to be "+
                       "advertised. The IPv4 address family supports the direct,"+
                       " IS-IS, OSPF, RIP, and static routing protocols. The "+
                       "IPv6 unicast address family of a public network instance"+
                       " supports the direct, IS-IS, OSPFv3, RIPng, and static "+
                       "routing protocols. The IPv6 address family of a VPNv6 "+
                       "instance supports the direct, IS-IS, RIPng, and static "+
                       "routing protocols.";
                     must "(../protocol ='op-route' and ../../../../type "+
                          "!='ipv4multi') or (../protocol !='op-route')";
                   }
                   leaf process-id {
                     type "uint32" {
                       range "0..4294967295";
                     }
                     must "((../protocol='ospf' or ../protocol='rip' or "+
                          "../protocol='isis') and ../process-id!=0) or "+
                          "((../protocol!='ospf' and ../protocol!='rip' and "+
                          "../protocol!='isis') and ../process-id=0)";
                     description
                       "Specify the process ID required to be matched. The value"+
                       " is an integer ranging from 0 to 4294967295. If direct "+
                       "or static routes need to be filtered, no process ID is "+
                       "required.";
                   }
                   choice ipv4-filter-protocol-policy-type {
                     mandatory "true";
                     description
                       "Set IPv4 filter protocol policy.";
                     case acl-ref {
                       description
                         "ACL Route Policy.";
                       leaf acl-name-or-num {
                         type "leafref" {
                           path "/acl:acl/acl:groups/acl:group/acl:identity";
                         }
                         description
                           "Specify the name or number of an ACL Rule. The "+
                           "number value ranges from 2000 to 2999 and is used by"+
                           " basic ACL rules. The name must start with a letter,"+
                           " and the name is case-sensitive.";
                       }
                     }
                     case ip-prefix-ref {
                       description
                         "IP prefix Policy.";
                       leaf ipv4-prefix-filter {
                         type "leafref" {
                           path "/rtp:routing-policy/rtp:ipv4-prefix-filters/rtp"+
                                ":ipv4-prefix-filter/rtp:name";
                         }
                         description
                           "Specify the IPv4 prefix list name.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
               }
               container slow-peer {
                 description
                   "Configure peer advertising routes slowly.";
                 leaf detection {
                   type "boolean";
                   default "true";
                   description
                     "Enable/disable detect slow peers.";
                 }
                 leaf detection-threshold {
                   type "uint16" {
                     range "120..3600";
                   }
                   units "s";
                   default "300";
                   description
                     "Specify the time in seconds lagging behind average when a "+
                     "peer is determined to be a slow peer.";
                 }
                 leaf absolute-detection {
                   type "boolean";
                   default "true";
                   description
                     "Enable/disable absolute-detect slow peers.";
                 }
                 leaf absolute-detection-threshold {
                   type "uint16" {
                     range "3..3600";
                   }
                   units "s";
                   default "9";
                   description
                     "Specify the packet send delay time in second when a peer "+
                     "is determined to be a slow peer.";
                 }
               }
               container qos {
                 description
                   "Configure QoS.";
                 choice local-id-policy {
                   description
                     "Configure QoS local ID.";
                   case value {
                     description
                       "Specify the QoS local ID value.";
                     leaf local-id {
                       type "uint8" {
                         range "1..255";
                       }
                       description
                         "Specify the QoS local ID value.";
                     }
                   }
                   case rtp-ref {
                     description
                       "Route policy.";
                     leaf local-id-policy-name {
                       type "leafref" {
                         path "/rtp:routing-policy/rtp:policy-definitions/rtp:po"+
                              "licy-definition/rtp:name";
                       }
                       description
                         "Set a routing policy to filter routes so that a "+
                         "configured QoS ID is applied to the routes that match "+
                         "the specified policy.";
                     }
                   }
                   case xpl-ref {
                     description
                       "Route filter.";
                     leaf local-id-filter-name {
                       type "leafref" {
                         path "/xpl:xpl/xpl:route-filters/xpl:route-filter/xpl:n"+
                              "ame";
                       }
                       description
                         "Specify a route-filter name.";
                     }
                     leaf local-id-filter-parameter {
                       when "../local-id-filter-name";
                       type "xpl:filter-parameter-type";
                       description
                         "Specify a route-filter parameter.";
                     }
                   }
                 }
               }
             }
           }
         }
         container vpn-as-number {
           when "../../../ni:name!='_public_'";
           description
             "Configure BGP vpn as-number.";
           leaf local-ipv4 {
             type "as-number-validate";
             description
               "IPv4 as-number.";
           }
           leaf local-ipv6 {
             type "as-number-validate";
             description
               "IPv6 as-number.";
           }
         }
         container dynamic-peer-prefixes {
           description
             "List of IP prefixes from which a dynamic BGP peer group listens "+
             "for BGP connection requests.";
           list dynamic-peer-prefix {
             key "address mask-length peer-group";
             description
               "Configure an IP prefix from which a dynamic BGP peer group "+
               "listens for BGP connection requests.";
             leaf address {
               type "inet:ip-address-no-zone";
               must "contains(., ':') = 'false'";
               description
                 "Network segment address for a dynamic peer connection.";
             }
             leaf mask-length {
               type "uint8" {
                 range "0..32";
               }
               description
                 "Mask length of a network segment. For an IPv4 network address,"+
                 " the value ranges from 0 to 32.";
             }
             leaf peer-group {
               type "leafref" {
                 path "../../../peer-groups/peer-group/name";
               }
               must "../../../peer-groups/peer-group[name = current()]/peer-esta"+
                    "blish-mode = 'dynamic'";
               must "../../../peer-groups/peer-group[name = current()]/listen-as"+
                    " or ../../../peer-groups/peer-group[name = current()]/liste"+
                    "n-as-segments/listen-as-segment or /ni:network-instance/ni:"+
                    "instances/ni:instance[ni:name='_public_']/bgp:bgp/bgp:base-"+
                    "process/bgp:peer-groups/bgp:peer-group[name = current()]/bg"+
                    "p:as-number-type='confederation'";
               description
                 "The peer-group within which the dynamic neighbor will be "+
                 "configured.";
             }
           }
         }
         container peer-groups {
           description
             "List of BGP peer groups. The BGP peer groups can help you simplify"+
             " the configurations. If you want to perform the same configuration"+
             " for several peers, you can create a peer group and then configure"+
             " the peer group. After you add these peers to the peer group, all "+
             "these peers will have the same configurations as the peer group.";
           list peer-group {
             key "name";
             description
               "Configure information about a BGP peer group.";
             leaf name {
               type "string" {
                 length "1..47";
                 pattern "([^\\? ]+)";
               }
               description
                 "Specify the name of a peer group. The value is a string of "+
                 "characters, spaces not supported.";
             }
             leaf type {
               type "group-type";
               mandatory "true";
               description
                 "Specify the type of a peer group. The value can be IBGP or "+
                 "EBGP.The object cannot be modified.";
               ext:operation-exclude "update" {
                 description
                   "The node cannot be modified, when node is already configured"+
                   ".";
               }
             }
             leaf local-if-name {
               type "leafref" {
                 path "/ifm:ifm/ifm:interfaces/ifm:interface/ifm:name";
               }
               description
                 "Name of a source interface that sends BGP packets. By default,"+
                 " the outbound interface of a BGP packet serves as the source "+
                 "interface of a BGP packet. To ensure that a router can send "+
                 "BGP packets when a physical interface fails, you can configure"+
                 " the source interface that sends BGP packets as a loopback "+
                 "interface. When using the loopback interface as the source "+
                 "interface, note the following points: 1. The address of the "+
                 "loopback interface of the BGP peer must be reachable. 2. For "+
                 "an EBGP connection, configure the maximum number of hops and "+
                 "allow EBGP peer relationships to be established in indirect "+
                 "mode.";
             }
             leaf local-if-address {
               type "inet:ip-address-no-zone";
               description
                 "Name of a source interface that sends BGP packets. By default,"+
                 " the outbound interface of a BGP packet serves as the source "+
                 "interface of a BGP packet. To ensure that a router can send "+
                 "BGP packets when a physical interface fails, you can configure"+
                 " the source interface that sends BGP packets as a loopback "+
                 "interface. When using the loopback interface as the source "+
                 "interface, note the following points:\n1. The address of the "+
                 "loopback interface of the BGP peer must be reachable.\n2. For "+
                 "an EBGP connection, configure the maximum number of hops and "+
                 "allow EBGP peer relationships to be established in indirect "+
                 "mode.";
             }
             leaf password-type {
               type "bgp:password-type";
               must "not((../password-type and ../password-type!='null') and "+
                    "(../key-chain-name or ../tcp-ao-name))";
               must "(not(../password-type and ../password-type!='null') and "+
                    "not(../password-text)) or (../password-type and ../password"+
                    "-type!='null' and ../password-text)";
               default "null";
               description
                 "Enable BGP peers to establish a TCP connection and perform the"+
                 " Message Digest 5 (MD5) authentication for BGP messages. "+
                 "Plaintexts and ciphertexts are supported.";
             }
             leaf password-text {
               when "../password-type and ../password-type!='null'";
               type "pub-type:password-extend";
               mandatory "true";
               description
                 "Enable BGP peers to establish a TCP connection and perform the"+
                 " Message Digest 5 (MD5) authentication for BGP messages. The "+
                 "character string in a password identifies the contents of the "+
                 "password, spaces not supported. The TCP connection can be "+
                 "established only when the same MD5 authentication password is "+
                 "set on both ends. If a plaintext is used, the maximum password"+
                 " length is 255. If a ciphertext is used, the maximum password "+
                 "length is 432. If the length is set to 0, no password is set.";
             }
             leaf key-chain-name {
               type "string" {
                 length "1..47";
                 pattern "[^A-Z]+";
               }
               must "not(../password-type!='null' or ../tcp-ao-name)";
               description
                 "Specify the Keychain authentication name used when BGP peers "+
                 "establish a TCP connection. The value is a string, spaces not "+
                 "supported. By default, the Keychain authentication is not "+
                 "configured. Keychain authentication mode and password "+
                 "authentication mode are mutually exclusive. Configuring "+
                 "Keychain authentication can enhance the security of the TCP "+
                 "connections between BGP peers. Keychain authentication using "+
                 "the same encryption algorithm and password must be configured "+
                 "on the two ends of BGP peers to establish a TCP connection and"+
                 " exchange BGP packets. Before configuring BGP Keychain "+
                 "authentication, you need to configure Keychain according to "+
                 "keychain name. Otherwise, the TCP connections between the BGP "+
                 "peers cannot be established.";
               ext:case-sensitivity "lower-only";
             }
             leaf tcp-ao-name {
               type "leafref" {
                 path "/socket:socket/socket:tcp-aos/socket:tcp-ao/socket:name";
               }
               must "not(../password-type!='null' or ../key-chain-name)";
               description
                 "Specify TCP-AO authentication for establishing the TCP "+
                 "connection between BGP peers.";
             }
             leaf description {
               type "string" {
                 length "1..255";
                 pattern "([^?]*)";
               }
               description
                 "Specify the description of a peer group. The value is a "+
                 "string, which can be letters or digits, spaces supported. By "+
                 "default, no description is configured.";
             }
             leaf group-as {
               when "not(../type='ibgp') and ../peer-establish-mode = 'static'";
               type "as-number-validate";
               description
                 "Specify the AS number of a peer group. The AS number is in "+
                 "either a 2-byte or 4-byte format. \nThe two-byte format is X. "+
                 "X is an integer ranging from 1 to 65535.\nThe four-byte format"+
                 " is X.Y and X. When the format is X.Y, X and Y are both "+
                 "integers, with the value of X ranging from 1 to 65535, and the"+
                 " value of Y ranging from 0 to 65535; when the format is X, X "+
                 "is an interger, with the value of X ranging from 1 to "+
                 "4294967295.";
             }
             leaf tcp-mss {
               type "uint16" {
                 range "176..4096";
               }
               description
                 "Maximum TCP MSS value used for TCP connection establishment "+
                 "for a peer group.";
             }
             leaf ebgp-max-hop {
               when "../type='ebgp'";
               type "uint32" {
                 range "1..255";
               }
               must "not(../valid-ttl-hops) or (../valid-ttl-hops>=1 and "+
                    "not(../valid-ttl-hops>255) and ../ebgp-max-hop=1)";
               default "1";
               description
                 "Maximum number of hops in an indirect EBGP connection. By "+
                 "default, EBGP connections can be established only between "+
                 "directly connected peers. The function must be configured on "+
                 "both ends.";
             }
             leaf valid-ttl-hops {
               type "uint16" {
                 range "1..255";
               }
               must "not(../ebgp-max-hop and ../ebgp-max-hop>1)";
               description
                 "Enable GTSM on a peer or peer group. The valid-TTL-Value "+
                 "parameter is used to specify the number of TTL hops to be "+
                 "detected. If the value is configured as hops, the valid TTL "+
                 "range of the detected packet is [255-hops+1, 255].";
             }
             leaf tracking-enable {
               type "boolean";
               default "false";
               description
                 "Enable/disable peer tracking, After peer tracking is enabled, "+
                 "the device can fast detect the unreachability of a peer and "+
                 "reset the session.";
             }
             leaf tracking-delay-time {
               when "../tracking-enable='true'";
               type "uint16";
               units "s";
               default "0";
               description
                 "Specify the delay to reset the session.";
             }
             leaf conventional {
               type "boolean";
               default "false";
               description
                 "Enable/disable general router functions on peers. In "+
                 "conventional mode, not all the extended router functions, such"+
                 " as, route refreshing, GR, and multi-address family negotiatio"+
                 "n, are available. Therefore, the router of a new version can "+
                 "be compatible with the routers of earlier versions.";
             }
             leaf route-refresh {
               type "boolean";
               default "true";
               description
                 "Enable/disable BGP to advertise Refresh messages to peers.";
             }
             leaf four-byte-as {
               type "boolean";
               default "true";
               description
                 "Enable/disable BGP to advertise routes carrying 4-byte AS "+
                 "numbers to peers. After the 4-byte AS number function is "+
                 "disabled, Open packets will not carry 4-byte AS number "+
                 "capability flag, and peer ends will not know that local ends "+
                 "have the 4-byte AS number function. The 4-byte AS number "+
                 "function cannot be disabled from peers (peer groups) if a "+
                 "4-byte AS number, fake AS number, or confederation ID is "+
                 "configured on a router and the AS number of a peer is 4-byte. "+
                 "If the 4-byte AS number function is disabled in such a "+
                 "situation, BGP sessions may fail to be established, and route "+
                 "transmission may be affected.";
             }
             leaf ignore {
               type "boolean";
               default "false";
               description
                 "Enable/disable the function to tear down sessions between "+
                 "peers and clear all related routing information.";
             }
             leaf connect-mode {
               when "../peer-establish-mode!='dynamic'";
               type "connect-mode";
               default "null";
               description
                 "The value can be Connect-only, Listen-only, or Both. If the "+
                 "value is Connect-only, the specified peer or peer group only "+
                 "initiatively sends connection requests, instead of listening "+
                 "to connection requests. If the value is Listen-only, the "+
                 "specified peer or peer group only listens to connection "+
                 "requests, instead of initiatively sending connection requests."+
                 " If the value is Both, the specified peer or peer group not "+
                 "only initiatively sends connection requests, but also listens "+
                 "to connection requests. The default value is Both.";
             }
             leaf log-change {
               type "boolean";
               default "true";
               description
                 "Enable/disable BGP to record the session status and events of "+
                 "the specified peer or peer group.";
             }
             leaf path-mtu-auto-discovery {
               when "../peer-establish-mode = 'static'";
               type "boolean";
               default "false";
               description
                 "Enable/disable path mtu auto discovery.";
             }
             leaf local-ifnet-disable {
               type "boolean";
               description
                 "Enable/disable MPLS local IFNET tunnel creation on a BGP peer."+
                 " By default, MPLS local IFNET tunnels can be created on an "+
                 "EBGP peer,but such tunnels cannot be created on an IBGP peer.";
               ext:dynamic-default;
             }
             leaf check-first-as {
               when "../type='ebgp'";
               type "peer-cap-config-state";
               default "default";
               description
                 "Check the first AS in the AS_Path of the update messages from "+
                 "EBGP peers.";
             }
             leaf memory-priority {
               type "memory-priority";
               default "medium";
               description
                 "Set a priority that determines the disconnection order of each"+
                 " BGP peer relationship in a peer group if memory overload "+
                 "occurs.";
             }
             leaf oscillation-dampening {
               when "../peer-establish-mode!='dynamic'";
               type "boolean";
               default "true";
               description
                 "Enable/disable BGP to suppress the establishment of a "+
                 "specified peer group's peer relationships that flap continuous"+
                 "ly. By default, the capability is enabled.";
             }
             leaf peer-establish-mode {
               type "enumeration" {
                 enum "static" {
                   value "1";
                   description
                     "Establish a BGP peer relationship statically.";
                 }
                 enum "dynamic" {
                   value "2";
                   description
                     "Establish a BGP peer relationship dynamically.";
                 }
               }
               default "static";
               description
                 "Specify mode in which a BGP peer is established.";
               ext:operation-exclude "update|delete" {
                 description
                   "The node cannot be modified, deleted when node is already "+
                   "configured.";
               }
             }
             leaf as-number-type {
               when "../peer-establish-mode = 'dynamic' and ../../../../../ni:na"+
                    "me='_public_'";
               type "as-number-type";
               must ". = 'dynamic-neighbor' or (. = 'confederation' and "+
                    "/bgp:bgp/bgp:base-process/bgp:confederation/bgp:id and "+
                    "../type = 'ebgp')";
               default "dynamic-neighbor";
               description
                 "Specify the type of the AS number that is used to establish a "+
                 "BGP peer relationship dynamically. The value can be dynamic-ne"+
                 "ighbor or confederation.";
               ext:operation-exclude "update|delete" {
                 description
                   "The node cannot be modified, deleted when node is already "+
                   "configured.";
               }
             }
             leaf-list listen-as {
               when "../peer-establish-mode = 'dynamic' and ../type = 'ebgp'";
               type "as-number-validate";
               must "not(. = /bgp:bgp/bgp:base-process/bgp:as) and not(/ni:netwo"+
                    "rk-instance/ni:instances/ni:instance[ni:name='_public_']/bg"+
                    "p:bgp/bgp:base-process/bgp:peer-groups/bgp:peer-group[name "+
                    "= current()/../name]/bgp:as-number-type='confederation')";
               max-elements "6";
               description
                 "Specify the peer AS from which a dynamic EBGP peer group "+
                 "listens for BGP connection requests.";
             }
             container listen-as-segments {
               when "../peer-establish-mode = 'dynamic' and ../type = 'ebgp'";
               description
                 "List of AS number ranges for listening.";
               list listen-as-segment {
                 must "not(../../listen-as) and not(/ni:network-instance/ni:inst"+
                      "ances/ni:instance[ni:name='_public_']/bgp:bgp/bgp:base-pr"+
                      "ocess/bgp:peer-groups/bgp:peer-group[name = current()/../"+
                      "../name]/bgp:as-number-type='confederation')";
                 key "begin-as end-as";
                 max-elements "16";
                 description
                   "Specify an AS number range from which a dynamic EBGP peer "+
                   "group listens for connection requests. The value of begin-as"+
                   " must be smaller than that of end-as. The value of "+
                   "As-Segment cannot contain the value of LocalAS or the value "+
                   "of fake-as. An AS number range cannot contain a confederatio"+
                   "n AS number, and any two AS number ranges cannot contain "+
                   "each other.";
                 leaf begin-as {
                   type "as-number-validate";
                   description
                     "Specify the start AS number in an AS range.";
                 }
                 leaf end-as {
                   type "as-number-validate";
                   description
                     "Specify the end AS number in an AS range.";
                 }
               }
             }
             container fake-as-parameter {
               description
                 "Configure BGP fake-as parameters.";
               leaf fake-as {
                 when "../../bgp:type='ebgp'";
                 type "bgp:as-number-validate";
                 description
                   "Fake AS number that is specified for a local peer. By "+
                   "default, a peer uses the actual AS number of the local "+
                   "end.\nAn AS number can be in either two-byte format or "+
                   "four-byte format:\nThe two-byte format is X. X is an integer"+
                   " ranging from 1 to 65535.\nThe four-byte format is X.Y and "+
                   "X. When the format is X.Y, X and Y are both integers, with "+
                   "the value of X ranging from 1 to 65535, and the value of Y "+
                   "ranging from 0 to 65535; when the format is X, X is an "+
                   "interger, with the value of X ranging from 1 to 4294967295.";
               }
               leaf dual-as {
                 when "../fake-as";
                 type "boolean";
                 default "false";
                 description
                   "Enable/disable the function to the remote EBGP peer can use "+
                   "the actual or fake AS number when specifying the AS number "+
                   "for a local peer. The local peer uses the fake and actual AS"+
                   " numbers to establish a BGP peer relationship with the "+
                   "remote end and identifies the AS number configured by the "+
                   "remote end through the error code (OPEN Message Error) and "+
                   "sub-error code (Bad Peer AS) of the Notification message "+
                   "from the remote end.";
               }
               leaf prepend-global-as {
                 when "../fake-as";
                 type "boolean";
                 default "false";
                 description
                   "Enable/disable the function to add the global AS number to "+
                   "the Update packets to be advertised.";
               }
               leaf prepend-fake-as {
                 when "../fake-as";
                 type "boolean";
                 default "false";
                 description
                   "Enable/disable the function to add the Fake AS number to "+
                   "received Update packets.";
               }
             }
             container timer {
               description
                 "Configure BGP peer timer parameters.";
               leaf keep-alive-time {
                 type "uint32" {
                   range "0..21845";
                 }
                 units "s";
                 must "(../keep-alive-time != 0 and (../hold-time>=../keep-alive"+
                      "-time * 3) and ../hold-time != ../keep-alive-time ) or "+
                      "(../hold-time = 0 and ../keep-alive-time = 0)";
                 default "60";
                 description
                   "If the value of a timer changes, the BGP peer relationship "+
                   "between the routers is disconnected. This is because the "+
                   "peers need to re-negotiate the Keepalive time and hold time."+
                   " Therefore, confirm the action before you change the value "+
                   "of the timer. The Keepalive time should be at least three "+
                   "times of the hold time.";
               }
               leaf hold-time {
                 type "uint32" {
                   range "0 | 3..65535";
                 }
                 units "s";
                 must "(((../hold-time>=../keep-alive-time * 3) and ../hold-time"+
                      " != ../keep-alive-time ) or (../hold-time = 0 and "+
                      "../keep-alive-time = 0)) and ../hold-time>=../min-hold-ti"+
                      "me";
                 default "180";
                 description
                   "Hold time. When setting keepalive-time and hold-time, note "+
                   "the following:\n1. The values of keepalive-time and "+
                   "hold-time cannot both be 0. Otherwise, the BGP timer becomes"+
                   " invalid. That is, BGP does not detect link faults according"+
                   " to the timer.\n2. The value of hold-time is much greater "+
                   "than that of keepalive-time, such as, keepalive 1 and hold "+
                   "65535. If the value of hold-time is too large, BGP cannot "+
                   "detect link faults timely.\nThe priority of a timer is lower"+
                   " than that of a peer timer.\nAfter a connection is "+
                   "established between peers, the values of keepalive-time and "+
                   "hold-time are negotiated by the peers. The smaller value of "+
                   "hold-time contained in Open packets of both peers is taken "+
                   "as the value of hold-time. The smaller value of the locally "+
                   "set value of keepalive-time and one third of the value of "+
                   "hold-time is taken as the value of keepalive-time.";
               }
               leaf min-hold-time {
                 type "uint32" {
                   range "0 | 20..65535";
                 }
                 units "s";
                 must "../hold-time>=../min-hold-time";
                 default "0";
                 description
                   "The default value of zero means that the minimum hold time "+
                   "check does not take effect. If the value is changed, the new"+
                   " value takes effect since the next peer relationship "+
                   "establishment. During the peer relationship establishment, "+
                   "the local device checks the hold time of the remote end. If "+
                   "the hold time is less than the minimum hold time, the local "+
                   "device sends an error packet with error code 02 and subcode "+
                   "06, and the peer relationship fails to be established.";
               }
               leaf connect-retry-time {
                 type "uint16" {
                   range "1..65535";
                 }
                 units "s";
                 default "32";
                 description
                   "ConnectRetry interval.";
               }
             }
             container bfd-parameter {
               description
                 "Configure BFD.";
               leaf enable {
                 type "boolean";
                 default "false";
                 description
                   "Enable/disable BFD.";
               }
               choice mode-type {
                 description
                   "Set bfd mode.";
                 case single {
                   description
                     "Single hop mode.";
                   leaf single-hop {
                     when "../enable='true'";
                     type "empty";
                     description
                       "The single hop mode is preferred during the BFD session "+
                       "establishment between IBGP peers.";
                   }
                   leaf compatible {
                     when "../enable='true'";
                     type "empty";
                     description
                       "Compatible.";
                   }
                 }
                 case link {
                   description
                     "Per-link-echo mode.";
                   leaf per-link-echo {
                     when "../enable='true'";
                     type "empty";
                     description
                       "The per-link one-arm-echo mode is preferred during the "+
                       "BFD session establishment between IBGP peers.";
                   }
                 }
               }
               leaf multiplier {
                 type "uint32" {
                   range "3..50";
                 }
                 default "3";
                 description
                   "Specify the detection multiplier.";
               }
               leaf min-rx-interval {
                 type "uint32" {
                   range "3..20000";
                 }
                 units "ms";
                 description
                   "Specify the minimum interval at which BFD packets are "+
                   "received. The value range and default value are controlled "+
                   "by the PAF.";
               }
               leaf min-tx-interval {
                 type "uint32" {
                   range "3..20000";
                 }
                 units "ms";
                 description
                   "Specify the minimum interval at which BFD packets are sent. "+
                   "The value range and default value are controlled by the "+
                   "PAF.";
               }
               leaf valid-ttl-hops {
                 type "uint8" {
                   range "1..255";
                 }
                 description
                   "Specify the valid TTL hops value.";
               }
             }
             container graceful-restart {
               when "../peer-establish-mode!='dynamic'";
               description
                 "Configure graceful restart.";
               leaf enable {
                 type "boolean";
                 default "false";
                 description
                   "Enable/disable graceful restart capability.";
               }
               leaf time-wait-for-rib {
                 type "uint32" {
                   range "3..3000";
                 }
                 units "s";
                 default "600";
                 description
                   "Period of waiting for the End-of-RIB flag. The value is an "+
                   "integer. When a BGP session is established or re-established"+
                   ", the router enabled with GR should receive the End-of-RIB "+
                   "flag in this period. If the router does not receive the "+
                   "End-of-RIB flag in this period, ensure that the router can "+
                   "exit from the GR process.";
               }
               leaf restart-time {
                 type "uint16" {
                   range "3..3600";
                 }
                 units "s";
                 default "150";
                 description
                   "Specifies the maximum time during which a peer waits for a "+
                   "BGP session reestablishment.";
               }
               leaf peer-reset {
                 type "boolean";
                 default "false";
                 description
                   "Enable/disable reseting BGP peer graceful.";
               }
             }
             container local-graceful-restart {
               when "../peer-establish-mode = 'static'";
               description
                 "Configure local graceful restart.";
               leaf enable {
                 type "boolean";
                 default "false";
                 description
                   "Enable/disable graceful restart capability.";
               }
               leaf time-wait-for-rib {
                 type "uint32" {
                   range "3..3000";
                 }
                 units "s";
                 default "600";
                 description
                   "Period of waiting for the End-of-RIB flag. The value is an "+
                   "integer. When a BGP session is established or re-established"+
                   ", the router enabled with GR should receive the End-of-RIB "+
                   "flag in this period. If the router does not receive the "+
                   "End-of-RIB flag in this period, ensure that the router can "+
                   "exit from the GR process.";
               }
               leaf restart-time {
                 type "uint16" {
                   range "3..3600";
                 }
                 units "s";
                 default "150";
                 description
                   "Specifies the maximum time during which a peer waits for a "+
                   "BGP session reestablishment.";
               }
             }
             container ssl-policy {
               when "../../../../../ni:name='_public_' and ../peer-establish-mod"+
                    "e='static'";
               description
                 "Configure SSL policy for BGP group.";
               leaf name {
                 type "leafref" {
                   path "/ssl:ssl/ssl:ssl-policys/ssl:ssl-policy/ssl:policy-name"+
                        "";
                 }
                 description
                   "SSL policy name.";
               }
               leaf role {
                 type "ssl-role-type";
                 description
                   "Configure a peer as an SSL client or server.";
                 ext:operation-exclude "update" {
                   description
                     "The node cannot be modified. You need to disable or delete"+
                     " the node first.";
                 }
                 must "(../role='client' and ../../connect-mode != 'listen-only'"+
                      ") or (../role='server' and ../../connect-mode != "+
                      "'connect-only')";
               }
               leaf server-certificate {
                 type "empty";
                 must "../role != 'client'";
                 description
                   "Enable/disable SSL/TLS authentication on an SSL server.";
               }
             }
             container members {
               config "false";
               description
                 "List of members in a peer group.";
               list member {
                 key "peer-address";
                 config "false";
                 description
                   "Statistics of member in a peer group.";
                 leaf peer-address {
                   type "inet:ip-address-no-zone";
                   config "false";
                   description
                     "Specify the address of the peer joining the peer group.";
                 }
               }
             }
             container afs {
               description
                 "List of all peer groups that are enabled in a specified "+
                 "address family.";
               list af {
                 key "type";
                 description
                   "Configure peer group enabled in a specified address family.";
                 leaf type {
                   type "enumeration" {
                     enum "ipv4uni" {
                       value "1";
                       description
                         "IPv4 unicast address family.";
                     }
                     enum "ipv4multi" {
                       value "2";
                       description
                         "IPv4 multicast address family.";
                     }
                     enum "ipv4vpn" {
                       value "3";
                       description
                         "IPv4 VPN address family.";
                     }
                     enum "ipv4labeluni" {
                       value "4";
                       description
                         "IPv4 Labeled Address Family.";
                     }
                     enum "ipv6uni" {
                       value "5";
                       description
                         "IPv6 unicast address family.";
                     }
                     enum "ipv6vpn" {
                       value "6";
                       description
                         "IPv6 VPN address family.";
                     }
                     enum "l2vpnad" {
                       value "8";
                       description
                         "L2VPN-AD Address Family.";
                     }
                     enum "evpn" {
                       value "9";
                       description
                         "EVPN address family.";
                     }
                     enum "mvpn" {
                       value "10";
                       description
                         "IPv4 MVPN address family.";
                     }
                     enum "vpntarget" {
                       value "11";
                       description
                         "Vpn Target Address Family.";
                     }
                     enum "ipv4vpnmcast" {
                       value "12";
                       description
                         "IPv4 VPN Multicast Address Family.";
                     }
                     enum "ls" {
                       value "13";
                       description
                         "Link-state Address Family.";
                     }
                     enum "mdt" {
                       value "14";
                       description
                         "IPv4 MDT Address Family.";
                     }
                     enum "mvpnv6" {
                       value "16";
                       description
                         "IPv6 MVPN address family.";
                     }
                   }
                   must "../../../../../afs/af[type = current()]";
                   must "((../type = 'mdt' or ../type = 'ipv4vpnmcast') and "+
                        "../../../type!='ebgp') or not (../type = 'mdt' or "+
                        "../type = 'ipv4vpnmcast')";
                   description
                     "Address family type of a BGP instance.";
                 }
                 container ipv4-unicast {
                   when "../type = 'ipv4uni'";
                   must "../../../../../../../l3vpn:afs/l3vpn:af[l3vpn:type='ipv"+
                        "4-unicast']";
                   description
                     "Configure IPv4 unicast options.";
                   leaf reflect-client {
                     when "../../../../bgp:type='ibgp'";
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf orf-type {
                     when "../../../../../../../../ni:name='_public_'";
                     type "bgp:bgp-orf-type";
                     must "(../orf-mode='null' and ../orf-type='null') or "+
                          "(../orf-mode!='null' and ../orf-type!='null')";
                     default "null";
                     description
                       "ORF Type.";
                   }
                   leaf orf-mode {
                     when "../../../../../../../../ni:name='_public_'";
                     type "bgp:bgp-orf-mode-type";
                     must "(../orf-mode='null' and ../orf-type='null') or "+
                          "(../orf-mode!='null' and ../orf-type!='null')";
                     default "null";
                     description
                       "Configure an outbound route filtering (ORF) mode, which "+
                       "can be Receive, Send, or Both, and the default ORF mode "+
                       "is Both.";
                   }
                   leaf label-route-capability {
                     type "boolean";
                     default "false";
                     description
                       "Enable/disable a device to exchange labeled routes.";
                   }
                   leaf check-tunnel-reachable {
                     when "../label-route-capability='true'";
                     type "boolean";
                     default "false";
                     description
                       "Enable/disable tunnel reachability check.";
                   }
                   leaf check-withdraw-type {
                     when "../label-route-capability='true'";
                     type "boolean";
                     default "true";
                     status "obsolete";
                     description
                       "Enable/disable withdraw type check.";
                   }
                   leaf nexthop-configure {
                     type "nexthop-configuration-type";
                     description
                       "Both the next-hop-local mode and next-hop-invariable "+
                       "mode are available when the peer address family is the "+
                       "VPNv4/VPNv6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   leaf static-route-nexthop-invariable {
                     when "../../../../../../../../ni:name='_public_' and "+
                          "../nexthop-configure='invariable'";
                     type "boolean";
                     default "false";
                     description
                       "Enable/disable BGP speaker does not change the next hop "+
                       "of an imported static route when advertising them to its"+
                       " peers.";
                   }
                   leaf unicast-route-nexthop-invariable {
                     when "../../../../../../../../ni:name='_public_' and "+
                          "../nexthop-configure='invariable'";
                     type "boolean";
                     default "false";
                     description
                       "Enable/disable BGP speaker does not change the next hop "+
                       "of an imported unicast route when advertising them to "+
                       "its peers.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf origin-as-validation {
                     when "../advertise-ext-community='true' and ../../../../pee"+
                          "r-establish-mode='static'";
                     type "boolean";
                     default "false";
                     description
                       "Enable/disable the BGP peer origin validation.";
                   }
                   leaf allow-as-loop {
                     type "uint32" {
                       range "1..10";
                     }
                     description
                       "Allow repetitive local AS numbers. By default, "+
                       "repetitive local AS numbers are not allowed.";
                   }
                   leaf aigp {
                     when "../../../../../../../../ni:name='_public_'";
                     type "boolean";
                     default "false";
                     description
                       "Enable/disable route with AIGP attribute advertisement "+
                       "to or from a peer.";
                   }
                   leaf add-path-mode {
                     when "../../../../../../../../ni:name='_public_' and "+
                          "../../../../bgp:type='ibgp'";
                     type "add-path-cap-type";
                     default "null";
                     description
                       "Enable Add-Path route advertisement to a peer.";
                   }
                   leaf import-ip-prefix {
                     type "leafref" {
                       path "/rtp:routing-policy/rtp:ipv4-prefix-filters/rtp:ipv"+
                            "4-prefix-filter/rtp:name";
                     }
                     description
                       "Specify the IPv4 filtering policy applied to the routes "+
                       "received from a specified peer. By default, no such "+
                       "policy is specified.";
                   }
                   leaf export-ip-prefix {
                     type "leafref" {
                       path "/rtp:routing-policy/rtp:ipv4-prefix-filters/rtp:ipv"+
                            "4-prefix-filter/rtp:name";
                     }
                     description
                       "Specify the IPv4 filtering policy applied to the routes "+
                       "to be advertised to a specified peer. By default, no "+
                       "such policy is specified.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl-name-or-num {
                     type "leafref" {
                       path "/acl:acl/acl:groups/acl:group/acl:identity";
                     }
                     description
                       "Specifies the name of the import ACL policy.";
                   }
                   leaf export-acl-name-or-num {
                     type "leafref" {
                       path "/acl:acl/acl:groups/acl:group/acl:identity";
                     }
                     description
                       "Specifies the name of the export ACL policy.";
                   }
                   leaf default-route-advertise {
                     type "boolean";
                     default "false";
                     description
                       "Enable/disable a device to advertise the default route "+
                       "to its peers. This option enables a device to send a "+
                       "default route with the device as the next hop address to"+
                       " its peers, regardless of whether there is a default "+
                       "route in the local routing table.";
                   }
                   choice default-route-advertise-policy-type {
                     description
                       "Set default route advertise-policy.";
                     case rtp-ref {
                       description
                         "The default-route-advertise-policy.";
                       leaf default-route-advertise-policy {
                         when "../default-route-advertise='true'";
                         type "leafref" {
                           path "/rtp:routing-policy/rtp:policy-definitions/rtp:"+
                                "policy-definition/rtp:name";
                         }
                         description
                           "Specify the name of a used policy.";
                       }
                     }
                     case xpl-ref {
                       description
                         "The default-route-advertise-filter.";
                       container default-route-advertise-filter {
                         when "../default-route-advertise='true'";
                         description
                           "Configure the route-filter for default route "+
                           "advertise.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                   leaf default-route-match-mode {
                     when "../default-route-advertise='true'";
                     type "cra-match-mode";
                     default "null";
                     description
                       "Configure the matching mode of default route advertiseme"+
                       "nt, which can be disabling of route advertisement "+
                       "conditions, enabling of all route advertisement "+
                       "conditions, and enabling of part route advertisement "+
                       "conditions. Enabling of all route advertisement "+
                       "conditions indicates that a default route can be "+
                       "advertised only when it matches all the conditions. "+
                       "Enabling of part route advertisement conditions "+
                       "indicates that a default route can be advertised only "+
                       "when it matches one condition.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf add-path-number {
                     when "../../../../../../../../ni:name='_public_' and "+
                          "../../../../bgp:type='ibgp'";
                     type "uint8" {
                       range "2..64";
                     }
                     description
                       "Number of Add-Path routes that can be advertised to a "+
                       "peer.";
                   }
                   leaf substitute-as-enable {
                     when "../../../../bgp:type='ebgp'";
                     type "boolean";
                     default "false";
                     description
                       "Enable/disable replace the AS number of a specified peer"+
                       " in the AS_Path attribute with the local AS number. On a"+
                       " PE where AS number replacement is enabled, if an AS "+
                       "number in the AS_Path attribute of a route is same as "+
                       "that of the CE to which the PE advertises the route, the"+
                       " PE replaces the AS number with its own AS number before"+
                       " advertising the route.";
                   }
                   leaf soo {
                     when "../../../../../../../../ni:name!='_public_'";
                     type "string" {
                       length "3..21";
                     }
                     description
                       "Configure the Site-of-Origin (SoO) extended community "+
                       "attribute. This attribute can be expressed in the "+
                       "following formats: X.X.X.X:number<0-65535>, number<0-655"+
                       "35>:number<0-4294967295>, or number<0-65535>.number<0-65"+
                       "535>:number<0-65535> or <65536-4294967295>:<0-65535>. "+
                       "0:0 or 0.0:0 is not supported. \nTwo CEs are in the same"+
                       " site and can advertise routes to each other, and they "+
                       "are connected to a VPN through PEs. If the local routes "+
                       "of a CE are advertised to the other CE over the VPN, a "+
                       "routing loop may occur. \nThe SoO feature can prevent a "+
                       "route advertised by a site from being sent back to the "+
                       "site, preventing routing loops. After SoO is enabled and"+
                       " a PE receives a route from a CE, the specified SoO "+
                       "attribute will be added to the route. Before advertising"+
                       " the route to the other CE, the PE checks the SoO "+
                       "attribute. If the SoO attribute is the same as the "+
                       "locally configured SoO attribute, the PE does not "+
                       "advertise the route, preventing routing loops.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   leaf exp-mode {
                     type "exp-mode-type";
                     default "null";
                     description
                       "Specify the ASs in which a BGP label can inherit the QoS"+
                       " priority carried in the outer label of public tunnel in"+
                       " the Core AS and the ASs in which the priorities of BGP "+
                       "LSPs must be restored before the LSPs are advertised to "+
                       "a non-core AS.";
                   }
                   leaf advertise-best-external {
                     when "../../../../../../../../ni:name='_public_' and "+
                          "../../../../bgp:type='ibgp'";
                     type "boolean";
                     must "../reflect-client='false' or ../advertise-best-extern"+
                          "al='false'";
                     must "../add-path-mode='null' or not(../add-path-mode) or "+
                          "../advertise-best-external='false'";
                     must "not(../add-path-number and ../advertise-best-external"+
                          "='true')";
                     default "false";
                     description
                       "Enable/disable the device to advertise Best External "+
                       "routes to peers.";
                   }
                   leaf prefix-sid {
                     when "../../../../../../../../ni:name='_public_'";
                     type "boolean";
                     default "false";
                     description
                       "Enable/disable a device to exchange IPv4 prefix SIDs "+
                       "with a specified IPv6 peer group.";
                   }
                   choice prefix-sid-packet {
                     description
                       "Prefix-sid packet method.";
                     case sid-type5 {
                       description
                         "Packet by type5.";
                       leaf advertise-srv6-locator {
                         when "../prefix-sid='true'";
                         type "empty";
                         description
                           "Advertise SRv6 locators.";
                       }
                     }
                   }
                   leaf update-group-independent {
                     type "boolean";
                     default "false";
                     description
                       "Enable/disable the peer which can reside in an "+
                       "independent peer group.";
                   }
                   leaf load-balancing-enable {
                     type "boolean";
                     default "false";
                     description
                       "Enable/disable a neighbour to participate in load "+
                       "balancing.";
                   }
                   choice load-balancing-ignore-as-type {
                     description
                       "Set load balancing as path type.";
                     case as-attribute {
                       description
                         "Ignore the as-path attribute.";
                       leaf load-balancing-as-path-ignore {
                         when "../load-balancing-enable='true'";
                         type "empty";
                         description
                           "Configure BGP to ignore the AS_Path attribute when "+
                           "selecting the equal route. After as-path-neglect is "+
                           "selected, BGP does not compare the AS_Path length.";
                       }
                     }
                     case same-length-as-attribute {
                       description
                         "Ignore comparison of as-path attributes with the same "+
                         "length.";
                       leaf load-balancing-as-path-relax {
                         when "../load-balancing-enable='true'";
                         type "empty";
                         description
                           "Configure BGP to ignore comparison of AS_Path "+
                           "attributes with the same length when selecting the "+
                           "equal route. After as-path-neglect is selected, BGP "+
                           "does not compare the AS_Path length.";
                       }
                     }
                   }
                   leaf advertise-community {
                     type "boolean";
                     default "false";
                     description
                       "Enable/disable advertise the community attribute to a "+
                       "peer or a peer group.";
                   }
                   leaf advertise-ext-community {
                     type "boolean";
                     default "false";
                     description
                       "Enable/disable advertise the extended community "+
                       "attribute to a peer or peer group.";
                   }
                   leaf discard-ext-community {
                     type "boolean";
                     default "false";
                     description
                       "Enable/disable discard the extended community attribute "+
                       "in the routing information about a specified peer.";
                   }
                   leaf advertise-large-community {
                     type "boolean";
                     default "false";
                     description
                       "Enable/disable large-community attribute advertisement. "+
                       "The Link-state address family and the RPD address family"+
                       " do not support this element.";
                   }
                   container option {
                     description
                       "Configure IPv4 unicast group common options.";
                     leaf export-origin-as-validation {
                       type "peer-attr-enable-type";
                       default "disable";
                       description
                         "Enable/disable the function ebgp group advertising "+
                         "dependent roa validation, route is advtised roa reslut"+
                         " is valid.";
                     }
                     leaf include-not-found {
                       when "../export-origin-as-validation='enable'";
                       type "boolean";
                       default "false";
                       description
                         "Enable/disable the include-not-found attribute of the "+
                         "ROA validation.";
                     }
                     leaf external {
                       when "../include-not-found='true'";
                       type "boolean";
                       default "false";
                       description
                         "Enable/disable ROA export validation to advertise only"+
                         " external not found routes.";
                     }
                   }
                   container default-route-match-conditions {
                     when "../default-route-match-mode and ../default-route-matc"+
                          "h-mode!='null'";
                     description
                       "List of condition matching to filter the default routes "+
                       "to be advertised. The value takes effect only when the "+
                       "default route matching mode is not null and more than "+
                       "one IPv4 default route matching condition lists are "+
                       "configured.";
                     list default-route-match-condition {
                       key "address mask";
                       min-elements "1";
                       max-elements "4";
                       description
                         "Configure the matching condition for default route "+
                         "advertisement.";
                       leaf address {
                         type "inet:ipv4-address-no-zone";
                         description
                           "Configure a prefix that is used to match default "+
                           "routes.";
                       }
                       leaf mask {
                         type "uint32" {
                           range "0..32";
                         }
                         description
                           "Configure a mask that is used to match default "+
                           "routes.";
                       }
                     }
                   }
                   container route-limit {
                     description
                       "Configure parameters of routes limited from this peer.";
                     leaf number {
                       type "uint32" {
                         range "1..4294967295";
                       }
                       description
                         "Configure the maximum number of routes that can be "+
                         "accepted from a peer.";
                     }
                     leaf accept-prefix {
                       when "../number";
                       type "boolean";
                       default "false";
                       description
                         "Enable/disable the device to keep receiving routes and"+
                         " the routes are valid if the maximum number of routes "+
                         "allowed have been received and the alert-only "+
                         "parameter is specified.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "boolean";
                       default "false";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'true'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                   }
                   container advertise-dependent-filter {
                     presence "Enable peer group advertising dependent filter.";
                     description
                       "Configure peer group advertising dependent filter.";
                     leaf dependent-filter {
                       type "leafref" {
                         path "/rtp:routing-policy/rtp:ipv4-prefix-lists/rtp:ipv"+
                              "4-prefix-list/rtp:name";
                       }
                       mandatory "true";
                       description
                         "Specify a dependent route-filter name.";
                     }
                     leaf dependent-filter-type {
                       type "bgp:dependent-prefix-filter-type";
                       mandatory "true";
                       description
                         "Specify a depentent route-filter mode.";
                     }
                     leaf condition-filter {
                       type "leafref" {
                         path "/rtp:routing-policy/rtp:ipv4-prefix-lists/rtp:ipv"+
                              "4-prefix-list/rtp:name";
                       }
                       description
                         "Specify a condition route-filter name.";
                     }
                   }
                   container entropy-label-parameter {
                     when "../../../../../../../../ni:name='_public_' and "+
                          "../label-route-capability='true'";
                     description
                       "Configure information about entropy label parameter in a"+
                       " peer group.";
                     leaf advertise-entropy-label {
                       type "boolean";
                       default "false";
                       description
                         "Enable/disable the capability of advertising entropy "+
                         "labels.";
                     }
                     leaf padding {
                       when "../advertise-entropy-label='true'";
                       type "string" {
                         length "1..32";
                         pattern "(([0-9A-F])*)";
                       }
                       description
                         "Padding format. The value is a hexadecimal string "+
                         "containing 1 to 32 characters (16 hexadecimal "+
                         "numbers). It cannot contain spaces, and can only "+
                         "contain uppercase letters (A to F) and digits (0 to "+
                         "9), and the length must be an even number.";
                     }
                     leaf attribute-type {
                       when "../advertise-entropy-label='true'";
                       type "entropy-label-attribute-type";
                       mandatory "true";
                       description
                         "The attribute-type of advertising entropy labels.";
                     }
                     leaf entropy-label {
                       type "boolean";
                       default "false";
                       description
                         "Enable/disable the function of delivering the entropy "+
                         "label capability to the forwarding plane.";
                     }
                   }
                   container route-server {
                     description
                       "Configure the route server function on a device and "+
                       "specifies an EBGP peer as its client.";
                     leaf route-server-client {
                       when "../../../../../bgp:type='ebgp' and ../../../../../p"+
                            "eer-establish-mode='static'";
                       type "empty";
                       must "not(../route-server-client) or (not(/bgp:bgp/bgp:ba"+
                            "se-process/bgp:confederation/bgp:id) and (/bgp:bgp/"+
                            "bgp:base-process/bgp:confederation/bgp:nonstanded ="+
                            " 'false'))";
                       must "not(../route-server-client) or (../../label-route-c"+
                            "apability = 'false')";
                       must "not(../route-server-client) or (../../prefix-sid = "+
                            "'false')";
                       description
                         "Enable/disable the route server function on a device "+
                         "and specifies an EBGP peer as its client.";
                     }
                   }
                   container link-bandwidth {
                     when "../../../../../../../../ni:name='_public_'";
                     description
                       "Configure link bandwidth attribute.";
                     leaf advertise {
                       when "../../../../../bgp:type='ebgp'";
                       type "peer-attr-enable-type";
                       default "disable";
                       description
                         "Enable/disable advertise the link bandwidth attribute "+
                         "to an EBGP peer.";
                     }
                     leaf transitive {
                       type "peer-attr-enable-type";
                       default "disable";
                       description
                         "Enable/disable transitive the link bandwidth "+
                         "attribute.";
                     }
                     leaf generate {
                       when "../../../../../bgp:type='ebgp'";
                       type "peer-attr-enable-type";
                       default "disable";
                       description
                         "Enable/disable generate the link bandwidth attribute "+
                         "to an EBGP peer.";
                     }
                   }
                 }
                 container ipv6-unicast {
                   when "../type = 'ipv6uni'";
                   must "../../../../../../../l3vpn:afs/l3vpn:af[l3vpn:type='ipv"+
                        "6-unicast']";
                   description
                     "Configure IPv6 unicast options.";
                   leaf advertise-community {
                     type "boolean";
                     default "false";
                     description
                       "Enable/disable advertise the community attribute to a "+
                       "peer or a peer group.";
                   }
                   leaf reflect-client {
                     when "../../../../bgp:type='ibgp'";
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf label-route-capability {
                     type "boolean";
                     default "false";
                     description
                       "Enable/disable a device to exchange labeled routes.";
                   }
                   leaf nexthop-configure {
                     type "nexthop-configuration-type";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   leaf static-route-nexthop-invariable {
                     when "../../../../../../../../ni:name='_public_' and "+
                          "../nexthop-configure='invariable'";
                     type "boolean";
                     default "false";
                     description
                       "Enable/disable BGP speaker does not change the next hop "+
                       "of an imported static route when advertising them to its"+
                       " peers.";
                   }
                   leaf unicast-route-nexthop-invariable {
                     when "../../../../../../../../ni:name='_public_' and "+
                          "../nexthop-configure='invariable'";
                     type "boolean";
                     default "false";
                     description
                       "Enable/disable BGP speaker does not change the next hop "+
                       "of an imported unicast route when advertising them to "+
                       "its peers.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf advertise-ext-community {
                     type "boolean";
                     default "false";
                     description
                       "Enable/disable advertise the extended community "+
                       "attribute to a peer or peer group.";
                   }
                   leaf origin-as-validation {
                     when "../advertise-ext-community='true' and ../../../../pee"+
                          "r-establish-mode='static' and ../../../../bgp:type='i"+
                          "bgp'";
                     type "boolean";
                     default "false";
                     description
                       "Enable/disable the BGP peer origin validation.";
                   }
                   leaf discard-ext-community {
                     type "boolean";
                     default "false";
                     description
                       "Enable/disable discard the extended community attribute "+
                       "in the routing information about a specified peer.";
                   }
                   leaf allow-as-loop {
                     type "uint32" {
                       range "1..10";
                     }
                     description
                       "Allow repetitive local AS numbers. By default, "+
                       "repetitive local AS numbers are not allowed.";
                   }
                   leaf aigp {
                     when "../../../../../../../../ni:name='_public_'";
                     type "boolean";
                     default "false";
                     description
                       "Enable/disable route with AIGP attribute advertisement "+
                       "to or from a peer.";
                   }
                   leaf default-route-advertise {
                     type "boolean";
                     default "false";
                     description
                       "Enable/disable a device to advertise the default route "+
                       "to its peers. This option enables a device to send a "+
                       "default route with the device as the next hop address to"+
                       " its peers, regardless of whether there is a default "+
                       "route in the local routing table.";
                   }
                   choice default-route-advertise-policy-type {
                     description
                       "Set default route advertise-policy.";
                     case rtp-ref {
                       description
                         "The default-route-advertise-policy.";
                       leaf default-route-advertise-policy {
                         when "../default-route-advertise='true'";
                         type "leafref" {
                           path "/rtp:routing-policy/rtp:policy-definitions/rtp:"+
                                "policy-definition/rtp:name";
                         }
                         description
                           "Specify the name of a used policy.";
                       }
                     }
                     case xpl-ref {
                       description
                         "The default-route-advertise-filter.";
                       container default-route-advertise-filter {
                         when "../default-route-advertise='true'";
                         description
                           "Configure the route-filter for default route "+
                           "advertise.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                   leaf default-route-match-mode {
                     when "../default-route-advertise='true'";
                     type "cra-match-mode";
                     default "null";
                     description
                       "Configure the matching mode of default route advertiseme"+
                       "nt, which can be disabling of route advertisement "+
                       "conditions, enabling of all route advertisement "+
                       "conditions, and enabling of part route advertisement "+
                       "conditions. Enabling of all route advertisement "+
                       "conditions indicates that a default route can be "+
                       "advertised only when it matches all the conditions. "+
                       "Enabling of part route advertisement conditions "+
                       "indicates that a default route can be advertised only "+
                       "when it matches one condition.";
                   }
                   leaf add-path-mode {
                     when "../../../../../../../../ni:name='_public_' and "+
                          "../../../../bgp:type='ibgp'";
                     type "add-path-cap-type";
                     default "null";
                     description
                       "Enable Add-Path route advertisement to a peer.";
                   }
                   leaf import-ipv6-prefix {
                     type "leafref" {
                       path "/rtp:routing-policy/rtp:ipv6-prefix-filters/rtp:ipv"+
                            "6-prefix-filter/rtp:name";
                     }
                     description
                       "Specify the IPv6 filtering policy applied to the routes "+
                       "received from a specified peer. By default, no such "+
                       "policy is specified.";
                   }
                   leaf export-ipv6-prefix {
                     type "leafref" {
                       path "/rtp:routing-policy/rtp:ipv6-prefix-filters/rtp:ipv"+
                            "6-prefix-filter/rtp:name";
                     }
                     description
                       "Specify the IPv6 filtering policy applied to the routes "+
                       "to be advertised to a specified peer. By default, no "+
                       "such policy is specified.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl6-name-or-num {
                     type "leafref" {
                       path "/acl:acl/acl:group6s/acl:group6/acl:identity";
                     }
                     description
                       "Specifies the name of the import ACL6 policy.";
                   }
                   leaf export-acl6-name-or-num {
                     type "leafref" {
                       path "/acl:acl/acl:group6s/acl:group6/acl:identity";
                     }
                     description
                       "Specifies the name of the export ACL6 policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf add-path-number {
                     when "../../../../../../../../ni:name='_public_' and "+
                          "../../../../bgp:type='ibgp'";
                     type "uint8" {
                       range "2..64";
                     }
                     description
                       "Number of Add-Path routes that can be advertised to a "+
                       "peer.";
                   }
                   leaf substitute-as-enable {
                     when "../../../../bgp:type='ebgp'";
                     type "boolean";
                     default "false";
                     description
                       "Enable/disable replace the AS number of a specified peer"+
                       " in the AS_Path attribute with the local AS number. On a"+
                       " PE where AS number replacement is enabled, if an AS "+
                       "number in the AS_Path attribute of a route is same as "+
                       "that of the CE to which the PE advertises the route, the"+
                       " PE replaces the AS number with its own AS number before"+
                       " advertising the route.";
                   }
                   leaf soo {
                     when "../../../../../../../../ni:name!='_public_'";
                     type "string" {
                       length "3..21";
                     }
                     description
                       "Configure the Site-of-Origin (SoO) extended community "+
                       "attribute. This attribute can be expressed in the "+
                       "following formats: X.X.X.X:number<0-65535>, number<0-655"+
                       "35>:number<0-4294967295>, or number<0-65535>.number<0-65"+
                       "535>:number<0-65535> or <65536-4294967295>:<0-65535>. "+
                       "0:0 or 0.0:0 is not supported. \nTwo CEs are in the same"+
                       " site and can advertise routes to each other, and they "+
                       "are connected to a VPN through PEs. If the local routes "+
                       "of a CE are advertised to the other CE over the VPN, a "+
                       "routing loop may occur. \nThe SoO feature can prevent a "+
                       "route advertised by a site from being sent back to the "+
                       "site, preventing routing loops. After SoO is enabled and"+
                       " a PE receives a route from a CE, the specified SoO "+
                       "attribute will be added to the route. Before advertising"+
                       " the route to the other CE, the PE checks the SoO "+
                       "attribute. If the SoO attribute is the same as the "+
                       "locally configured SoO attribute, the PE does not "+
                       "advertise the route, preventing routing loops.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   leaf advertise-best-external {
                     when "../../../../../../../../ni:name='_public_' and "+
                          "../../../../bgp:type='ibgp'";
                     type "boolean";
                     must "../reflect-client='false' or ../advertise-best-extern"+
                          "al='false'";
                     must "../add-path-mode='null' or not(../add-path-mode) or "+
                          "../advertise-best-external='false'";
                     must "not(../add-path-number and ../advertise-best-external"+
                          "='true')";
                     default "false";
                     description
                       "Enable/disable the device to advertise Best External "+
                       "routes to peers.";
                   }
                   leaf load-balancing-enable {
                     type "boolean";
                     default "false";
                     description
                       "Enable/disable a neighbour to participate in load "+
                       "balancing.";
                   }
                   choice load-balancing-ignore-as-type {
                     description
                       "Set load balancing as path type.";
                     case as-attribute {
                       description
                         "Ignore the as-path attribute.";
                       leaf load-balancing-as-path-ignore {
                         when "../load-balancing-enable='true'";
                         type "empty";
                         description
                           "Configure BGP to ignore the AS_Path attribute when "+
                           "selecting the equal route. After as-path-neglect is "+
                           "selected, BGP does not compare the AS_Path length.";
                       }
                     }
                     case same-length-as-attribute {
                       description
                         "Ignore comparison of as-path attributes with the same "+
                         "length.";
                       leaf load-balancing-as-path-relax {
                         when "../load-balancing-enable='true'";
                         type "empty";
                         description
                           "Configure BGP to ignore comparison of AS_Path "+
                           "attributes with the same length when selecting the "+
                           "equal route. After as-path-neglect is selected, BGP "+
                           "does not compare the AS_Path length.";
                       }
                     }
                   }
                   leaf prefix-sid {
                     when "../../../../../../../../ni:name='_public_'";
                     type "boolean";
                     default "false";
                     description
                       "Enable/disable a device to exchange IPv4 prefix SIDs "+
                       "with a specified IPv6 peer group.";
                   }
                   choice prefix-sid-packet {
                     description
                       "Prefix-sid packet method.";
                     case sid-type5 {
                       description
                         "Packet by type5.";
                       leaf advertise-srv6-locator {
                         when "../prefix-sid='true'";
                         type "empty";
                         description
                           "Advertise SRv6 locators.";
                       }
                     }
                   }
                   leaf advertise-large-community {
                     type "boolean";
                     default "false";
                     description
                       "Enable/disable large-community attribute advertisement. "+
                       "The Link-state address family and the RPD address family"+
                       " do not support this element.";
                   }
                   leaf update-group-independent {
                     type "boolean";
                     default "false";
                     description
                       "Enable/disable the peer which can reside in an "+
                       "independent peer group.";
                   }
                   container option {
                     description
                       "Configure IPv6 unicast group common options.";
                     leaf export-origin-as-validation {
                       type "peer-attr-enable-type";
                       default "disable";
                       description
                         "Enable/disable the function ebgp group advertising "+
                         "dependent roa validation, route is advtised roa reslut"+
                         " is valid.";
                     }
                     leaf include-not-found {
                       when "../export-origin-as-validation='enable'";
                       type "boolean";
                       default "false";
                       description
                         "Enable/disable the include-not-found attribute of the "+
                         "ROA validation.";
                     }
                     leaf external {
                       when "../include-not-found='true'";
                       type "boolean";
                       default "false";
                       description
                         "Enable/disable ROA export validation to advertise only"+
                         " external not found routes.";
                     }
                   }
                   container default-route-match-conditions {
                     when "../default-route-match-mode and ../default-route-matc"+
                          "h-mode!='null'";
                     description
                       "List of condition matching to filter the default routes "+
                       "to be advertised. The value takes effect only when the "+
                       "default route matching mode is not null and more than "+
                       "one IPv6 default route matching condition lists are "+
                       "configured.";
                     list default-route-match-condition {
                       key "address mask";
                       min-elements "1";
                       max-elements "4";
                       description
                         "Configure the matching condition for default route "+
                         "advertisement.";
                       leaf address {
                         type "inet:ipv6-address-no-zone";
                         description
                           "Configure a IPv6-prefix that is used to match "+
                           "default routes.";
                       }
                       leaf mask {
                         type "uint32" {
                           range "0..128";
                         }
                         description
                           "Configure a mask that is used to match default "+
                           "routes.";
                       }
                     }
                   }
                   container route-limit {
                     description
                       "Configure parameters of routes limited from this peer.";
                     leaf number {
                       type "uint32" {
                         range "1..4294967295";
                       }
                       description
                         "Configure the maximum number of routes that can be "+
                         "accepted from a peer.";
                     }
                     leaf accept-prefix {
                       when "../number";
                       type "boolean";
                       default "false";
                       description
                         "Enable/disable the device to keep receiving routes and"+
                         " the routes are valid if the maximum number of routes "+
                         "allowed have been received and the alert-only "+
                         "parameter is specified.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "boolean";
                       default "false";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'true'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                   }
                   container advertise-dependent-filter6 {
                     presence "Enable peer group advertising dependent filter.";
                     description
                       "Configure peer group advertising dependent filter.";
                     leaf dependent-filter6 {
                       type "leafref" {
                         path "/rtp:routing-policy/rtp:ipv6-prefix-lists/rtp:ipv"+
                              "6-prefix-list/rtp:name";
                       }
                       mandatory "true";
                       description
                         "Specify a dependent route-filter name.";
                     }
                     leaf dependent-filter-type {
                       type "bgp:dependent-prefix-filter-type";
                       mandatory "true";
                       description
                         "Specify a dependent route-filter mode.";
                     }
                     leaf condition-filter6 {
                       type "leafref" {
                         path "/rtp:routing-policy/rtp:ipv6-prefix-lists/rtp:ipv"+
                              "6-prefix-list/rtp:name";
                       }
                       description
                         "Specify a condition route-filter name.";
                     }
                   }
                   container route-server {
                     description
                       "Configure the route server function on a device and "+
                       "specifies an EBGP peer as its client.";
                     leaf route-server-client {
                       when "../../../../../bgp:type='ebgp' and ../../../../../p"+
                            "eer-establish-mode='static'";
                       type "empty";
                       must "not(../route-server-client) or (not(/bgp:bgp/bgp:ba"+
                            "se-process/bgp:confederation/bgp:id) and (/bgp:bgp/"+
                            "bgp:base-process/bgp:confederation/bgp:nonstanded ="+
                            " 'false'))";
                       must "not(../route-server-client) or (../../label-route-c"+
                            "apability = 'false')";
                       must "not(../route-server-client) or (../../prefix-sid = "+
                            "'false')";
                       description
                         "Enable/disable the route server function on a device "+
                         "and specifies an EBGP peer as its client.";
                     }
                   }
                   container link-bandwidth {
                     when "../../../../../../../../ni:name='_public_'";
                     description
                       "Configure link bandwidth attribute.";
                     leaf advertise {
                       when "../../../../../bgp:type='ebgp'";
                       type "peer-attr-enable-type";
                       default "disable";
                       description
                         "Enable/disable advertise the link bandwidth attribute "+
                         "to an EBGP peer.";
                     }
                     leaf transitive {
                       type "peer-attr-enable-type";
                       default "disable";
                       description
                         "Enable/disable transitive the link bandwidth "+
                         "attribute.";
                     }
                     leaf generate {
                       when "../../../../../bgp:type='ebgp'";
                       type "peer-attr-enable-type";
                       default "disable";
                       description
                         "Enable/disable generate the link bandwidth attribute "+
                         "to an EBGP peer.";
                     }
                   }
                 }
                 container ipv4-vpn {
                   when "../type = 'ipv4vpn'";
                   description
                     "Configure IPv4 vpnv4 options.";
                   leaf advertise-community {
                     type "boolean";
                     default "false";
                     description
                       "Enable/disable advertise the community attribute to a "+
                       "peer or a peer group.";
                   }
                   leaf reflect-client {
                     when "../../../../bgp:type='ibgp'";
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf nexthop-configure {
                     type "nexthop-configuration-type";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf ignore-bit-error {
                     when "../export-policy or ../export-filter";
                     type "boolean";
                     default "false";
                     description
                       "Enable/disable the peer to ignore bit error detection "+
                       "results.";
                   }
                   leaf allow-as-loop {
                     type "uint32" {
                       range "1..10";
                     }
                     description
                       "Allow repetitive local AS numbers. By default, "+
                       "repetitive local AS numbers are not allowed.";
                   }
                   leaf aigp {
                     type "boolean";
                     default "false";
                     description
                       "Enable/disable route with AIGP attribute advertisement "+
                       "to or from a peer.";
                   }
                   leaf add-path-mode {
                     when "../../../../bgp:type='ibgp'";
                     type "add-path-cap-type";
                     default "null";
                     description
                       "Enable Add-Path route advertisement to a peer.";
                   }
                   leaf import-ip-prefix {
                     type "leafref" {
                       path "/rtp:routing-policy/rtp:ipv4-prefix-filters/rtp:ipv"+
                            "4-prefix-filter/rtp:name";
                     }
                     description
                       "Specify the IPv4 filtering policy applied to the routes "+
                       "received from a specified peer. By default, no such "+
                       "policy is specified.";
                   }
                   leaf export-ip-prefix {
                     type "leafref" {
                       path "/rtp:routing-policy/rtp:ipv4-prefix-filters/rtp:ipv"+
                            "4-prefix-filter/rtp:name";
                     }
                     description
                       "Specify the IPv4 filtering policy applied to the routes "+
                       "to be advertised to a specified peer. By default, no "+
                       "such policy is specified.";
                   }
                   leaf reoriginate-route-enable {
                     type "boolean";
                     default "false";
                     description
                       "Enable/disable route regeneration.";
                   }
                   leaf reoriginate-ip-enable {
                     type "boolean";
                     default "false";
                     description
                       "Enable/disable IP route regeneration and advertisement.";
                   }
                   leaf reoriginate-mac-ip-enable {
                     type "boolean";
                     default "false";
                     description
                       "Enable/disable MAC-IP route regeneration and advertiseme"+
                       "nt.";
                   }
                   leaf reoriginate-vpnv4-route-enable {
                     type "boolean";
                     default "false";
                     description
                       "Enable/disable VPNv4 route regeneration and advertisemen"+
                       "t.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl-name-or-num {
                     type "leafref" {
                       path "/acl:acl/acl:groups/acl:group/acl:identity";
                     }
                     description
                       "Specifies the name of the import ACL policy.";
                   }
                   leaf export-acl-name-or-num {
                     type "leafref" {
                       path "/acl:acl/acl:groups/acl:group/acl:identity";
                     }
                     description
                       "Specifies the name of the export ACL policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf add-path-number {
                     when "../../../../bgp:type='ibgp'";
                     type "uint8" {
                       range "2..64";
                     }
                     description
                       "Number of Add-Path routes that can be advertised to a "+
                       "peer.";
                   }
                   leaf upe {
                     type "boolean";
                     default "false";
                     description
                       "Enable/disable the peer as an underlayer PE (UPE).";
                   }
                   leaf advertise-best-external {
                     when "../../../../bgp:type='ibgp'";
                     type "boolean";
                     must "../reflect-client='false' or ../advertise-best-extern"+
                          "al='false'";
                     must "../add-path-mode='null' or not(../add-path-mode) or "+
                          "../advertise-best-external='false'";
                     must "not(../add-path-number and ../advertise-best-external"+
                          "='true')";
                     default "false";
                     description
                       "Enable/disable the device to advertise Best External "+
                       "routes to peers.";
                   }
                   leaf advertise-large-community {
                     type "boolean";
                     default "false";
                     description
                       "Enable/disable large-community attribute advertisement. "+
                       "The Link-state address family and the RPD address family"+
                       " do not support this element.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   leaf update-group-independent {
                     type "boolean";
                     default "false";
                     description
                       "Enable/disable the peer which can reside in an "+
                       "independent peer group.";
                   }
                   leaf origin-as-validation {
                     when "../../../../peer-establish-mode='static' and "+
                          "../../../../bgp:type='ibgp'";
                     type "boolean";
                     default "false";
                     description
                       "Enable/disable the BGP peer origin validation.";
                   }
                   leaf high-priority {
                     type "boolean";
                     default "false";
                     description
                       "Enable/disable vpn-router high priority.";
                   }
                   container default-route-originates {
                     description
                       "Configure advertised default VPNv4 routes.";
                     list default-route-originate {
                       key "vpn-name";
                       description
                         "Configure advertised default VPNv4 route.";
                       leaf vpn-name {
                         type "leafref" {
                           path "/ni:network-instance/ni:instances/ni:instance/n"+
                                "i:name";
                         }
                         must "../vpn-name!='_public_'";
                         description
                           "VPN instance name. It uniquely identifies a VPN "+
                           "instance. The name is a string of case-sensitive "+
                           "characters.";
                       }
                     }
                   }
                   container route-limit {
                     description
                       "Configure parameters of routes limited from this peer.";
                     leaf number {
                       type "uint32" {
                         range "1..4294967295";
                       }
                       description
                         "Configure the maximum number of routes that can be "+
                         "accepted from a peer.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "boolean";
                       default "false";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'true'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                   }
                 }
                 container ipv6-vpn {
                   when "../type = 'ipv6vpn'";
                   description
                     "Configure IPv6 vpn options.";
                   leaf advertise-community {
                     type "boolean";
                     default "false";
                     description
                       "Enable/disable advertise the community attribute to a "+
                       "peer or a peer group.";
                   }
                   leaf reflect-client {
                     when "../../../../bgp:type='ibgp'";
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf nexthop-configure {
                     type "nexthop-configuration-type";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf ignore-bit-error {
                     when "../export-policy or ../export-filter";
                     type "boolean";
                     default "false";
                     description
                       "Enable/disable the peer to ignore bit error detection "+
                       "results.";
                   }
                   leaf allow-as-loop {
                     type "uint32" {
                       range "1..10";
                     }
                     description
                       "Allow repetitive local AS numbers. By default, "+
                       "repetitive local AS numbers are not allowed.";
                   }
                   leaf aigp {
                     type "boolean";
                     default "false";
                     description
                       "Enable/disable route with AIGP attribute advertisement "+
                       "to or from a peer.";
                   }
                   leaf add-path-mode {
                     when "../../../../bgp:type='ibgp'";
                     type "add-path-cap-type";
                     default "null";
                     description
                       "Enable Add-Path route advertisement to a peer.";
                   }
                   leaf import-ipv6-prefix {
                     type "leafref" {
                       path "/rtp:routing-policy/rtp:ipv6-prefix-filters/rtp:ipv"+
                            "6-prefix-filter/rtp:name";
                     }
                     description
                       "Specify the IPv6 filtering policy applied to the routes "+
                       "received from a specified peer. By default, no such "+
                       "policy is specified.";
                   }
                   leaf export-ipv6-prefix {
                     type "leafref" {
                       path "/rtp:routing-policy/rtp:ipv6-prefix-filters/rtp:ipv"+
                            "6-prefix-filter/rtp:name";
                     }
                     description
                       "Specify the IPv6 filtering policy applied to the routes "+
                       "to be advertised to a specified peer. By default, no "+
                       "such policy is specified.";
                   }
                   leaf reoriginate-route-enable {
                     type "boolean";
                     default "false";
                     description
                       "Enable/disable route regeneration.";
                   }
                   leaf reoriginate-ipv6-enable {
                     type "boolean";
                     default "false";
                     description
                       "Enable/disable IP route regeneration and advertisement.";
                   }
                   leaf reoriginate-mac-ipv6-enable {
                     type "boolean";
                     default "false";
                     description
                       "Enable/disable MAC-IP route regeneration and advertiseme"+
                       "nt.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl6-name-or-num {
                     type "leafref" {
                       path "/acl:acl/acl:group6s/acl:group6/acl:identity";
                     }
                     description
                       "Specifies the name of the import ACL6 policy.";
                   }
                   leaf export-acl6-name-or-num {
                     type "leafref" {
                       path "/acl:acl/acl:group6s/acl:group6/acl:identity";
                     }
                     description
                       "Specifies the name of the export ACL6 policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf add-path-number {
                     when "../../../../bgp:type='ibgp'";
                     type "uint8" {
                       range "2..64";
                     }
                     description
                       "Number of Add-Path routes that can be advertised to a "+
                       "peer.";
                   }
                   leaf advertise-best-external {
                     when "../../../../bgp:type='ibgp'";
                     type "boolean";
                     must "../reflect-client='false' or ../advertise-best-extern"+
                          "al='false'";
                     must "../add-path-mode='null' or not(../add-path-mode) or "+
                          "../advertise-best-external='false'";
                     must "not(../add-path-number and ../advertise-best-external"+
                          "='true')";
                     default "false";
                     description
                       "Enable/disable the device to advertise Best External "+
                       "routes to peers.";
                   }
                   leaf advertise-large-community {
                     type "boolean";
                     default "false";
                     description
                       "Enable/disable large-community attribute advertisement. "+
                       "The Link-state address family and the RPD address family"+
                       " do not support this element.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   leaf update-group-independent {
                     type "boolean";
                     default "false";
                     description
                       "Enable/disable the peer which can reside in an "+
                       "independent peer group.";
                   }
                   leaf origin-as-validation {
                     when "../../../../peer-establish-mode='static'";
                     type "boolean";
                     default "false";
                     description
                       "Enable/disable the BGP peer origin validation.";
                   }
                   leaf high-priority {
                     type "boolean";
                     default "false";
                     description
                       "Enable/disable vpn-router high priority.";
                   }
                   leaf prefix-sid {
                     type "boolean";
                     default "false";
                     description
                       "Enable/disable a SID mode relay for group.";
                   }
                   choice prefix-sid-packet {
                     description
                       "Prefix-sid packet method.";
                     case sid-type5 {
                       description
                         "Packet by type5.";
                       leaf advertise-srv6-locator {
                         when "../prefix-sid='true'";
                         type "empty";
                         description
                           "Advertise SRv6 locators.";
                       }
                     }
                   }
                   container route-limit {
                     description
                       "Configure parameters of routes limited from this peer.";
                     leaf number {
                       type "uint32" {
                         range "1..4294967295";
                       }
                       description
                         "Configure the maximum number of routes that can be "+
                         "accepted from a peer.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "boolean";
                       default "false";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'true'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                   }
                 }
                 container ipv4-labeluni {
                   when "../type = 'ipv4labeluni'";
                   must "../../../../../../../l3vpn:afs/l3vpn:af[l3vpn:type='ipv"+
                        "4-unicast']";
                   description
                     "Configure IPv4 label unicast options.";
                   leaf advertise-community {
                     type "boolean";
                     default "false";
                     description
                       "Enable/disable advertise the community attribute to a "+
                       "peer or a peer group.";
                   }
                   leaf reflect-client {
                     when "../../../../bgp:type='ibgp'";
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf check-tunnel-reachable {
                     type "boolean";
                     default "false";
                     description
                       "Enable/disable tunnel reachability check.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf advertise-ext-community {
                     type "boolean";
                     default "false";
                     description
                       "Enable/disable advertise the extended community "+
                       "attribute to a peer or peer group.";
                   }
                   leaf discard-ext-community {
                     type "boolean";
                     default "false";
                     description
                       "Enable/disable discard the extended community attribute "+
                       "in the routing information about a specified peer.";
                   }
                   leaf allow-as-loop {
                     type "uint32" {
                       range "1..10";
                     }
                     description
                       "Allow repetitive local AS numbers. By default, "+
                       "repetitive local AS numbers are not allowed.";
                   }
                   leaf aigp {
                     when "../../../../../../../../ni:name='_public_'";
                     type "boolean";
                     default "false";
                     description
                       "Enable/disable route with AIGP attribute advertisement "+
                       "to or from a peer.";
                   }
                   leaf add-path-mode {
                     when "../../../../../../../../ni:name='_public_' and "+
                          "../../../../bgp:type='ibgp'";
                     type "add-path-cap-type";
                     default "null";
                     description
                       "Enable Add-Path route advertisement to a peer.";
                   }
                   leaf import-ip-prefix {
                     type "leafref" {
                       path "/rtp:routing-policy/rtp:ipv4-prefix-filters/rtp:ipv"+
                            "4-prefix-filter/rtp:name";
                     }
                     description
                       "Specify the IPv4 filtering policy applied to the routes "+
                       "received from a specified peer. By default, no such "+
                       "policy is specified.";
                   }
                   leaf export-ip-prefix {
                     type "leafref" {
                       path "/rtp:routing-policy/rtp:ipv4-prefix-filters/rtp:ipv"+
                            "4-prefix-filter/rtp:name";
                     }
                     description
                       "Specify the IPv4 filtering policy applied to the routes "+
                       "to be advertised to a specified peer. By default, no "+
                       "such policy is specified.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl-name-or-num {
                     type "leafref" {
                       path "/acl:acl/acl:groups/acl:group/acl:identity";
                     }
                     description
                       "Specifies the name of the import ACL policy.";
                   }
                   leaf export-acl-name-or-num {
                     type "leafref" {
                       path "/acl:acl/acl:groups/acl:group/acl:identity";
                     }
                     description
                       "Specifies the name of the export ACL policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf nexthop-configure {
                     type "nexthop-configuration-type";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf exp-mode {
                     when "../../../../../../../../ni:name!='_public_'";
                     type "exp-mode-type";
                     default "null";
                     description
                       "Specify the ASs in which a BGP label can inherit the QoS"+
                       " priority carried in the outer label of public tunnel in"+
                       " the Core AS and the ASs in which the priorities of BGP "+
                       "LSPs must be restored before the LSPs are advertised to "+
                       "a non-core AS.";
                   }
                   leaf add-path-number {
                     when "../../../../../../../../ni:name='_public_' and "+
                          "../../../../bgp:type='ibgp'";
                     type "uint8" {
                       range "2..64";
                     }
                     description
                       "Number of Add-Path routes that can be advertised to a "+
                       "peer.";
                   }
                   leaf substitute-as-enable {
                     when "../../../../bgp:type='ebgp'";
                     type "boolean";
                     default "false";
                     description
                       "Enable/disable replace the AS number of a specified peer"+
                       " in the AS_Path attribute with the local AS number. On a"+
                       " PE where AS number replacement is enabled, if an AS "+
                       "number in the AS_Path attribute of a route is same as "+
                       "that of the CE to which the PE advertises the route, the"+
                       " PE replaces the AS number with its own AS number before"+
                       " advertising the route.";
                   }
                   leaf soo {
                     when "../../../../../../../../ni:name!='_public_'";
                     type "string" {
                       length "3..21";
                     }
                     description
                       "Configure the Site-of-Origin (SoO) extended community "+
                       "attribute. This attribute can be expressed in the "+
                       "following formats: X.X.X.X:number<0-65535>, number<0-655"+
                       "35>:number<0-4294967295>, or number<0-65535>.number<0-65"+
                       "535>:number<0-65535> or <65536-4294967295>:<0-65535>. "+
                       "0:0 or 0.0:0 is not supported. \nTwo CEs are in the same"+
                       " site and can advertise routes to each other, and they "+
                       "are connected to a VPN through PEs. If the local routes "+
                       "of a CE are advertised to the other CE over the VPN, a "+
                       "routing loop may occur. \nThe SoO feature can prevent a "+
                       "route advertised by a site from being sent back to the "+
                       "site, preventing routing loops. After SoO is enabled and"+
                       " a PE receives a route from a CE, the specified SoO "+
                       "attribute will be added to the route. Before advertising"+
                       " the route to the other CE, the PE checks the SoO "+
                       "attribute. If the SoO attribute is the same as the "+
                       "locally configured SoO attribute, the PE does not "+
                       "advertise the route, preventing routing loops.";
                   }
                   leaf advertise-best-external {
                     when "../../../../../../../../ni:name='_public_' and "+
                          "../../../../bgp:type='ibgp'";
                     type "boolean";
                     must "../reflect-client='false' or ../advertise-best-extern"+
                          "al='false'";
                     must "../add-path-mode='null' or ../advertise-best-external"+
                          "='false'";
                     must "not(../add-path-number and ../advertise-best-external"+
                          "='true')";
                     default "false";
                     description
                       "Enable/disable the device to advertise Best External "+
                       "routes to peers.";
                   }
                   leaf load-balancing-enable {
                     when "../../../../../../../../ni:name='_public_'";
                     type "boolean";
                     default "false";
                     description
                       "Enable/disable a neighbour to participate in load "+
                       "balancing.";
                   }
                   leaf prefix-sid {
                     when "../../../../../../../../ni:name='_public_'";
                     type "boolean";
                     default "false";
                     description
                       "Enable/disable a device to exchange IPv4 prefix SIDs "+
                       "with a specified IPv6 peer group.";
                   }
                   choice load-balancing-ignore-as-type {
                     description
                       "Set load balancing as path type.";
                     case as-attribute {
                       description
                         "Ignore the as-path attribute.";
                       leaf load-balancing-as-path-ignore {
                         when "../load-balancing-enable='true'";
                         type "empty";
                         description
                           "Configure BGP to ignore the AS_Path attribute when "+
                           "selecting the equal route. After as-path-neglect is "+
                           "selected, BGP does not compare the AS_Path length.";
                       }
                     }
                     case same-length-as-attribute {
                       description
                         "Ignore comparison of as-path attributes with the same "+
                         "length.";
                       leaf load-balancing-as-path-relax {
                         when "../load-balancing-enable='true'";
                         type "empty";
                         description
                           "Configure BGP to ignore comparison of AS_Path "+
                           "attributes with the same length when selecting the "+
                           "equal route. After as-path-neglect is selected, BGP "+
                           "does not compare the AS_Path length.";
                       }
                     }
                   }
                   leaf advertise-large-community {
                     type "boolean";
                     default "false";
                     description
                       "Enable/disable large-community attribute advertisement. "+
                       "The Link-state address family and the RPD address family"+
                       " do not support this element.";
                   }
                   leaf update-group-independent {
                     type "boolean";
                     default "false";
                     description
                       "Enable/disable the peer which can reside in an "+
                       "independent peer group.";
                   }
                   container route-limit {
                     description
                       "Configure parameters of routes limited from this peer.";
                     leaf number {
                       type "uint32" {
                         range "1..4294967295";
                       }
                       description
                         "Configure the maximum number of routes that can be "+
                         "accepted from a peer.";
                     }
                     leaf accept-prefix {
                       when "../number";
                       type "boolean";
                       default "false";
                       description
                         "Enable/disable the device to keep receiving routes and"+
                         " the routes are valid if the maximum number of routes "+
                         "allowed have been received and the alert-only "+
                         "parameter is specified.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "boolean";
                       default "false";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'true'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                   }
                   container entropy-label-parameter {
                     when "../../../../../../../../ni:name='_public_'";
                     description
                       "Configure information about entropy label parameter in a"+
                       " peer group.";
                     leaf advertise-entropy-label {
                       type "boolean";
                       default "false";
                       description
                         "Enable/disable the capability of advertising entropy "+
                         "labels.";
                     }
                     leaf padding {
                       when "../advertise-entropy-label='true'";
                       type "string" {
                         length "1..32";
                         pattern "(([0-9A-F])*)";
                       }
                       description
                         "Padding format. The value is a hexadecimal string "+
                         "containing 1 to 32 characters (16 hexadecimal "+
                         "numbers). It cannot contain spaces, and can only "+
                         "contain uppercase letters (A to F) and digits (0 to "+
                         "9), and the length must be an even number.";
                     }
                     leaf attribute-type {
                       when "../advertise-entropy-label='true'";
                       type "entropy-label-attribute-type";
                       mandatory "true";
                       description
                         "The attribute-type of advertising entropy labels.";
                     }
                     leaf entropy-label {
                       type "boolean";
                       default "false";
                       description
                         "Enable/disable the function of delivering the entropy "+
                         "label capability to the forwarding plane.";
                     }
                   }
                 }
                 container ipv4-multicast {
                   when "../type='ipv4multi'";
                   description
                     "Configure IPv4 multicast options.";
                   leaf default-route-advertise {
                     type "boolean";
                     default "false";
                     description
                       "Enable/disable a device to advertise the default route "+
                       "to its peers. This option enables a device to send a "+
                       "default route with the device as the next hop address to"+
                       " its peers, regardless of whether there is a default "+
                       "route in the local routing table.";
                   }
                   choice default-route-advertise-policy-type {
                     description
                       "Set default route advertise-policy.";
                     case rtp-ref {
                       description
                         "The default-route-advertise-policy.";
                       leaf default-route-advertise-policy {
                         when "../default-route-advertise='true'";
                         type "leafref" {
                           path "/rtp:routing-policy/rtp:policy-definitions/rtp:"+
                                "policy-definition/rtp:name";
                         }
                         description
                           "Specify the name of a used policy.";
                       }
                     }
                     case xpl-ref {
                       description
                         "The default-route-advertise-filter.";
                       container default-route-advertise-filter {
                         when "../default-route-advertise='true'";
                         description
                           "Configure the route-filter for default route "+
                           "advertise.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                   leaf import-ip-prefix {
                     type "leafref" {
                       path "/rtp:routing-policy/rtp:ipv4-prefix-filters/rtp:ipv"+
                            "4-prefix-filter/rtp:name";
                     }
                     description
                       "Specify the IPv4 filtering policy applied to the routes "+
                       "received from a specified peer. By default, no such "+
                       "policy is specified.";
                   }
                   leaf export-ip-prefix {
                     type "leafref" {
                       path "/rtp:routing-policy/rtp:ipv4-prefix-filters/rtp:ipv"+
                            "4-prefix-filter/rtp:name";
                     }
                     description
                       "Specify the IPv4 filtering policy applied to the routes "+
                       "to be advertised to a specified peer. By default, no "+
                       "such policy is specified.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl-name-or-num {
                     type "leafref" {
                       path "/acl:acl/acl:groups/acl:group/acl:identity";
                     }
                     description
                       "Specifies the name of the import ACL policy.";
                   }
                   leaf export-acl-name-or-num {
                     type "leafref" {
                       path "/acl:acl/acl:groups/acl:group/acl:identity";
                     }
                     description
                       "Specifies the name of the export ACL policy.";
                   }
                   leaf advertise-ext-community {
                     type "boolean";
                     default "false";
                     description
                       "Enable/disable advertise the extended community "+
                       "attribute to a peer or peer group.";
                   }
                   leaf discard-ext-community {
                     type "boolean";
                     default "false";
                     description
                       "Enable/disable discard the extended community attribute "+
                       "in the routing information about a specified peer.";
                   }
                   leaf allow-as-loop {
                     type "uint32" {
                       range "1..10";
                     }
                     description
                       "Allow repetitive local AS numbers. By default, "+
                       "repetitive local AS numbers are not allowed.";
                   }
                   leaf nexthop-configure {
                     type "nexthop-configuration-type";
                     must "../nexthop-configure='local'";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   leaf advertise-community {
                     type "boolean";
                     default "false";
                     description
                       "Enable/disable advertise the community attribute to a "+
                       "peer or a peer group.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf reflect-client {
                     when "../../../../bgp:type='ibgp'";
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf load-balancing-enable {
                     type "boolean";
                     default "false";
                     description
                       "Enable/disable a neighbour to participate in load "+
                       "balancing.";
                   }
                   choice load-balancing-ignore-as-type {
                     description
                       "Set load balancing as path type.";
                     case as-attribute {
                       description
                         "Ignore the as-path attribute.";
                       leaf load-balancing-as-path-ignore {
                         when "../load-balancing-enable='true'";
                         type "empty";
                         description
                           "Configure BGP to ignore the AS_Path attribute when "+
                           "selecting the equal route. After as-path-neglect is "+
                           "selected, BGP does not compare the AS_Path length.";
                       }
                     }
                     case same-length-as-attribute {
                       description
                         "Ignore comparison of as-path attributes with the same "+
                         "length.";
                       leaf load-balancing-as-path-relax {
                         when "../load-balancing-enable='true'";
                         type "empty";
                         description
                           "Configure BGP to ignore comparison of AS_Path "+
                           "attributes with the same length when selecting the "+
                           "equal route. After as-path-neglect is selected, BGP "+
                           "does not compare the AS_Path length.";
                       }
                     }
                   }
                   leaf advertise-large-community {
                     type "boolean";
                     default "false";
                     description
                       "Enable/disable large-community attribute advertisement. "+
                       "The Link-state address family and the RPD address family"+
                       " do not support this element.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf update-group-independent {
                     type "boolean";
                     default "false";
                     description
                       "Enable/disable the peer which can reside in an "+
                       "independent peer group.";
                   }
                   container route-limit {
                     description
                       "Configure parameters of routes limited from this peer.";
                     leaf number {
                       type "uint32" {
                         range "1..4294967295";
                       }
                       description
                         "Configure the maximum number of routes that can be "+
                         "accepted from a peer.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "boolean";
                       default "false";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'true'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                   }
                 }
               }
             }
           }
         }
         container peers {
           description
             "List of BGP peers.";
           list peer {
             key "address";
             description
               "Configure a single BGP peer.";
             leaf address {
               type "inet:ip-address-no-zone";
               description
                 "Connection address of a peer, which can be an IPv4 or IPv6 "+
                 "address.";
             }
             leaf remote-as {
               type "as-number-validate";
               mandatory "true";
               description
                 "AS number of a peer, which must be selected or group name when"+
                 " creating, and which can be in either two-byte format or "+
                 "four-byte format:\nThe two-byte format is X. X is an integer "+
                 "ranging from 1 to 65535.\nThe four-byte format is X.Y and X. "+
                 "When the format is X.Y, X and Y are both integers, with the "+
                 "value of X ranging from 1 to 65535, and the value of Y ranging"+
                 " from 0 to 65535; when the format is X, X is an interger, with"+
                 " the value of X ranging from 1 to 4294967295.\nThe object "+
                 "cannot be modified.";
               ext:operation-exclude "update" {
                 description
                   "The node cannot be modified, when node is already configured"+
                   ".";
               }
             }
             leaf group-name {
               type "leafref" {
                 path "../../../peer-groups/peer-group/name";
               }
               must "../../../peer-groups/peer-group[name = current()]/peer-esta"+
                    "blish-mode = 'static'";
               description
                 "Specify the name of a peer group that BGP peers need to join. "+
                 "That must be selected group name or AS when creating, and the "+
                 "value is a string, spaces not supported. By default, BGP peers"+
                 " join no peer group. BGP peers distinguish the peer group type"+
                 " when joining a peer group. IBGP peers cannot join an EBGP "+
                 "peer group. BGP peers will be deleted when they leave a peer "+
                 "group. The object cannot be modified.";
               ext:operation-exclude "update" {
                 description
                   "The node cannot be modified, when the peer already belongs "+
                   "to a peer-group.";
               }
             }
             leaf local-if-name {
               type "leafref" {
                 path "/ifm:ifm/ifm:interfaces/ifm:interface/ifm:name";
               }
               description
                 "Name of a source interface that sends BGP packets. By default,"+
                 " the outbound interface of a BGP packet serves as the source "+
                 "interface of a BGP packet. To ensure that a router can send "+
                 "BGP packets when a physical interface fails, you can configure"+
                 " the source interface that sends BGP packets as a loopback "+
                 "interface. When using the loopback interface as the source "+
                 "interface, note the following points: 1. The address of the "+
                 "loopback interface of the BGP peer must be reachable. 2. For "+
                 "an EBGP connection, configure the maximum number of hops and "+
                 "allow EBGP peer relationships to be established in indirect "+
                 "mode.";
             }
             leaf local-if-address {
               type "inet:ip-address-no-zone";
               description
                 "Name of a source interface that sends BGP packets. By default,"+
                 " the outbound interface of a BGP packet serves as the source "+
                 "interface of a BGP packet. To ensure that a router can send "+
                 "BGP packets when a physical interface fails, you can configure"+
                 " the source interface that sends BGP packets as a loopback "+
                 "interface. When using the loopback interface as the source "+
                 "interface, note the following points:\n1. The address of the "+
                 "loopback interface of the BGP peer must be reachable.\n2. For "+
                 "an EBGP connection, configure the maximum number of hops and "+
                 "allow EBGP peer relationships to be established in indirect "+
                 "mode.";
             }
             leaf password-type {
               type "bgp:password-type";
               must "not((../password-type and ../password-type!='null') and "+
                    "(../key-chain-name or ../tcp-ao-name))";
               must "(not(../password-type and ../password-type!='null') and "+
                    "not(../password-text)) or (../password-type and ../password"+
                    "-type!='null' and ../password-text)";
               default "null";
               description
                 "Enable BGP peers to establish a TCP connection and perform the"+
                 " Message Digest 5 (MD5) authentication for BGP messages. "+
                 "Plaintexts and ciphertexts are supported.";
             }
             leaf password-text {
               when "../password-type and ../password-type!='null'";
               type "pub-type:password-extend";
               mandatory "true";
               description
                 "Enable BGP peers to establish a TCP connection and perform the"+
                 " Message Digest 5 (MD5) authentication for BGP messages. The "+
                 "character string in a password identifies the contents of the "+
                 "password, spaces not supported. The TCP connection can be "+
                 "established only when the same MD5 authentication password is "+
                 "set on both ends. If a plaintext is used, the maximum password"+
                 " length is 255. If a ciphertext is used, the maximum password "+
                 "length is 432. If the length is set to 0, no password is set.";
             }
             leaf key-chain-name {
               type "string" {
                 length "1..47";
                 pattern "[^A-Z]+";
               }
               must "not(../password-type!='null' or ../tcp-ao-name)";
               description
                 "Specify the Keychain authentication name used when BGP peers "+
                 "establish a TCP connection. The value is a string, spaces not "+
                 "supported. By default, the Keychain authentication is not "+
                 "configured. Keychain authentication mode and password "+
                 "authentication mode are mutually exclusive. Configuring "+
                 "Keychain authentication can enhance the security of the TCP "+
                 "connections between BGP peers. Keychain authentication using "+
                 "the same encryption algorithm and password must be configured "+
                 "on the two ends of BGP peers to establish a TCP connection and"+
                 " exchange BGP packets. Before configuring BGP Keychain "+
                 "authentication, you need to configure Keychain according to "+
                 "keychain name. Otherwise, the TCP connections between the BGP "+
                 "peers cannot be established.";
               ext:case-sensitivity "lower-only";
             }
             leaf tcp-ao-disable {
               type "empty";
               description
                 "Disable the TCP-AO authentication for establishing the TCP "+
                 "connection between BGP peers.";
             }
             leaf tcp-ao-name {
               when "not(../tcp-ao-disable)";
               type "leafref" {
                 path "/socket:socket/socket:tcp-aos/socket:tcp-ao/socket:name";
               }
               must "not(../password-type!='null' or ../key-chain-name)";
               description
                 "Specify TCP-AO authentication for establishing the TCP "+
                 "connection between BGP peers.";
             }
             leaf description {
               type "string" {
                 length "1..255";
                 pattern "([^?]*)";
               }
               description
                 "Description of a peer, which can be letters or digits. The "+
                 "description is a string, spaces supported. By default, no "+
                 "description is configured for a peer.";
             }
             leaf ebgp-max-hop {
               type "uint32" {
                 range "1..255";
               }
               must "not(../valid-ttl-hops) or (../valid-ttl-hops>=1 and "+
                    "../valid-ttl-hops<=255 and ../ebgp-max-hop=1)";
               description
                 "Maximum number of hops in an indirect EBGP connection. By "+
                 "default, EBGP connections can be established only between "+
                 "directly connected peers. The function must be configured on "+
                 "both ends. By default, value is determined by the neighbor "+
                 "type, the default value of EBGP is 1 and the default value of "+
                 "IBGP is 0.";
             }
             leaf tracking-enable {
               type "boolean";
               default "false";
               description
                 "Enable/disable peer tracking, After peer tracking is enabled, "+
                 "the device can fast detect the unreachability of a peer and "+
                 "reset the session.";
             }
             leaf tracking-delay-time {
               when "../tracking-enable='true'";
               type "uint16";
               units "s";
               default "0";
               description
                 "Specify the delay to reset the session.";
             }
             leaf conventional {
               type "boolean";
               default "false";
               description
                 "Enable/disable general router functions on peers. In "+
                 "conventional mode, not all the extended router functions, such"+
                 " as, route refreshing, GR, and multi-address family negotiatio"+
                 "n, are available. Therefore, the router of a new version can "+
                 "be compatible with the routers of earlier versions.";
             }
             leaf route-refresh {
               type "boolean";
               default "true";
               description
                 "Enable/disable BGP to advertise Refresh messages to peers.";
             }
             leaf four-byte-as {
               type "boolean";
               default "true";
               description
                 "Enable/disable BGP to advertise routes carrying 4-byte AS "+
                 "numbers to peers. After the 4-byte AS number function is "+
                 "disabled, Open packets will not carry 4-byte AS number "+
                 "capability flag, and peer ends will not know that local ends "+
                 "have the 4-byte AS number function. The 4-byte AS number "+
                 "function cannot be disabled from peers (peer groups) if a "+
                 "4-byte AS number, fake AS number, or confederation ID is "+
                 "configured on a router and the AS number of a peer is 4-byte. "+
                 "If the 4-byte AS number function is disabled in such a "+
                 "situation, BGP sessions may fail to be established, and route "+
                 "transmission may be affected.";
             }
             leaf ignore {
               type "boolean";
               default "false";
               description
                 "Enable/disable the function to tear down sessions between "+
                 "peers and clear all related routing information.";
             }
             leaf valid-ttl-hops {
               type "uint16" {
                 range "1..255";
               }
               must "not(../ebgp-max-hop and ../ebgp-max-hop>1)";
               description
                 "Enable GTSM on a peer or peer group. The valid-TTL-Value "+
                 "parameter is used to specify the number of TTL hops to be "+
                 "detected. If the value is configured as hops, the valid TTL "+
                 "range of the detected packet is [255-hops+1, 255].";
             }
             leaf connect-mode {
               type "connect-mode";
               default "null";
               description
                 "The value can be Connect-only, Listen-only, or Both. If the "+
                 "value is Connect-only, the specified peer or peer group only "+
                 "initiatively sends connection requests, instead of listening "+
                 "to connection requests. If the value is Listen-only, the "+
                 "specified peer or peer group only listens to connection "+
                 "requests, instead of initiatively sending connection requests."+
                 " If the value is Both, the specified peer or peer group not "+
                 "only initiatively sends connection requests, but also listens "+
                 "to connection requests. The default value is Both.";
             }
             leaf log-change {
               type "boolean";
               default "true";
               description
                 "Enable/disable BGP to record the session status and events of "+
                 "the specified peer or peer group.";
             }
             leaf path-mtu-auto-discovery {
               type "boolean";
               default "false";
               description
                 "Enable/disable path mtu auto discovery.";
             }
             leaf local-ifnet-disable {
               type "boolean";
               description
                 "Enable/disable MPLS local IFNET tunnel creation on a BGP IPv4 "+
                 "peer. By default, MPLS local IFNET tunnels can be created on "+
                 "an EBGP peer,but such tunnels cannot be created on an IBGP "+
                 "peer.";
               ext:dynamic-default;
             }
             leaf check-first-as {
               type "peer-cap-config-state";
               default "default";
               description
                 "Check the first AS in the AS_Path of the update messages from "+
                 "EBGP peers.";
             }
             leaf egress-engineer {
               when "../../../../../ni:name='_public_'";
               type "epe-state";
               default "default";
               description
                 "BGP Egress Peer Engineering (BGP-EPE) is enable or disable. "+
                 "The default value is default (The function is disable, If the "+
                 "neighbour joins the group, the function is Inheritance "+
                 "group).";
             }
             leaf tcp-mss {
               type "uint16" {
                 range "176..4096";
               }
               description
                 "Maximum TCP MSS value used for TCP connection establishment "+
                 "for a peer.";
             }
             leaf memory-priority {
               type "peer-memory-priority";
               default "default";
               description
                 "Set a priority that determines the disconnection order of a "+
                 "BGP peer relationship if memory overload occurs.";
             }
             leaf memory-priority-capability {
               type "memory-priority";
               config "false";
               description
                 "Priority that is used to determine the disconnection order of "+
                 "a BGP peer relationship if memory overload occurs.";
             }
             leaf oscillation-dampening {
               type "peer-attr-enable-type";
               description
                 "Enable/disable BGP to suppress the establishment of a "+
                 "specified peer relationship that flaps continuously. By "+
                 "default, the capability is enabled.";
             }
             container effect-state {
               config "false";
               description
                 "Operational state of a BGP peer. It uses the peer-specific "+
                 "configuration or inherits the configuration of its peer "+
                 "group.";
               leaf oscillation-dampening {
                 type "boolean";
                 description
                   "Whether the capability of suppressing the establishment of a"+
                   " specified peer relationship that flaps continuously is "+
                   "enabled on the BGP peer.";
               }
             }
             container fake-as-parameter {
               description
                 "Configure BGP fake-as parameters.";
               leaf fake-as {
                 type "bgp:as-number-validate";
                 description
                   "Fake AS number that is specified for a local peer. By "+
                   "default, a peer uses the actual AS number of the local "+
                   "end.\nAn AS number can be in either two-byte format or "+
                   "four-byte format:\nThe two-byte format is X. X is an integer"+
                   " ranging from 1 to 65535.\nThe four-byte format is X.Y and "+
                   "X. When the format is X.Y, X and Y are both integers, with "+
                   "the value of X ranging from 1 to 65535, and the value of Y "+
                   "ranging from 0 to 65535; when the format is X, X is an "+
                   "interger, with the value of X ranging from 1 to 4294967295.";
               }
               leaf dual-as {
                 when "../fake-as";
                 type "boolean";
                 default "false";
                 description
                   "Enable/disable the function to the remote EBGP peer can use "+
                   "the actual or fake AS number when specifying the AS number "+
                   "for a local peer. The local peer uses the fake and actual AS"+
                   " numbers to establish a BGP peer relationship with the "+
                   "remote end and identifies the AS number configured by the "+
                   "remote end through the error code (OPEN Message Error) and "+
                   "sub-error code (Bad Peer AS) of the Notification message "+
                   "from the remote end.";
               }
               leaf prepend-global-as {
                 when "../fake-as";
                 type "boolean";
                 default "false";
                 description
                   "Enable/disable the function to add the global AS number to "+
                   "the update packets to be advertised.";
               }
               leaf prepend-fake-as {
                 when "../fake-as";
                 type "boolean";
                 default "false";
                 description
                   "Enable/disable the function to add the fake AS number to "+
                   "received update packets.";
               }
             }
             container timer {
               description
                 "Configure BGP peer timer parameters.";
               leaf keep-alive-time {
                 type "uint32" {
                   range "0..21845";
                 }
                 units "s";
                 must "(../keep-alive-time != 0 and (../hold-time>=../keep-alive"+
                      "-time * 3) and ../hold-time != ../keep-alive-time ) or "+
                      "(../hold-time = 0 and ../keep-alive-time = 0)";
                 default "60";
                 description
                   "If the value of a timer changes, the BGP peer relationship "+
                   "between the routers is disconnected. This is because the "+
                   "peers need to re-negotiate the Keepalive time and hold time."+
                   " Therefore, confirm the action before you change the value "+
                   "of the timer. The Keepalive time should be at least three "+
                   "times of the hold time.";
               }
               leaf hold-time {
                 type "uint32" {
                   range "0 | 3..65535";
                 }
                 units "s";
                 must "(((../hold-time>=../keep-alive-time * 3) and ../hold-time"+
                      " != ../keep-alive-time ) or (../hold-time = 0 and "+
                      "../keep-alive-time = 0)) and ../hold-time>=../min-hold-ti"+
                      "me";
                 default "180";
                 description
                   "Hold time. When setting keepalive-time and hold-time, note "+
                   "the following:\n1. The values of keepalive-time and "+
                   "hold-time cannot both be 0. Otherwise, the BGP timer becomes"+
                   " invalid. That is, BGP does not detect link faults according"+
                   " to the timer.\n2. The value of hold-time is much greater "+
                   "than that of keepalive-time, such as, keepalive 1 and hold "+
                   "65535. If the value of hold-time is too large, BGP cannot "+
                   "detect link faults timely.\nThe priority of a timer is lower"+
                   " than that of a peer timer.\nAfter a connection is "+
                   "established between peers, the values of keepalive-time and "+
                   "hold-time are negotiated by the peers. The smaller value of "+
                   "hold-time contained in Open packets of both peers is taken "+
                   "as the value of hold-time. The smaller value of the locally "+
                   "set value of keepalive-time and one third of the value of "+
                   "hold-time is taken as the value of keepalive-time.";
               }
               leaf min-hold-time {
                 type "uint32" {
                   range "0 | 20..65535";
                 }
                 units "s";
                 must "../hold-time>=../min-hold-time";
                 default "0";
                 description
                   "The default value of zero means that the minimum hold time "+
                   "check does not take effect. If the value is changed, the new"+
                   " value takes effect since the next peer relationship "+
                   "establishment. During the peer relationship establishment, "+
                   "the local device checks the hold time of the remote end. If "+
                   "the hold time is less than the minimum hold time, the local "+
                   "device sends an error packet with error code 02 and subcode "+
                   "06, and the peer relationship fails to be established.";
               }
               leaf connect-retry-time {
                 type "uint16" {
                   range "1..65535";
                 }
                 units "s";
                 default "32";
                 description
                   "ConnectRetry interval.";
               }
             }
             container bfd-parameter {
               description
                 "Configure BFD.";
               leaf block {
                 type "boolean";
                 must "not(../block='true' and ../enable='true')";
                 default "false";
                 description
                   "Enable/disable preventing a BGP peer from inheriting the BFD"+
                   " configuration of the BGP peer group.";
               }
               leaf enable {
                 type "boolean";
                 must "not(../block='true' and ../enable='true')";
                 default "false";
                 description
                   "Enable/disable BFD.";
               }
               choice mode-type {
                 description
                   "Set bfd mode.";
                 case single {
                   description
                     "Single hop mode.";
                   leaf single-hop {
                     when "../enable='true'";
                     type "empty";
                     description
                       "The single hop mode is preferred during the BFD session "+
                       "establishment between IBGP peers.";
                   }
                   leaf compatible {
                     when "../enable='true'";
                     type "empty";
                     description
                       "Compatible.";
                   }
                 }
                 case link {
                   description
                     "The per-link-echo mode.";
                   leaf per-link-echo {
                     when "../enable='true'";
                     type "empty";
                     description
                       "The per-link one-arm-echo mode is preferred during the "+
                       "BFD session establishment between IBGP peers.";
                   }
                 }
               }
               leaf multiplier {
                 type "uint32" {
                   range "3..50";
                 }
                 default "3";
                 description
                   "Specify the detection multiplier.";
               }
               leaf min-rx-interval {
                 type "uint32" {
                   range "3..20000";
                 }
                 units "ms";
                 description
                   "Specify the minimum interval at which BFD packets are "+
                   "received. The value range and default value are controlled "+
                   "by the PAF.";
               }
               leaf min-tx-interval {
                 type "uint32" {
                   range "3..20000";
                 }
                 units "ms";
                 description
                   "Specify the minimum interval at which BFD packets are sent. "+
                   "The value range and default value are controlled by the "+
                   "PAF.";
               }
               leaf valid-ttl-hops-operation {
                 type "enumeration" {
                   enum "enable" {
                     value "1";
                     description
                       "Enable:";
                   }
                   enum "disable" {
                     value "2";
                     description
                       "Disable:";
                   }
                 }
                 description
                   "Control specify the valid TTL hops value operation.";
               }
               leaf valid-ttl-hops {
                 when "../valid-ttl-hops-operation='enable'";
                 type "uint8" {
                   range "1..255";
                 }
                 mandatory "true";
                 description
                   "Specify the valid TTL hops value.";
               }
             }
             container bfd-parameter-state {
               config "false";
               description
                 "Statistics of BFD Parameter State.";
               leaf valid-ttl-hops {
                 type "uint8" {
                   range "1..255";
                 }
                 description
                   "The valid TTL hops value.";
               }
             }
             container egress-engineer-parameter {
               when "../egress-engineer='enable'";
               description
                 "Configure BGP peer egress engineering information.";
               leaf static-label {
                 type "uint32" {
                   range "16..32783";
                 }
                 description
                   "The static label for BGP EPE. The value range and default "+
                   "value are controlled by the PAF.";
               }
               leaf label-pop {
                 when "../static-label";
                 type "boolean";
                 must "not(../relate-bfd='true' and ../label-pop='true')";
                 default "false";
                 description
                   "Enable/disable the BGP-EPE label popping function.";
               }
               leaf relate-bfd {
                 type "boolean";
                 must "not(../relate-bfd='true' and ../label-pop='true')";
                 default "false";
                 description
                   "Enable/disable association between the BGP-EPE label and BFD"+
                   " status.";
               }
               leaf peer-set-name {
                 type "leafref" {
                   path "../../../../bgp:egress-engineer-peer-sets/bgp:egress-en"+
                        "gineer-peer-set/bgp:peer-set-name";
                 }
                 description
                   "Add peer to peer set.";
               }
             }
             container graceful-restart {
               description
                 "Configure graceful restart.";
               leaf enable {
                 type "peer-comm-config-type";
                 default "default";
                 description
                   "Enable/disable graceful restart capability.";
               }
               leaf time-wait-for-rib {
                 type "uint32" {
                   range "3..3000";
                 }
                 units "s";
                 description
                   "Period of waiting for the End-of-RIB flag. The value is an "+
                   "integer. When a BGP session is established or re-established"+
                   ", the router enabled with GR should receive the End-of-RIB "+
                   "flag in this period. If the router does not receive the "+
                   "End-of-RIB flag in this period, ensure that the router can "+
                   "exit from the GR process.";
               }
               leaf restart-time {
                 type "uint16" {
                   range "3..3600";
                 }
                 units "s";
                 description
                   "Specifies the maximum time during which a peer waits for a "+
                   "BGP session reestablishment.";
               }
               leaf effect-restart-time {
                 type "uint16" {
                   range "3..3600";
                 }
                 units "s";
                 config "false";
                 description
                   "The maximum time during which a peer waits for a BGP session"+
                   " reestablishment.";
               }
               leaf effect-time-wait-for-rib {
                 type "uint32" {
                   range "3..3000";
                 }
                 units "s";
                 config "false";
                 description
                   "Period of waiting for the End-of-RIB flag.";
               }
               leaf effect-enable {
                 type "boolean";
                 config "false";
                 description
                   "Whether enable/disable graceful restart capability.";
               }
               leaf peer-reset {
                 type "peer-comm-config-type";
                 default "default";
                 description
                   "Enable/disable reseting BGP peer graceful.";
               }
               leaf effect-peer-reset {
                 type "boolean";
                 config "false";
                 description
                   "Whether enable/disable reseting BGP peer graceful.";
               }
             }
             container local-graceful-restart {
               description
                 "Configure local graceful restart.";
               leaf enable {
                 type "peer-comm-config-type";
                 default "default";
                 description
                   "Enable/disable graceful restart capability.";
               }
               leaf time-wait-for-rib {
                 type "uint32" {
                   range "3..3000";
                 }
                 units "s";
                 description
                   "Period of waiting for the End-of-RIB flag. The value is an "+
                   "integer. When a BGP session is established or re-established"+
                   ", the router enabled with GR should receive the End-of-RIB "+
                   "flag in this period. If the router does not receive the "+
                   "End-of-RIB flag in this period, ensure that the router can "+
                   "exit from the GR process.";
               }
               leaf restart-time {
                 type "uint16" {
                   range "3..3600";
                 }
                 units "s";
                 description
                   "Specifies the maximum time during which a peer waits for a "+
                   "BGP session reestablishment.";
               }
               leaf effect-restart-time {
                 type "uint16" {
                   range "3..3600";
                 }
                 units "s";
                 config "false";
                 description
                   "The maximum time during which a peer waits for a BGP session"+
                   " reestablishment.";
               }
               leaf effect-time-wait-for-rib {
                 type "uint32" {
                   range "3..3000";
                 }
                 units "s";
                 config "false";
                 description
                   "Period of waiting for the End-of-RIB flag.";
               }
               leaf effect-enable {
                 type "boolean";
                 config "false";
                 description
                   "Whether enable/disable graceful restart capability.";
               }
             }
             container ssl-policy {
               when "../../../../../ni:name='_public_'";
               description
                 "Configure SSL policy for BGP peer.";
               leaf enable {
                 type "peer-attr-enable-type";
                 description
                   "Enable/disable SSL policy.";
               }
               leaf name {
                 when "../enable = 'enable'";
                 type "leafref" {
                   path "/ssl:ssl/ssl:ssl-policys/ssl:ssl-policy/ssl:policy-name"+
                        "";
                 }
                 mandatory "true";
                 description
                   "SSL policy name.";
               }
               leaf role {
                 type "peer-ssl-role-type";
                 must "(.='client' and ../../connect-mode != 'listen-only') or "+
                      "(.='server' and ../../connect-mode != 'connect-only') or "+
                      "(.= 'disable')";
                 description
                   "Configure a peer as an SSL client or server.";
                 ext:operation-exclude "update" {
                   description
                     "The node cannot be modified. You need to disable or delete"+
                     " the node first.";
                 }
               }
               leaf server-certificate {
                 type "peer-attr-enable-type";
                 must "(../role = 'server') or (../role = 'disable') or (../role"+
                      " = 'client' and ../server-certificate != 'enable') or "+
                      "(not(../role) and not(../../bgp:group-name)) or "+
                      "(not(../role) and ../../bgp:group-name and  (../../../../"+
                      "bgp:peer-groups/bgp:peer-group[bgp:name=current()/../../b"+
                      "gp:group-name]/bgp:ssl-policy/bgp:role = 'server' or "+
                      "not(../../../../bgp:peer-groups/bgp:peer-group[bgp:name=c"+
                      "urrent()/../../bgp:group-name]/bgp:ssl-policy/bgp:role)))"+
                      " or (not(../role) and ../../bgp:group-name and  "+
                      "../../../../bgp:peer-groups/bgp:peer-group[bgp:name=curre"+
                      "nt()/../../bgp:group-name]/bgp:ssl-policy/bgp:role = "+
                      "'client' and ../server-certificate != 'enable')";
                 description
                   "Enable/disable SSL/TLS authentication on an SSL server.";
               }
             }
             container afs {
               description
                 "List of peers in a specified address family.";
               list af {
                 key "type";
                 description
                   "Configure peer in a specified address family.";
                 leaf type {
                   type "enumeration" {
                     enum "ipv4uni" {
                       value "1";
                       description
                         "IPv4 unicast address family.";
                     }
                     enum "ipv4multi" {
                       value "2";
                       description
                         "IPv4 multicast address family.";
                     }
                     enum "ipv4vpn" {
                       value "3";
                       description
                         "IPv4 VPN address family.";
                     }
                     enum "ipv4labeluni" {
                       value "4";
                       description
                         "IPv4 labeled address family.";
                     }
                     enum "ipv6uni" {
                       value "5";
                       description
                         "IPv6 unicast address family.";
                     }
                     enum "ipv6vpn" {
                       value "6";
                       description
                         "IPv6 VPN address family.";
                     }
                     enum "ipv4flow" {
                       value "7";
                       description
                         "IPv4 flow address family.";
                     }
                     enum "l2vpnad" {
                       value "8";
                       description
                         "L2VPN-AD address family.";
                     }
                     enum "evpn" {
                       value "9";
                       description
                         "EVPN address family.";
                     }
                     enum "mvpn" {
                       value "10";
                       description
                         "IPv4 MVPN address family.";
                     }
                     enum "vpntarget" {
                       value "11";
                       description
                         "VPN target address family.";
                     }
                     enum "ipv4vpnmcast" {
                       value "12";
                       description
                         "IPv4 VPN multicast address family.";
                     }
                     enum "ls" {
                       value "13";
                       description
                         "Link-state address family.";
                     }
                     enum "mdt" {
                       value "14";
                       description
                         "IPv4 MDT address family.";
                     }
                     enum "ipv6flow" {
                       value "15";
                       description
                         "IPv6 flow address family.";
                     }
                     enum "mvpnv6" {
                       value "16";
                       description
                         "IPv6 MVPN address family.";
                     }
                     enum "vpnv4flow" {
                       value "17";
                       description
                         "VPNv4 flow address family.";
                     }
                     enum "vpnv6flow" {
                       value "18";
                       description
                         "VPNv6 flow address family.";
                     }
                     enum "rpd" {
                       value "19";
                       description
                         "RPD address family.";
                     }
                     enum "ipv4srpolicy" {
                       value "20";
                       description
                         "IPv4-family SR-Policy address family.";
                     }
                     enum "ipv6srpolicy" {
                       value "21";
                       description
                         "IPv6-family SR-Policy address family.";
                     }
                   }
                   must "../../../../../afs/af[type = current()]";
                   description
                     "Specify the address family type to set the peer enable.";
                 }
                 container ipv4-unicast {
                   when "../type='ipv4uni'";
                   must "../../../../../../../l3vpn:afs/l3vpn:af[l3vpn:type='ipv"+
                        "4-unicast']";
                   description
                     "Configure IPv4 unicast options.";
                   leaf group-name {
                     type "leafref" {
                       path "../../../../../../peer-groups/peer-group/name";
                     }
                     must "../../../../../../peer-groups/peer-group[name = "+
                          "current()]/afs/af[type = 'ipv4uni']";
                     must "../../../../../../peer-groups/peer-group[name = "+
                          "current()]/peer-establish-mode = 'static'";
                     description
                       "Configure a name for a peer group. After a peer is "+
                       "deleted from the peer group, the peer is disabled from "+
                       "the address family. The object cannot be modified.";
                     ext:operation-exclude "update" {
                       description
                         "The node cannot be modified, when the peer already "+
                         "belongs to a peer-group.";
                     }
                   }
                   leaf reflect-client {
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf orf-type {
                     when "../../../../../../../../ni:name='_public_'";
                     type "bgp:bgp-orf-type";
                     must "(../orf-mode='null' and ../orf-type='null') or "+
                          "(../orf-mode!='null' and ../orf-type!='null')";
                     default "null";
                     description
                       "ORF Type.";
                   }
                   leaf orf-mode {
                     when "../../../../../../../../ni:name='_public_'";
                     type "bgp:bgp-orf-mode-type";
                     must "(../orf-mode='null' and ../orf-type='null') or "+
                          "(../orf-mode!='null' and ../orf-type!='null')";
                     default "null";
                     description
                       "Configure an outbound route filtering (ORF) mode, which "+
                       "can be Receive, Send, or Both, and the default ORF mode "+
                       "is Both.";
                   }
                   leaf label-route-capability {
                     type "boolean";
                     default "false";
                     description
                       "Enable/disable a device to exchange labeled routes.";
                   }
                   leaf check-tunnel-reachable {
                     when "../label-route-capability='true'";
                     type "boolean";
                     default "false";
                     description
                       "Enable/disable tunnel reachability check.";
                   }
                   leaf check-withdraw-type {
                     when "../label-route-capability='true'";
                     type "boolean";
                     default "true";
                     status "obsolete";
                     description
                       "Enable/disable withdraw type check.";
                   }
                   leaf nexthop-configure {
                     type "nexthop-configuration-type";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   leaf static-route-nexthop-invariable {
                     when "../../../../../../../../ni:name='_public_' and "+
                          "../nexthop-configure='invariable' and contains(../../"+
                          "../../address,'.')";
                     type "boolean";
                     default "false";
                     description
                       "Enable/disable BGP speaker does not change the next hop "+
                       "of an imported static route when advertising them to its"+
                       " peers.";
                   }
                   leaf unicast-route-nexthop-invariable {
                     when "../../../../../../../../ni:name='_public_' and "+
                          "../nexthop-configure='invariable' and contains(../../"+
                          "../../address,'.')";
                     type "boolean";
                     default "false";
                     description
                       "Enable/disable BGP speaker does not change the next hop "+
                       "of an imported unicast route when advertising them to "+
                       "its peers.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf origin-as-validation {
                     when "../advertise-ext-community='true'";
                     type "boolean";
                     default "false";
                     description
                       "Enable/disable the BGP peer origin validation.";
                   }
                   leaf allow-as-loop {
                     type "uint32" {
                       range "1..10";
                     }
                     description
                       "Allow repetitive local AS numbers. By default, "+
                       "repetitive local AS numbers are not allowed.";
                   }
                   leaf aigp {
                     when "../../../../../../../../ni:name='_public_'";
                     type "boolean";
                     default "false";
                     description
                       "Enable/disable route with AIGP attribute advertisement "+
                       "to or from a peer.";
                   }
                   leaf default-route-advertise {
                     type "boolean";
                     default "false";
                     description
                       "Enable/disable a device to advertise the default route "+
                       "to its peers. This option enables a device to send a "+
                       "default route with the device as the next hop address to"+
                       " its peers, regardless of whether there is a default "+
                       "route in the local routing table.";
                   }
                   choice default-route-advertise-policy-type {
                     description
                       "Set default route advertise-policy.";
                     case rtp-ref {
                       description
                         "The default-route-advertise-policy.";
                       leaf default-route-advertise-policy {
                         when "../default-route-advertise='true'";
                         type "leafref" {
                           path "/rtp:routing-policy/rtp:policy-definitions/rtp:"+
                                "policy-definition/rtp:name";
                         }
                         description
                           "Specify the name of a used policy.";
                       }
                     }
                     case xpl-ref {
                       description
                         "The default-route-advertise-filter.";
                       container default-route-advertise-filter {
                         when "../default-route-advertise='true'";
                         description
                           "Configure the route-filter for default route "+
                           "advertise.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                   leaf default-route-match-mode {
                     when "../default-route-advertise='true'";
                     type "cra-match-mode";
                     default "null";
                     description
                       "Configure the matching mode of default route advertiseme"+
                       "nt, which can be disabling of route advertisement "+
                       "conditions, enabling of all route advertisement "+
                       "conditions, and enabling of part route advertisement "+
                       "conditions. Enabling of all route advertisement "+
                       "conditions indicates that a default route can be "+
                       "advertised only when it matches all the conditions. "+
                       "Enabling of part route advertisement conditions "+
                       "indicates that a default route can be advertised only "+
                       "when it matches one condition.";
                   }
                   leaf add-path-mode {
                     when "../../../../../../../../ni:name='_public_'";
                     type "add-path-cap-type";
                     default "null";
                     description
                       "Enable add-path route advertisement to a peer.";
                   }
                   leaf import-ip-prefix {
                     type "leafref" {
                       path "/rtp:routing-policy/rtp:ipv4-prefix-filters/rtp:ipv"+
                            "4-prefix-filter/rtp:name";
                     }
                     description
                       "Specify the IPv4 filtering policy applied to the routes "+
                       "received from a specified peer. By default, no such "+
                       "policy is specified.";
                   }
                   leaf export-ip-prefix {
                     type "leafref" {
                       path "/rtp:routing-policy/rtp:ipv4-prefix-filters/rtp:ipv"+
                            "4-prefix-filter/rtp:name";
                     }
                     description
                       "Specify the IPv4 filtering policy applied to the routes "+
                       "to be advertised to a specified peer. By default, no "+
                       "such policy is specified.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl-name-or-num {
                     type "leafref" {
                       path "/acl:acl/acl:groups/acl:group/acl:identity";
                     }
                     description
                       "Specifies the name of the import ACL policy.";
                   }
                   leaf export-acl-name-or-num {
                     type "leafref" {
                       path "/acl:acl/acl:groups/acl:group/acl:identity";
                     }
                     description
                       "Specifies the name of the export ACL policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf add-path-number {
                     when "../../../../../../../../ni:name='_public_'";
                     type "uint8" {
                       range "2..64";
                     }
                     description
                       "Number of add-path routes that can be advertised to a "+
                       "peer.";
                   }
                   leaf substitute-as-enable {
                     type "boolean";
                     default "false";
                     description
                       "Enable/disable replace the AS number of a specified peer"+
                       " in the AS_Path attribute with the local AS number. On a"+
                       " PE where AS number replacement is enabled, if an AS "+
                       "number in the AS_Path attribute of a route is same as "+
                       "that of the CE to which the PE advertises the route, the"+
                       " PE replaces the AS number with its own AS number before"+
                       " advertising the route.";
                   }
                   leaf soo {
                     when "../../../../../../../../ni:name!='_public_'";
                     type "string" {
                       length "3..21";
                     }
                     description
                       "Configure the Site-of-Origin (SoO) extended community "+
                       "attribute. This attribute can be expressed in the "+
                       "following formats: X.X.X.X:number<0-65535>, number<0-655"+
                       "35>:number<0-4294967295>, or number<0-65535>.number<0-65"+
                       "535>:number<0-65535> or <65536-4294967295>:<0-65535>. "+
                       "0:0 or 0.0:0 is not supported. \nTwo CEs are in the same"+
                       " site and can advertise routes to each other, and they "+
                       "are connected to a VPN through PEs. If the local routes "+
                       "of a CE are advertised to the other CE over the VPN, a "+
                       "routing loop may occur. \nThe SoO feature can prevent a "+
                       "route advertised by a site from being sent back to the "+
                       "site, preventing routing loops. After SoO is enabled and"+
                       " a PE receives a route from a CE, the specified SoO "+
                       "attribute will be added to the route. Before advertising"+
                       " the route to the other CE, the PE checks the SoO "+
                       "attribute. If the SoO attribute is the same as the "+
                       "locally configured SoO attribute, the PE does not "+
                       "advertise the route, preventing routing loops.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   leaf exp-mode {
                     type "exp-mode-type";
                     default "null";
                     description
                       "Specify the ASs in which a BGP label can inherit the QoS"+
                       " priority carried in the outer label of public tunnel in"+
                       " the Core AS and the ASs in which the priorities of BGP "+
                       "LSPs must be restored before the LSPs are advertised to "+
                       "a non-core AS.";
                   }
                   leaf advertise-best-external {
                     when "../../../../../../../../ni:name='_public_'";
                     type "boolean";
                     must "../reflect-client='false' or ../advertise-best-extern"+
                          "al='false'";
                     must "../add-path-mode='null' or not(../add-path-mode) or "+
                          "../advertise-best-external='false'";
                     must "not(../add-path-number and ../advertise-best-external"+
                          "='true')";
                     default "false";
                     description
                       "Enable/disable the device to advertise Best External "+
                       "routes to peers.";
                   }
                   leaf prefix-sid {
                     when "../../../../../../../../ni:name='_public_'";
                     type "bgp:peer-comm-config-type";
                     default "default";
                     description
                       "Enable/disable a device to exchange IPv4 prefix SIDs "+
                       "with a specified IPv6 peer.";
                   }
                   leaf prefix-sid-state {
                     when "../../../../../../../../ni:name='_public_'";
                     type "boolean";
                     default "false";
                     config "false";
                     description
                       "Whether the prefix-sid to a peer is enabled.";
                   }
                   choice prefix-sid-packet {
                     description
                       "Prefix-sid packet method.";
                     case sid-type5 {
                       description
                         "Packet by type5.";
                       leaf advertise-srv6-locator {
                         when "../prefix-sid='enable'";
                         type "empty";
                         description
                           "Advertise SRv6 locators.";
                       }
                     }
                   }
                   container effect-state {
                     config "false";
                     description
                       "Operational state of peer.";
                     leaf advertise-srv6-locator {
                       type "boolean";
                       description
                         "Whether to advertise SRv6 locators on the BGP peer.";
                     }
                   }
                   leaf load-balancing-enable {
                     type "boolean";
                     default "false";
                     description
                       "Enable/disable a neighbour to participate in load "+
                       "balancing.";
                   }
                   choice load-balancing-ignore-as-type {
                     description
                       "Set load balancing as path type.";
                     case as-attribute {
                       description
                         "Ignore the as-path attribute.";
                       leaf load-balancing-as-path-ignore {
                         when "../load-balancing-enable='true'";
                         type "empty";
                         description
                           "Configure BGP to ignore the AS_Path attribute when "+
                           "selecting the equal route. After as-path-neglect is "+
                           "selected, BGP does not compare the AS_Path length.";
                       }
                     }
                     case same-length-as-attribute {
                       description
                         "Ignore comparison of as-path attributes with the same "+
                         "length.";
                       leaf load-balancing-as-path-relax {
                         when "../load-balancing-enable='true'";
                         type "empty";
                         description
                           "Configure BGP to ignore comparison of AS_Path "+
                           "attributes with the same length when selecting the "+
                           "equal route. After as-path-neglect is selected, BGP "+
                           "does not compare the AS_Path length.";
                       }
                     }
                   }
                   leaf advertise-community {
                     type "boolean";
                     default "false";
                     description
                       "Enable/disable advertise the community attribute to a "+
                       "peer or a peer group.";
                   }
                   leaf advertise-ext-community {
                     type "boolean";
                     default "false";
                     description
                       "Enable/disable advertise the extended community "+
                       "attribute to a peer or peer group.";
                   }
                   leaf discard-ext-community {
                     type "boolean";
                     default "false";
                     description
                       "Enable/disable discard the extended community attribute "+
                       "in the routing information about a specified peer.";
                   }
                   leaf advertise-large-community {
                     type "bgp:peer-comm-config-type";
                     default "default";
                     description
                       "Enable large-community attribute advertisement. The "+
                       "Link-state address family and the RPD address family do "+
                       "not support this element.";
                   }
                   leaf advertise-large-community-state {
                     type "boolean";
                     default "false";
                     config "false";
                     description
                       "Whether large-community attribute advertisement is "+
                       "enabled on a peer. The Link-state address family and the"+
                       " RPD address family do not support this element.";
                   }
                   leaf update-group-independent {
                     type "bgp:peer-comm-config-type";
                     default "default";
                     description
                       "Enable/disable the peer which can reside in an "+
                       "independent peer group.";
                   }
                   leaf update-group-independent-state {
                     type "boolean";
                     config "false";
                     description
                       "Whether the peer can reside in an independent peer "+
                       "group.";
                   }
                   leaf rpd-policy-export {
                     when "../../../../../../../../ni:name='_public_'";
                     type "bgp:peer-enable-config-type";
                     default "default";
                     description
                       "Enable/disable RPD export policy.";
                   }
                   container option {
                     description
                       "Configure IPv4 unicast peer common options.";
                     leaf export-origin-as-validation {
                       type "peer-attr-enable-type";
                       description
                         "Enable/disable the function ebgp peer advertising "+
                         "dependent roa validation, route is advtised roa reslut"+
                         " is valid.";
                     }
                     leaf include-not-found {
                       when "../export-origin-as-validation='enable'";
                       type "boolean";
                       default "false";
                       description
                         "Enable/disable the include-not-found attribute of the "+
                         "ROA validation.";
                     }
                     leaf external {
                       when "../include-not-found='true'";
                       type "boolean";
                       default "false";
                       description
                         "Enable/disable ROA export validation to advertise only"+
                         " external not found routes.";
                     }
                   }
                   container default-route-match-conditions {
                     when "../default-route-match-mode and ../default-route-matc"+
                          "h-mode!='null'";
                     description
                       "List of condition matching to filter the default routes "+
                       "to be advertised. The value takes effect only when the "+
                       "default route matching mode is not null and more than "+
                       "one IPv4 default route matching condition lists are "+
                       "configured.";
                     list default-route-match-condition {
                       key "address mask";
                       min-elements "1";
                       max-elements "4";
                       description
                         "Configure the matching condition for default route "+
                         "advertisement.";
                       leaf address {
                         type "inet:ipv4-address-no-zone";
                         description
                           "Configure a prefix that is used to match default "+
                           "routes.";
                       }
                       leaf mask {
                         type "uint32" {
                           range "0..32";
                         }
                         description
                           "Configure a mask that is used to match default "+
                           "routes.";
                       }
                     }
                   }
                   container route-limit {
                     description
                       "Configure parameters of routes limited from this peer.";
                     leaf number {
                       type "uint32" {
                         range "1..4294967295";
                       }
                       description
                         "Configure the maximum number of routes that can be "+
                         "accepted from a peer.";
                     }
                     leaf accept-prefix {
                       when "../number";
                       type "boolean";
                       default "false";
                       description
                         "Enable/disable the device to keep receiving routes and"+
                         " the routes are valid if the maximum number of routes "+
                         "allowed have been received and the alert-only "+
                         "parameter is specified.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "bgp:peer-comm-config-type";
                       default "default";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'enable'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                     leaf effect-enable {
                       type "boolean";
                       config "false";
                       description
                         "Flag indicating that the device is enabled to remove "+
                         "private AS numbers from the AS_Path list in received "+
                         "BGP update messages.";
                     }
                     leaf effect-force {
                       type "boolean";
                       config "false";
                       description
                         "Flag indicating that the device is enabled to forcibly"+
                         " remove all the private AS numbers from the AS_Path "+
                         "list in received BGP update messages.";
                     }
                   }
                   container entropy-label-parameter {
                     when "../../../../../../../../ni:name='_public_' and "+
                          "../label-route-capability='true'";
                     description
                       "Configure information about entropy label parameter "+
                       "configuration in a peer.";
                     leaf advertise-entropy-label {
                       type "peer-comm-config-type";
                       default "default";
                       description
                         "Enable the capability of advertising entropy labels.";
                     }
                     leaf padding {
                       when "../advertise-entropy-label='enable'";
                       type "string" {
                         length "1..32";
                         pattern "(([0-9A-F])*)";
                       }
                       description
                         "Padding format. The value is a hexadecimal string "+
                         "containing 1 to 32 characters (16 hexadecimal "+
                         "numbers). It cannot contain spaces, and can only "+
                         "contain uppercase letters (A to F) and digits (0 to "+
                         "9), and the length must be an even number.";
                     }
                     leaf attribute-type {
                       when "../advertise-entropy-label='enable'";
                       type "entropy-label-attribute-type";
                       mandatory "true";
                       description
                         "The attribute-type of advertising entropy labels.";
                     }
                     leaf entropy-label {
                       type "peer-comm-config-type";
                       default "default";
                       description
                         "Enable the function of delivering the entropy label "+
                         "capability to the forwarding plane.";
                     }
                     leaf effect-advertise-entropy-label {
                       type "boolean";
                       default "false";
                       config "false";
                       description
                         "Whether the capability of advertising entropy labels "+
                         "is enabled on the BGP peer.";
                     }
                     leaf effect-padding {
                       when "../effect-advertise-entropy-label='true'";
                       type "string" {
                         length "1..32";
                         pattern "(([0-9A-F])*)";
                       }
                       config "false";
                       description
                         "Padding format.";
                     }
                     leaf effect-attribute-type {
                       when "../effect-advertise-entropy-label='true'";
                       type "entropy-label-attribute-type";
                       config "false";
                       description
                         "The attribute-type of advertising entropy labels.";
                     }
                     leaf effect-entropy-label {
                       type "boolean";
                       default "false";
                       config "false";
                       description
                         "Whether the function of delivering the entropy label "+
                         "capability to the forwarding plane is enabled on the "+
                         "BGP peer.";
                     }
                   }
                   container path-attribute-treats {
                     description
                       "List of modes in which specified path attributes are "+
                       "processed.";
                     list path-attribute-treat {
                       must "discard-id-map or withdraw-id-map or unknown-id-map"+
                            "";
                       key "treat-type";
                       description
                         "Configure mode in which specified path attributes are "+
                         "processed.";
                       leaf treat-type {
                         type "bgp:path-attr-treat-type";
                         description
                           "Mode in which specified path attributes are "+
                           "processed.";
                       }
                       leaf discard-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a discard attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf withdraw-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a withdraw attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf unknown-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify an unknown attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                     }
                   }
                   container advertise-dependent-filter {
                     presence "Enable peer advertising dependent filter.";
                     description
                       "Configure peer advertising dependent filter.";
                     leaf dependent-filter-switch {
                       type "bgp:peer-attr-enable-type";
                       mandatory "true";
                       description
                         "Specify a switch type.";
                     }
                     leaf dependent-filter {
                       when "../dependent-filter-switch='enable'";
                       type "leafref" {
                         path "/rtp:routing-policy/rtp:ipv4-prefix-lists/rtp:ipv"+
                              "4-prefix-list/rtp:name";
                       }
                       mandatory "true";
                       description
                         "Specify a dependent route-filter name.";
                     }
                     leaf dependent-filter-type {
                       when "../dependent-filter-switch='enable'";
                       type "bgp:dependent-prefix-filter-type";
                       mandatory "true";
                       description
                         "Specify a dependent route-filter mode.";
                     }
                     leaf condition-filter {
                       when "../dependent-filter-switch='enable'";
                       type "leafref" {
                         path "/rtp:routing-policy/rtp:ipv4-prefix-lists/rtp:ipv"+
                              "4-prefix-list/rtp:name";
                       }
                       description
                         "Specify a condition route-filter name.";
                     }
                   }
                   container advertise-dependent-filter-state {
                     config "false";
                     description
                       "Peer advertising dependent filter state.";
                     leaf dependent-filter {
                       type "leafref" {
                         path "/rtp:routing-policy/rtp:ipv4-prefix-lists/rtp:ipv"+
                              "4-prefix-list/rtp:name";
                       }
                       description
                         "Specify a dependent route-filter name.";
                     }
                     leaf dependent-filter-type {
                       type "bgp:dependent-prefix-filter-type";
                       description
                         "Specify a dependent route-filter mode.";
                     }
                     leaf condition-filter {
                       type "leafref" {
                         path "/rtp:routing-policy/rtp:ipv4-prefix-lists/rtp:ipv"+
                              "4-prefix-list/rtp:name";
                       }
                       description
                         "Specify a condition route-filter name.";
                     }
                   }
                   container route-server {
                     description
                       "Configure the route server function on a device and "+
                       "specifies an EBGP peer as its client.";
                     leaf route-server-client {
                       type "peer-attr-enable-type";
                       must "(. = 'disable') or (not(/bgp:bgp/bgp:base-process/b"+
                            "gp:confederation/bgp:id) and (/bgp:bgp/bgp:base-pro"+
                            "cess/bgp:confederation/bgp:nonstanded = 'false'))";
                       must "(. = 'disable') or (../../label-route-capability = "+
                            "'false')";
                       description
                         "Enable/disable the route server function on a device "+
                         "and specifies an EBGP peer as its client.";
                     }
                   }
                   container link-bandwidth {
                     when "../../../../../../../../ni:name='_public_'";
                     description
                       "Configure peer link bandwidth attribute.";
                     leaf advertise {
                       type "peer-attr-enable-type";
                       description
                         "Enable/disable advertise the link bandwidth attribute "+
                         "to an EBGP peer.";
                     }
                     leaf transitive {
                       type "peer-attr-enable-type";
                       description
                         "Enable/disable transitive the link bandwidth "+
                         "attribute.";
                     }
                     leaf generate {
                       type "peer-attr-enable-type";
                       description
                         "Enable/disable generate the link bandwidth attribute "+
                         "to an EBGP peer.";
                     }
                   }
                 }
                 container ipv6-unicast {
                   when "../type = 'ipv6uni'";
                   must "../../../../../../../l3vpn:afs/l3vpn:af[l3vpn:type='ipv"+
                        "6-unicast']";
                   description
                     "Configure IPv6 unicast options.";
                   leaf group-name {
                     type "leafref" {
                       path "../../../../../../peer-groups/peer-group/name";
                     }
                     must "../../../../../../peer-groups/peer-group[name = "+
                          "current()]/afs/af[type = 'ipv6uni']";
                     must "../../../../../../peer-groups/peer-group[name = "+
                          "current()]/peer-establish-mode = 'static'";
                     description
                       "Configure a name for a peer group. After a peer is "+
                       "deleted from the peer group, the peer is disabled from "+
                       "the address family. The object cannot be modified.";
                     ext:operation-exclude "update" {
                       description
                         "The node cannot be modified, when the peer already "+
                         "belongs to a peer-group.";
                     }
                   }
                   leaf advertise-community {
                     type "boolean";
                     default "false";
                     description
                       "Enable/disable advertise the community attribute to a "+
                       "peer or a peer group.";
                   }
                   leaf reflect-client {
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf label-route-capability {
                     type "boolean";
                     default "false";
                     description
                       "Enable/disable a device to exchange labeled routes.";
                   }
                   leaf nexthop-configure {
                     type "nexthop-configuration-type";
                     must "(not(contains(../../../../address,':')) and "+
                          "../nexthop-configure='local') or contains(../../../.."+
                          "/address,':')";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   leaf static-route-nexthop-invariable {
                     when "../../../../../../../../ni:name='_public_' and "+
                          "../nexthop-configure='invariable'";
                     type "boolean";
                     default "false";
                     description
                       "Enable/disable BGP speaker does not change the next hop "+
                       "of an imported static route when advertising them to its"+
                       " peers.";
                   }
                   leaf unicast-route-nexthop-invariable {
                     when "../../../../../../../../ni:name='_public_' and "+
                          "../nexthop-configure='invariable'";
                     type "boolean";
                     default "false";
                     description
                       "Enable/disable BGP speaker does not change the next hop "+
                       "of an imported unicast route when advertising them to "+
                       "its peers.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf advertise-ext-community {
                     type "boolean";
                     default "false";
                     description
                       "Enable/disable advertise the extended community "+
                       "attribute to a peer or peer group.";
                   }
                   leaf origin-as-validation {
                     when "../advertise-ext-community='true'";
                     type "boolean";
                     default "false";
                     description
                       "Enable/disable the BGP peer origin validation.";
                   }
                   leaf discard-ext-community {
                     type "boolean";
                     default "false";
                     description
                       "Enable/disable discard the extended community attribute "+
                       "in the routing information about a specified peer.";
                   }
                   leaf allow-as-loop {
                     type "uint32" {
                       range "1..10";
                     }
                     description
                       "Allow repetitive local AS numbers. By default, "+
                       "repetitive local AS numbers are not allowed.";
                   }
                   leaf aigp {
                     when "../../../../../../../../ni:name='_public_'";
                     type "boolean";
                     default "false";
                     description
                       "Enable/disable route with AIGP attribute advertisement "+
                       "to or from a peer.";
                   }
                   leaf default-route-advertise {
                     type "boolean";
                     default "false";
                     description
                       "Enable/disable a device to advertise the default route "+
                       "to its peers. This option enables a device to send a "+
                       "default route with the device as the next hop address to"+
                       " its peers, regardless of whether there is a default "+
                       "route in the local routing table.";
                   }
                   choice default-route-advertise-policy-type {
                     description
                       "Set default route advertise-policy.";
                     case rtp-ref {
                       description
                         "The default-route-advertise-policy.";
                       leaf default-route-advertise-policy {
                         when "../default-route-advertise='true'";
                         type "leafref" {
                           path "/rtp:routing-policy/rtp:policy-definitions/rtp:"+
                                "policy-definition/rtp:name";
                         }
                         description
                           "Specify the name of a used policy.";
                       }
                     }
                     case xpl-ref {
                       description
                         "The default-route-advertise-filter.";
                       container default-route-advertise-filter {
                         when "../default-route-advertise='true'";
                         description
                           "Configure the route-filter for default route "+
                           "advertise.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                   leaf default-route-match-mode {
                     when "../default-route-advertise='true'";
                     type "cra-match-mode";
                     default "null";
                     description
                       "Configure the matching mode of default route advertiseme"+
                       "nt, which can be disabling of route advertisement "+
                       "conditions, enabling of all route advertisement "+
                       "conditions, and enabling of part route advertisement "+
                       "conditions. Enabling of all route advertisement "+
                       "conditions indicates that a default route can be "+
                       "advertised only when it matches all the conditions. "+
                       "Enabling of part route advertisement conditions "+
                       "indicates that a default route can be advertised only "+
                       "when it matches one condition.";
                   }
                   leaf add-path-mode {
                     when "../../../../../../../../ni:name='_public_'";
                     type "add-path-cap-type";
                     default "null";
                     description
                       "Enable Add-Path route advertisement to a peer.";
                   }
                   leaf import-ipv6-prefix {
                     type "leafref" {
                       path "/rtp:routing-policy/rtp:ipv6-prefix-filters/rtp:ipv"+
                            "6-prefix-filter/rtp:name";
                     }
                     description
                       "Specify the IPv6 filtering policy applied to the routes "+
                       "received from a specified peer. By default, no such "+
                       "policy is specified.";
                   }
                   leaf export-ipv6-prefix {
                     type "leafref" {
                       path "/rtp:routing-policy/rtp:ipv6-prefix-filters/rtp:ipv"+
                            "6-prefix-filter/rtp:name";
                     }
                     description
                       "Specify the IPv6 filtering policy applied to the routes "+
                       "to be advertised to a specified peer. By default, no "+
                       "such policy is specified.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl6-name-or-num {
                     type "leafref" {
                       path "/acl:acl/acl:group6s/acl:group6/acl:identity";
                     }
                     description
                       "Specifies the name of the import ACL6 policy.";
                   }
                   leaf export-acl6-name-or-num {
                     type "leafref" {
                       path "/acl:acl/acl:group6s/acl:group6/acl:identity";
                     }
                     description
                       "Specifies the name of the export ACL6 policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf add-path-number {
                     when "../../../../../../../../ni:name='_public_'";
                     type "uint8" {
                       range "2..64";
                     }
                     description
                       "Number of Add-Path routes that can be advertised to a "+
                       "peer.";
                   }
                   leaf substitute-as-enable {
                     type "boolean";
                     default "false";
                     description
                       "Enable/disable replace the AS number of a specified peer"+
                       " in the AS_Path attribute with the local AS number. On a"+
                       " PE where AS number replacement is enabled, if an AS "+
                       "number in the AS_Path attribute of a route is same as "+
                       "that of the CE to which the PE advertises the route, the"+
                       " PE replaces the AS number with its own AS number before"+
                       " advertising the route.";
                   }
                   leaf soo {
                     when "../../../../../../../../ni:name!='_public_'";
                     type "string" {
                       length "3..21";
                     }
                     description
                       "Configure the Site-of-Origin (SoO) extended community "+
                       "attribute. This attribute can be expressed in the "+
                       "following formats: X.X.X.X:number<0-65535>, number<0-655"+
                       "35>:number<0-4294967295>, or number<0-65535>.number<0-65"+
                       "535>:number<0-65535> or <65536-4294967295>:<0-65535>. "+
                       "0:0 or 0.0:0 is not supported. \nTwo CEs are in the same"+
                       " site and can advertise routes to each other, and they "+
                       "are connected to a VPN through PEs. If the local routes "+
                       "of a CE are advertised to the other CE over the VPN, a "+
                       "routing loop may occur. \nThe SoO feature can prevent a "+
                       "route advertised by a site from being sent back to the "+
                       "site, preventing routing loops. After SoO is enabled and"+
                       " a PE receives a route from a CE, the specified SoO "+
                       "attribute will be added to the route. Before advertising"+
                       " the route to the other CE, the PE checks the SoO "+
                       "attribute. If the SoO attribute is the same as the "+
                       "locally configured SoO attribute, the PE does not "+
                       "advertise the route, preventing routing loops.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   leaf advertise-best-external {
                     when "../../../../../../../../ni:name='_public_'";
                     type "boolean";
                     must "../reflect-client='false' or ../advertise-best-extern"+
                          "al='false'";
                     must "../add-path-mode='null' or not(../add-path-mode) or "+
                          "../advertise-best-external='false'";
                     must "not(../add-path-number and ../advertise-best-external"+
                          "='true')";
                     default "false";
                     description
                       "Enable/disable the device to advertise Best External "+
                       "routes to peers.";
                   }
                   leaf load-balancing-enable {
                     type "boolean";
                     default "false";
                     description
                       "Enable/disable a neighbour to participate in load "+
                       "balancing.";
                   }
                   choice load-balancing-ignore-as-type {
                     description
                       "Set load balancing as path type.";
                     case as-attribute {
                       description
                         "Ignore the as-path attribute.";
                       leaf load-balancing-as-path-ignore {
                         when "../load-balancing-enable='true'";
                         type "empty";
                         description
                           "Configure BGP to ignore the AS_Path attribute when "+
                           "selecting the equal route. After as-path-neglect is "+
                           "selected, BGP does not compare the AS_Path length.";
                       }
                     }
                     case same-length-as-attribute {
                       description
                         "Ignore comparison of as-path attributes with the same "+
                         "length.";
                       leaf load-balancing-as-path-relax {
                         when "../load-balancing-enable='true'";
                         type "empty";
                         description
                           "Configure BGP to ignore comparison of AS_Path "+
                           "attributes with the same length when selecting the "+
                           "equal route. After as-path-neglect is selected, BGP "+
                           "does not compare the AS_Path length.";
                       }
                     }
                   }
                   leaf tunnel-policy {
                     when "../../../../../../../../ni:name='_public_'";
                     type "leafref" {
                       path "/tnlm:tunnel-management/tnlm:tunnel-policys/tnlm:tu"+
                            "nnel-policy/tnlm:name";
                     }
                     description
                       "Apply a tunnel policy for a 6PE peer. By default, no "+
                       "tunnel policy is configured.";
                   }
                   leaf prefix-sid {
                     when "../../../../../../../../ni:name='_public_'";
                     type "bgp:peer-comm-config-type";
                     must "(contains(../../../../address,'.') and ../prefix-sid="+
                          "'default') or contains(../../../../address,':')";
                     default "default";
                     description
                       "Enable/disable a device to exchange prefix SIDs with a "+
                       "specified IPv6 peer.";
                   }
                   leaf prefix-sid-state {
                     when "../../../../../../../../ni:name='_public_'";
                     type "boolean";
                     default "false";
                     config "false";
                     description
                       "Whether the prefix-sid to a peer is enabled.";
                   }
                   choice prefix-sid-packet {
                     description
                       "Prefix-sid packet method.";
                     case sid-type5 {
                       description
                         "Packet by type5.";
                       leaf advertise-srv6-locator {
                         when "../prefix-sid='enable'";
                         type "empty";
                         description
                           "Advertise SRv6 locators.";
                       }
                     }
                   }
                   container effect-state {
                     config "false";
                     description
                       "Operational state of peer.";
                     leaf advertise-srv6-locator {
                       type "boolean";
                       description
                         "Whether to advertise SRv6 locators on the BGP peer.";
                     }
                   }
                   leaf advertise-large-community {
                     type "bgp:peer-comm-config-type";
                     default "default";
                     description
                       "Enable large-community attribute advertisement. The "+
                       "Link-state address family and the RPD address family do "+
                       "not support this element.";
                   }
                   leaf advertise-large-community-state {
                     type "boolean";
                     default "false";
                     config "false";
                     description
                       "Whether large-community attribute advertisement is "+
                       "enabled on a peer. The Link-state address family and the"+
                       " RPD address family do not support this element.";
                   }
                   leaf update-group-independent {
                     type "bgp:peer-comm-config-type";
                     default "default";
                     description
                       "Enable/disable the peer which can reside in an "+
                       "independent peer group.";
                   }
                   leaf update-group-independent-state {
                     type "boolean";
                     config "false";
                     description
                       "Whether the peer can reside in an independent peer "+
                       "group.";
                   }
                   container option {
                     description
                       "Configure IPv6 unicast peer common options.";
                     leaf export-origin-as-validation {
                       type "peer-attr-enable-type";
                       description
                         "Enable/disable the function ebgp peer advertising "+
                         "dependent roa validation, route is advtised roa reslut"+
                         " is valid.";
                     }
                     leaf include-not-found {
                       when "../export-origin-as-validation='enable'";
                       type "boolean";
                       default "false";
                       description
                         "Enable/disable the include-not-found attribute of the "+
                         "ROA validation.";
                     }
                     leaf external {
                       when "../include-not-found='true'";
                       type "boolean";
                       default "false";
                       description
                         "Enable/disable ROA export validation to advertise only"+
                         " external not found routes.";
                     }
                   }
                   container default-route-match-conditions {
                     when "../default-route-match-mode and ../default-route-matc"+
                          "h-mode!='null'";
                     description
                       "List of condition matching to filter the default routes "+
                       "to be advertised. The value takes effect only when the "+
                       "default route matching mode is not null and more than "+
                       "one IPv6 default route matching condition lists are "+
                       "configured.";
                     list default-route-match-condition {
                       key "address mask";
                       min-elements "1";
                       max-elements "4";
                       description
                         "Configure the matching condition for default route "+
                         "advertisement.";
                       leaf address {
                         type "inet:ipv6-address-no-zone";
                         description
                           "Configure a IPv6-prefix that is used to match "+
                           "default routes.";
                       }
                       leaf mask {
                         type "uint32" {
                           range "0..128";
                         }
                         description
                           "Configure a mask that is used to match default "+
                           "routes.";
                       }
                     }
                   }
                   container route-limit {
                     description
                       "Configure parameters of routes limited from this peer.";
                     leaf number {
                       type "uint32" {
                         range "1..4294967295";
                       }
                       description
                         "Configure the maximum number of routes that can be "+
                         "accepted from a peer.";
                     }
                     leaf accept-prefix {
                       when "../number";
                       type "boolean";
                       default "false";
                       description
                         "Enable/disable the device to keep receiving routes and"+
                         " the routes are valid if the maximum number of routes "+
                         "allowed have been received and the alert-only "+
                         "parameter is specified.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "bgp:peer-comm-config-type";
                       default "default";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'enable'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                     leaf effect-enable {
                       type "boolean";
                       config "false";
                       description
                         "Flag indicating that the device is enabled to remove "+
                         "private AS numbers from the AS_Path list in received "+
                         "BGP update messages.";
                     }
                     leaf effect-force {
                       type "boolean";
                       config "false";
                       description
                         "Flag indicating that the device is enabled to forcibly"+
                         " remove all the private AS numbers from the AS_Path "+
                         "list in received BGP update messages.";
                     }
                   }
                   container path-attribute-treats {
                     description
                       "List of modes in which specified path attributes are "+
                       "processed.";
                     list path-attribute-treat {
                       must "discard-id-map or withdraw-id-map or unknown-id-map"+
                            "";
                       key "treat-type";
                       description
                         "Configure mode in which specified path attributes are "+
                         "processed.";
                       leaf treat-type {
                         type "bgp:path-attr-treat-type";
                         description
                           "Mode in which specified path attributes are "+
                           "processed.";
                       }
                       leaf discard-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a discard attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf withdraw-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a withdraw attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf unknown-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify an unknown attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                     }
                   }
                   container advertise-dependent-filter6 {
                     presence "Enable peer advertising dependent filter.";
                     description
                       "Configure peer advertising dependent filter.";
                     leaf dependent-filter-switch {
                       type "bgp:peer-attr-enable-type";
                       mandatory "true";
                       description
                         "Specify a switch type.";
                     }
                     leaf dependent-filter6 {
                       when "../dependent-filter-switch='enable'";
                       type "leafref" {
                         path "/rtp:routing-policy/rtp:ipv6-prefix-lists/rtp:ipv"+
                              "6-prefix-list/rtp:name";
                       }
                       mandatory "true";
                       description
                         "Specify a dependent route-filter name.";
                     }
                     leaf dependent-filter-type {
                       when "../dependent-filter-switch='enable'";
                       type "bgp:dependent-prefix-filter-type";
                       mandatory "true";
                       description
                         "Specify a dependent route-filter mode.";
                     }
                     leaf condition-filter6 {
                       when "../dependent-filter-switch='enable'";
                       type "leafref" {
                         path "/rtp:routing-policy/rtp:ipv6-prefix-lists/rtp:ipv"+
                              "6-prefix-list/rtp:name";
                       }
                       description
                         "Specify a condition route-filter name.";
                     }
                   }
                   container advertise-dependent-filter6-state {
                     config "false";
                     description
                       "Peer advertising dependent filter state.";
                     leaf dependent-filter6 {
                       type "leafref" {
                         path "/rtp:routing-policy/rtp:ipv6-prefix-lists/rtp:ipv"+
                              "6-prefix-list/rtp:name";
                       }
                       description
                         "Specify a dependent route-filter name.";
                     }
                     leaf dependent-filter-type {
                       type "bgp:dependent-prefix-filter-type";
                       description
                         "Specify a dependent route-filter mode.";
                     }
                     leaf condition-filter6 {
                       type "leafref" {
                         path "/rtp:routing-policy/rtp:ipv6-prefix-lists/rtp:ipv"+
                              "6-prefix-list/rtp:name";
                       }
                       description
                         "Specify a condition route-filter name.";
                     }
                   }
                   container route-server {
                     description
                       "Configure the route server function on a device and "+
                       "specifies an EBGP peer as its client.";
                     leaf route-server-client {
                       type "peer-attr-enable-type";
                       must "(. = 'disable') or (not(/bgp:bgp/bgp:base-process/b"+
                            "gp:confederation/bgp:id) and (/bgp:bgp/bgp:base-pro"+
                            "cess/bgp:confederation/bgp:nonstanded = 'false'))";
                       must "(. = 'disable') or (../../label-route-capability = "+
                            "'false')";
                       must "(. = 'disable') or (../../prefix-sid = 'disable')";
                       description
                         "Enable/disable the route server function on a device "+
                         "and specifies an EBGP peer as its client.";
                     }
                   }
                   container link-bandwidth {
                     when "../../../../../../../../ni:name='_public_'";
                     description
                       "Configure peer link bandwidth attribute.";
                     leaf advertise {
                       type "peer-attr-enable-type";
                       description
                         "Enable/disable advertise the link bandwidth attribute "+
                         "to an EBGP peer.";
                     }
                     leaf transitive {
                       type "peer-attr-enable-type";
                       description
                         "Enable/disable transitive the link bandwidth "+
                         "attribute.";
                     }
                     leaf generate {
                       type "peer-attr-enable-type";
                       description
                         "Enable/disable generate the link bandwidth attribute "+
                         "to an EBGP peer.";
                     }
                   }
                 }
                 container ipv4-vpn {
                   when "../type = 'ipv4vpn'";
                   description
                     "Configure IPv4 VPNv4 options.";
                   leaf group-name {
                     type "leafref" {
                       path "../../../../../../peer-groups/peer-group/name";
                     }
                     must "../../../../../../peer-groups/peer-group[name = "+
                          "current()]/afs/af[type = 'ipv4vpn']";
                     must "../../../../../../peer-groups/peer-group[name = "+
                          "current()]/peer-establish-mode = 'static'";
                     description
                       "Configure a name for a peer group. After a peer is "+
                       "deleted from the peer group, the peer is disabled from "+
                       "the address family. The object cannot be modified.";
                     ext:operation-exclude "update" {
                       description
                         "The node cannot be modified, when the peer already "+
                         "belongs to a peer-group.";
                     }
                   }
                   leaf advertise-community {
                     type "boolean";
                     default "false";
                     description
                       "Enable/disable advertise the community attribute to a "+
                       "peer or a peer group.";
                   }
                   leaf reflect-client {
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf nexthop-configure {
                     type "nexthop-configuration-type";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf ignore-bit-error {
                     when "../export-policy or ../export-filter";
                     type "boolean";
                     default "false";
                     description
                       "Enable/disable the peer to ignore bit error detection "+
                       "results.";
                   }
                   leaf allow-as-loop {
                     type "uint32" {
                       range "1..10";
                     }
                     description
                       "Allow repetitive local AS numbers. By default, "+
                       "repetitive local AS numbers are not allowed.";
                   }
                   leaf aigp {
                     type "boolean";
                     default "false";
                     description
                       "Enable/disable route with AIGP attribute advertisement "+
                       "to or from a peer.";
                   }
                   leaf add-path-mode {
                     type "add-path-cap-type";
                     default "null";
                     description
                       "Enable Add-Path route advertisement to a peer.";
                   }
                   leaf add-path-number {
                     type "uint8" {
                       range "2..64";
                     }
                     description
                       "Number of Add-Path routes that can be advertised to a "+
                       "peer.";
                   }
                   leaf import-ip-prefix {
                     type "leafref" {
                       path "/rtp:routing-policy/rtp:ipv4-prefix-filters/rtp:ipv"+
                            "4-prefix-filter/rtp:name";
                     }
                     description
                       "Specify the IPv4 filtering policy applied to the routes "+
                       "received from a specified peer. By default, no such "+
                       "policy is specified.";
                   }
                   leaf export-ip-prefix {
                     type "leafref" {
                       path "/rtp:routing-policy/rtp:ipv4-prefix-filters/rtp:ipv"+
                            "4-prefix-filter/rtp:name";
                     }
                     description
                       "Specify the IPv4 filtering policy applied to the routes "+
                       "to be advertised to a specified peer. By default, no "+
                       "such policy is specified.";
                   }
                   leaf reoriginate-route-enable {
                     type "boolean";
                     default "false";
                     description
                       "Enable/disable route regeneration.";
                   }
                   leaf reoriginate-ip-enable {
                     type "boolean";
                     default "false";
                     description
                       "Enable/disable IP route regeneration and advertisement.";
                   }
                   leaf reoriginate-mac-ip-enable {
                     type "boolean";
                     default "false";
                     description
                       "Enable/disable MAC-IP route regeneration and advertiseme"+
                       "nt.";
                   }
                   leaf reoriginate-vpnv4-route-enable {
                     type "boolean";
                     default "false";
                     description
                       "Enable/disable VPNv4 route regeneration and advertisemen"+
                       "t.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl-name-or-num {
                     type "leafref" {
                       path "/acl:acl/acl:groups/acl:group/acl:identity";
                     }
                     description
                       "Specifies the name of the import ACL policy.";
                   }
                   leaf export-acl-name-or-num {
                     type "leafref" {
                       path "/acl:acl/acl:groups/acl:group/acl:identity";
                     }
                     description
                       "Specifies the name of the export ACL policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf upe {
                     type "boolean";
                     default "false";
                     description
                       "Enable/disable the peer as an underlayer PE (UPE).";
                   }
                   leaf high-priority {
                     type "peer-comm-config-type";
                     default "default";
                     description
                       "Enable/disable vpn-router high priority.";
                   }
                   leaf prefix-sid {
                     type "bgp:peer-enable-config-type";
                     must "(contains(../../../../address,'.') and ../prefix-sid="+
                          "'default') or contains(../../../../address,':')";
                     default "default";
                     description
                       "Specify a SID mode relay for peer.";
                   }
                   choice prefix-sid-packet {
                     description
                       "Prefix-sid packet method.";
                     case sid-type5 {
                       description
                         "Packet by type5.";
                       leaf sid-type5 {
                         when "../prefix-sid='enable'";
                         type "empty";
                         description
                           "Packet by type5.";
                       }
                       leaf advertise-srv6-locator {
                         when "../sid-type5";
                         type "empty";
                         description
                           "Advertise SRv6 locators.";
                       }
                     }
                   }
                   leaf advertise-best-external {
                     type "boolean";
                     must "../reflect-client='false' or ../advertise-best-extern"+
                          "al='false'";
                     must "../add-path-mode='null' or not(../add-path-mode) or "+
                          "../advertise-best-external='false'";
                     must "not(../add-path-number and ../advertise-best-external"+
                          "='true')";
                     default "false";
                     description
                       "Enable/disable the device to advertise Best External "+
                       "routes to peers.";
                   }
                   leaf advertise-large-community {
                     type "bgp:peer-comm-config-type";
                     default "default";
                     description
                       "Enable large-community attribute advertisement. The "+
                       "Link-state address family and the RPD address family do "+
                       "not support this element.";
                   }
                   leaf advertise-large-community-state {
                     type "boolean";
                     default "false";
                     config "false";
                     description
                       "Whether large-community attribute advertisement is "+
                       "enabled on a peer. The Link-state address family and the"+
                       " RPD address family do not support this element.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   leaf update-group-independent {
                     type "bgp:peer-comm-config-type";
                     default "default";
                     description
                       "Enable/disable the peer which can reside in an "+
                       "independent peer group.";
                   }
                   leaf update-group-independent-state {
                     type "boolean";
                     config "false";
                     description
                       "Whether the peer can reside in an independent peer "+
                       "group.";
                   }
                   leaf origin-as-validation {
                     type "boolean";
                     default "false";
                     description
                       "Enable/disable the BGP peer origin validation.";
                   }
                   container default-route-originates {
                     description
                       "Configure advertised default VPNv4 routes.";
                     list default-route-originate {
                       key "vpn-name";
                       description
                         "Configure advertised default VPNv4 route.";
                       leaf vpn-name {
                         type "leafref" {
                           path "/ni:network-instance/ni:instances/ni:instance/n"+
                                "i:name";
                         }
                         must "../vpn-name!='_public_'";
                         description
                           "VPN instance name. It uniquely identifies a VPN "+
                           "instance. The name is a string of case-sensitive "+
                           "characters.";
                       }
                     }
                   }
                   container route-limit {
                     description
                       "Configure parameters of routes limited from this peer.";
                     leaf number {
                       type "uint32" {
                         range "1..4294967295";
                       }
                       description
                         "Configure the maximum number of routes that can be "+
                         "accepted from a peer.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "bgp:peer-comm-config-type";
                       default "default";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'enable'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                     leaf effect-enable {
                       type "boolean";
                       config "false";
                       description
                         "Flag indicating that the device is enabled to remove "+
                         "private AS numbers from the AS_Path list in received "+
                         "BGP update messages.";
                     }
                     leaf effect-force {
                       type "boolean";
                       config "false";
                       description
                         "Flag indicating that the device is enabled to forcibly"+
                         " remove all the private AS numbers from the AS_Path "+
                         "list in received BGP update messages.";
                     }
                   }
                   container path-attribute-treats {
                     description
                       "List of modes in which specified path attributes are "+
                       "processed.";
                     list path-attribute-treat {
                       must "discard-id-map or withdraw-id-map or unknown-id-map"+
                            "";
                       key "treat-type";
                       description
                         "Configure mode in which specified path attributes are "+
                         "processed.";
                       leaf treat-type {
                         type "bgp:path-attr-treat-type";
                         description
                           "Mode in which specified path attributes are "+
                           "processed.";
                       }
                       leaf discard-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a discard attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf withdraw-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a withdraw attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf unknown-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify an unknown attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                     }
                   }
                 }
                 container ipv6-vpn {
                   when "../type = 'ipv6vpn'";
                   description
                     "Configure IPv6 vpn options.";
                   leaf group-name {
                     type "leafref" {
                       path "../../../../../../peer-groups/peer-group/name";
                     }
                     must "../../../../../../peer-groups/peer-group[name = "+
                          "current()]/afs/af[type = 'ipv6vpn']";
                     must "../../../../../../peer-groups/peer-group[name = "+
                          "current()]/peer-establish-mode = 'static'";
                     description
                       "Configure a name for a peer group. After a peer is "+
                       "deleted from the peer group, the peer is disabled from "+
                       "the address family. The object cannot be modified.";
                     ext:operation-exclude "update" {
                       description
                         "The node cannot be modified, when the peer already "+
                         "belongs to a peer-group.";
                     }
                   }
                   leaf advertise-community {
                     type "boolean";
                     default "false";
                     description
                       "Enable/disable advertise the community attribute to a "+
                       "peer or a peer group.";
                   }
                   leaf reflect-client {
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf nexthop-configure {
                     type "nexthop-configuration-type";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf ignore-bit-error {
                     when "../export-policy or ../export-filter";
                     type "boolean";
                     default "false";
                     description
                       "Enable/disable the peer to ignore bit error detection "+
                       "results.";
                   }
                   leaf allow-as-loop {
                     type "uint32" {
                       range "1..10";
                     }
                     description
                       "Allow repetitive local AS numbers. By default, "+
                       "repetitive local AS numbers are not allowed.";
                   }
                   leaf aigp {
                     type "boolean";
                     default "false";
                     description
                       "Enable/disable route with AIGP attribute advertisement "+
                       "to or from a peer.";
                   }
                   leaf add-path-mode {
                     type "add-path-cap-type";
                     default "null";
                     description
                       "Enable Add-Path route advertisement to a peer.";
                   }
                   leaf add-path-number {
                     type "uint8" {
                       range "2..64";
                     }
                     description
                       "Number of Add-Path routes that can be advertised to a "+
                       "peer.";
                   }
                   leaf import-ipv6-prefix {
                     type "leafref" {
                       path "/rtp:routing-policy/rtp:ipv6-prefix-filters/rtp:ipv"+
                            "6-prefix-filter/rtp:name";
                     }
                     description
                       "Specify the IPv6 filtering policy applied to the routes "+
                       "received from a specified peer. By default, no such "+
                       "policy is specified.";
                   }
                   leaf export-ipv6-prefix {
                     type "leafref" {
                       path "/rtp:routing-policy/rtp:ipv6-prefix-filters/rtp:ipv"+
                            "6-prefix-filter/rtp:name";
                     }
                     description
                       "Specify the IPv6 filtering policy applied to the routes "+
                       "to be advertised to a specified peer. By default, no "+
                       "such policy is specified.";
                   }
                   leaf reoriginate-route-enable {
                     type "boolean";
                     default "false";
                     description
                       "Enable/disable route regeneration.";
                   }
                   leaf reoriginate-ipv6-enable {
                     type "boolean";
                     default "false";
                     description
                       "Enable/disable IP route regeneration and advertisement.";
                   }
                   leaf reoriginate-mac-ipv6-enable {
                     type "boolean";
                     default "false";
                     description
                       "Enable/disable MAC-IP route regeneration and advertiseme"+
                       "nt.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl6-name-or-num {
                     type "leafref" {
                       path "/acl:acl/acl:group6s/acl:group6/acl:identity";
                     }
                     description
                       "Specifies the name of the import ACL6 policy.";
                   }
                   leaf export-acl6-name-or-num {
                     type "leafref" {
                       path "/acl:acl/acl:group6s/acl:group6/acl:identity";
                     }
                     description
                       "Specifies the name of the export ACL6 policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf advertise-best-external {
                     type "boolean";
                     must "../reflect-client='false' or ../advertise-best-extern"+
                          "al='false'";
                     must "../add-path-mode='null' or ../advertise-best-external"+
                          "='false'";
                     must "not(../add-path-number and ../advertise-best-external"+
                          "='true')";
                     default "false";
                     description
                       "Enable/disable the device to advertise Best External "+
                       "routes to peers.";
                   }
                   leaf advertise-large-community {
                     type "bgp:peer-comm-config-type";
                     default "default";
                     description
                       "Enable large-community attribute advertisement. The "+
                       "Link-state address family and the RPD address family do "+
                       "not support this element.";
                   }
                   leaf advertise-large-community-state {
                     type "boolean";
                     default "false";
                     config "false";
                     description
                       "Whether large-community attribute advertisement is "+
                       "enabled on a peer. The Link-state address family and the"+
                       " RPD address family do not support this element.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   leaf update-group-independent {
                     type "bgp:peer-comm-config-type";
                     default "default";
                     description
                       "Enable/disable the peer which can reside in an "+
                       "independent peer group.";
                   }
                   leaf update-group-independent-state {
                     type "boolean";
                     config "false";
                     description
                       "Whether the peer can reside in an independent peer "+
                       "group.";
                   }
                   leaf origin-as-validation {
                     type "boolean";
                     default "false";
                     description
                       "Enable/disable the BGP peer origin validation.";
                   }
                   leaf high-priority {
                     type "peer-comm-config-type";
                     default "default";
                     description
                       "Enable/disable vpn-router high priority.";
                   }
                   leaf prefix-sid {
                     type "bgp:peer-comm-config-type";
                     must "(contains(../../../../address,'.') and ../prefix-sid="+
                          "'default') or contains(../../../../address,':')";
                     default "default";
                     description
                       "Specify a SID mode relay for peer.";
                   }
                   leaf prefix-sid-state {
                     type "boolean";
                     default "false";
                     config "false";
                     description
                       "Whether the prefix-sid to a peer is enabled.";
                   }
                   choice prefix-sid-packet {
                     description
                       "Prefix-sid packet method.";
                     case sid-type5 {
                       description
                         "Packet by type5.";
                       leaf advertise-srv6-locator {
                         when "../prefix-sid='enable'";
                         type "empty";
                         description
                           "Advertise SRv6 locators.";
                       }
                     }
                   }
                   container route-limit {
                     description
                       "Configure parameters of routes limited from this peer.";
                     leaf number {
                       type "uint32" {
                         range "1..4294967295";
                       }
                       description
                         "Configure the maximum number of routes that can be "+
                         "accepted from a peer.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "bgp:peer-comm-config-type";
                       default "default";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'enable'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                     leaf effect-enable {
                       type "boolean";
                       config "false";
                       description
                         "Flag indicating that the device is enabled to remove "+
                         "private AS numbers from the AS_Path list in received "+
                         "BGP update messages.";
                     }
                     leaf effect-force {
                       type "boolean";
                       config "false";
                       description
                         "Flag indicating that the device is enabled to forcibly"+
                         " remove all the private AS numbers from the AS_Path "+
                         "list in received BGP update messages.";
                     }
                   }
                   container path-attribute-treats {
                     description
                       "List of modes in which specified path attributes are "+
                       "processed.";
                     list path-attribute-treat {
                       must "discard-id-map or withdraw-id-map or unknown-id-map"+
                            "";
                       key "treat-type";
                       description
                         "Configure mode in which specified path attributes are "+
                         "processed.";
                       leaf treat-type {
                         type "bgp:path-attr-treat-type";
                         description
                           "Mode in which specified path attributes are "+
                           "processed.";
                       }
                       leaf discard-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a discard attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf withdraw-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a withdraw attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf unknown-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify an unknown attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                     }
                   }
                 }
                 container ipv4-labeluni {
                   when "../type = 'ipv4labeluni'";
                   must "../../../../../../../l3vpn:afs/l3vpn:af[l3vpn:type='ipv"+
                        "4-unicast']";
                   description
                     "Configure IPv4 label unicast options.";
                   leaf group-name {
                     type "leafref" {
                       path "../../../../../../peer-groups/peer-group/name";
                     }
                     must "../../../../../../peer-groups/peer-group[name = "+
                          "current()]/afs/af[type = 'ipv4labeluni']";
                     must "../../../../../../peer-groups/peer-group[name = "+
                          "current()]/peer-establish-mode = 'static'";
                     description
                       "Configure a name for a peer group. After a peer is "+
                       "deleted from the peer group, the peer is disabled from "+
                       "the address family. The object cannot be modified.";
                     ext:operation-exclude "update" {
                       description
                         "The node cannot be modified, when the peer already "+
                         "belongs to a peer-group.";
                     }
                   }
                   leaf advertise-community {
                     type "boolean";
                     default "false";
                     description
                       "Enable/disable advertise the community attribute to a "+
                       "peer or a peer group.";
                   }
                   leaf reflect-client {
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf check-tunnel-reachable {
                     type "boolean";
                     default "false";
                     description
                       "Enable/disable tunnel reachability check.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf advertise-ext-community {
                     type "boolean";
                     default "false";
                     description
                       "Enable/disable advertise the extended community "+
                       "attribute to a peer or peer group.";
                   }
                   leaf discard-ext-community {
                     type "boolean";
                     default "false";
                     description
                       "Enable/disable discard the extended community attribute "+
                       "in the routing information about a specified peer.";
                   }
                   leaf allow-as-loop {
                     type "uint32" {
                       range "1..10";
                     }
                     description
                       "Allow repetitive local AS numbers. By default, "+
                       "repetitive local AS numbers are not allowed.";
                   }
                   leaf aigp {
                     when "../../../../../../../../ni:name='_public_'";
                     type "boolean";
                     default "false";
                     description
                       "Enable/disable route with AIGP attribute advertisement "+
                       "to or from a peer.";
                   }
                   leaf add-path-mode {
                     when "../../../../../../../../ni:name='_public_'";
                     type "add-path-cap-type";
                     default "null";
                     description
                       "Enable add-path route advertisement to a peer.";
                   }
                   leaf import-ip-prefix {
                     type "leafref" {
                       path "/rtp:routing-policy/rtp:ipv4-prefix-filters/rtp:ipv"+
                            "4-prefix-filter/rtp:name";
                     }
                     description
                       "Specify the IPv4 filtering policy applied to the routes "+
                       "received from a specified peer. By default, no such "+
                       "policy is specified.";
                   }
                   leaf export-ip-prefix {
                     type "leafref" {
                       path "/rtp:routing-policy/rtp:ipv4-prefix-filters/rtp:ipv"+
                            "4-prefix-filter/rtp:name";
                     }
                     description
                       "Specify the IPv4 filtering policy applied to the routes "+
                       "to be advertised to a specified peer. By default, no "+
                       "such policy is specified.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl-name-or-num {
                     type "leafref" {
                       path "/acl:acl/acl:groups/acl:group/acl:identity";
                     }
                     description
                       "Specifies the name of the import ACL policy.";
                   }
                   leaf export-acl-name-or-num {
                     type "leafref" {
                       path "/acl:acl/acl:groups/acl:group/acl:identity";
                     }
                     description
                       "Specifies the name of the export ACL policy.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf nexthop-configure {
                     type "nexthop-configuration-type";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf exp-mode {
                     when "../../../../../../../../ni:name!='_public_'";
                     type "exp-mode-type";
                     default "null";
                     description
                       "Specify the ASs in which a BGP label can inherit the QoS"+
                       " priority carried in the outer label of public tunnel in"+
                       " the Core AS and the ASs in which the priorities of BGP "+
                       "LSPs must be restored before the LSPs are advertised to "+
                       "a non-core AS.";
                   }
                   leaf add-path-number {
                     when "../../../../../../../../ni:name='_public_'";
                     type "uint8" {
                       range "2..64";
                     }
                     description
                       "Number of Add-Path routes that can be advertised to a "+
                       "peer.";
                   }
                   leaf substitute-as-enable {
                     type "boolean";
                     default "false";
                     description
                       "Enable/disable replace the AS number of a specified peer"+
                       " in the AS_Path attribute with the local AS number. On a"+
                       " PE where AS number replacement is enabled, if an AS "+
                       "number in the AS_Path attribute of a route is same as "+
                       "that of the CE to which the PE advertises the route, the"+
                       " PE replaces the AS number with its own AS number before"+
                       " advertising the route.";
                   }
                   leaf soo {
                     when "../../../../../../../../ni:name!='_public_'";
                     type "string" {
                       length "3..21";
                     }
                     description
                       "Configure the Site-of-Origin (SoO) extended community "+
                       "attribute. This attribute can be expressed in the "+
                       "following formats: X.X.X.X:number<0-65535>, number<0-655"+
                       "35>:number<0-4294967295>, or number<0-65535>.number<0-65"+
                       "535>:number<0-65535> or <65536-4294967295>:<0-65535>. "+
                       "0:0 or 0.0:0 is not supported. \nTwo CEs are in the same"+
                       " site and can advertise routes to each other, and they "+
                       "are connected to a VPN through PEs. If the local routes "+
                       "of a CE are advertised to the other CE over the VPN, a "+
                       "routing loop may occur. \nThe SoO feature can prevent a "+
                       "route advertised by a site from being sent back to the "+
                       "site, preventing routing loops. After SoO is enabled and"+
                       " a PE receives a route from a CE, the specified SoO "+
                       "attribute will be added to the route. Before advertising"+
                       " the route to the other CE, the PE checks the SoO "+
                       "attribute. If the SoO attribute is the same as the "+
                       "locally configured SoO attribute, the PE does not "+
                       "advertise the route, preventing routing loops.";
                   }
                   leaf advertise-best-external {
                     when "../../../../../../../../ni:name='_public_'";
                     type "boolean";
                     must "../reflect-client='false' or ../advertise-best-extern"+
                          "al='false'";
                     must "../add-path-mode='null' or not(../add-path-mode) or "+
                          "../advertise-best-external='false'";
                     must "not(../add-path-number and ../advertise-best-external"+
                          "='true')";
                     default "false";
                     description
                       "Enable/disable the device to advertise Best External "+
                       "routes to peers.";
                   }
                   leaf prefix-sid {
                     when "../../../../../../../../ni:name='_public_'";
                     type "bgp:peer-comm-config-type";
                     default "default";
                     description
                       "Enable/disable a device to exchange IPv4 prefix SIDs "+
                       "with a specified IPv6 peer.";
                   }
                   leaf prefix-sid-state {
                     when "../../../../../../../../ni:name='_public_'";
                     type "boolean";
                     config "false";
                     description
                       "Whether the prefix-sid to a peer is enabled.";
                   }
                   leaf load-balancing-enable {
                     when "../../../../../../../../ni:name='_public_'";
                     type "boolean";
                     default "false";
                     description
                       "Enable/disable a neighbour to participate in load "+
                       "balancing.";
                   }
                   choice load-balancing-ignore-as-type {
                     description
                       "Set load balancing as path type.";
                     case as-attribute {
                       description
                         "Ignore the as-path attribute.";
                       leaf load-balancing-as-path-ignore {
                         when "../load-balancing-enable='true'";
                         type "empty";
                         description
                           "Configure BGP to ignore the AS_Path attribute when "+
                           "selecting the equal route. After as-path-neglect is "+
                           "selected, BGP does not compare the AS_Path length.";
                       }
                     }
                     case same-length-as-attribute {
                       description
                         "Ignore comparison of as-path attributes with the same "+
                         "length.";
                       leaf load-balancing-as-path-relax {
                         when "../load-balancing-enable='true'";
                         type "empty";
                         description
                           "Configure BGP to ignore comparison of AS_Path "+
                           "attributes with the same length when selecting the "+
                           "equal route. After as-path-neglect is selected, BGP "+
                           "does not compare the AS_Path length.";
                       }
                     }
                   }
                   leaf advertise-large-community {
                     type "bgp:peer-comm-config-type";
                     default "default";
                     description
                       "Enable large-community attribute advertisement. The "+
                       "Link-state address family and the RPD address family do "+
                       "not support this element.";
                   }
                   leaf advertise-large-community-state {
                     type "boolean";
                     default "false";
                     config "false";
                     description
                       "Whether large-community attribute advertisement is "+
                       "enabled on a peer. The Link-state address family and the"+
                       " RPD address family do not support this element.";
                   }
                   leaf update-group-independent {
                     type "bgp:peer-comm-config-type";
                     default "default";
                     description
                       "Enable/disable the peer which can reside in an "+
                       "independent peer group.";
                   }
                   leaf update-group-independent-state {
                     type "boolean";
                     config "false";
                     description
                       "Whether the peer can reside in an independent peer "+
                       "group.";
                   }
                   container route-limit {
                     description
                       "Configure parameters of routes limited from this peer.";
                     leaf number {
                       type "uint32" {
                         range "1..4294967295";
                       }
                       description
                         "Configure the maximum number of routes that can be "+
                         "accepted from a peer.";
                     }
                     leaf accept-prefix {
                       when "../number";
                       type "boolean";
                       default "false";
                       description
                         "Enable/disable the device to keep receiving routes and"+
                         " the routes are valid if the maximum number of routes "+
                         "allowed have been received and the alert-only "+
                         "parameter is specified.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "bgp:peer-comm-config-type";
                       default "default";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'enable'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                     leaf effect-enable {
                       type "boolean";
                       config "false";
                       description
                         "Flag indicating that the device is enabled to remove "+
                         "private AS numbers from the AS_Path list in received "+
                         "BGP update messages.";
                     }
                     leaf effect-force {
                       type "boolean";
                       config "false";
                       description
                         "Flag indicating that the device is enabled to forcibly"+
                         " remove all the private AS numbers from the AS_Path "+
                         "list in received BGP update messages.";
                     }
                   }
                   container entropy-label-parameter {
                     when "../../../../../../../../ni:name='_public_'";
                     description
                       "Configure information about entropy label parameter "+
                       "configuration in a peer.";
                     leaf advertise-entropy-label {
                       type "peer-comm-config-type";
                       default "default";
                       description
                         "Enable the capability of advertising entropy labels.";
                     }
                     leaf padding {
                       when "../advertise-entropy-label='enable'";
                       type "string" {
                         length "1..32";
                         pattern "(([0-9A-F])*)";
                       }
                       description
                         "Padding format. The value is a hexadecimal string "+
                         "containing 1 to 32 characters (16 hexadecimal "+
                         "numbers). It cannot contain spaces, and can only "+
                         "contain uppercase letters (A to F) and digits (0 to "+
                         "9), and the length must be an even number.";
                     }
                     leaf attribute-type {
                       when "../advertise-entropy-label='enable'";
                       type "entropy-label-attribute-type";
                       mandatory "true";
                       description
                         "The attribute-type of advertising entropy labels.";
                     }
                     leaf entropy-label {
                       type "peer-comm-config-type";
                       default "default";
                       description
                         "Enable the function of delivering the entropy label "+
                         "capability to the forwarding plane.";
                     }
                     leaf effect-advertise-entropy-label {
                       type "boolean";
                       default "false";
                       config "false";
                       description
                         "Whether the capability of advertising entropy labels "+
                         "is enabled on the BGP peer.";
                     }
                     leaf effect-padding {
                       when "../effect-advertise-entropy-label='true'";
                       type "string" {
                         length "1..32";
                         pattern "(([0-9A-F])*)";
                       }
                       config "false";
                       description
                         "Padding format.";
                     }
                     leaf effect-attribute-type {
                       when "../effect-advertise-entropy-label='true'";
                       type "entropy-label-attribute-type";
                       config "false";
                       description
                         "The attribute-type of advertising entropy labels.";
                     }
                     leaf effect-entropy-label {
                       type "boolean";
                       default "false";
                       config "false";
                       description
                         "Whether the function of delivering the entropy label "+
                         "capability to the forwarding plane is enabled on the "+
                         "BGP peer.";
                     }
                   }
                   container path-attribute-treats {
                     description
                       "List of modes in which specified path attributes are "+
                       "processed.";
                     list path-attribute-treat {
                       must "discard-id-map or withdraw-id-map or unknown-id-map"+
                            "";
                       key "treat-type";
                       description
                         "Configure mode in which specified path attributes are "+
                         "processed.";
                       leaf treat-type {
                         type "bgp:path-attr-treat-type";
                         description
                           "Mode in which specified path attributes are "+
                           "processed.";
                       }
                       leaf discard-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a discard attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf withdraw-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a withdraw attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf unknown-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify an unknown attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                     }
                   }
                 }
                 container ipv4-multicast {
                   when "../type='ipv4multi'";
                   description
                     "Configure IPv4 multicast options.";
                   leaf group-name {
                     type "leafref" {
                       path "../../../../../../peer-groups/peer-group/name";
                     }
                     must "../../../../../../peer-groups/peer-group[name = "+
                          "current()]/afs/af[type = 'ipv4multi']";
                     must "../../../../../../peer-groups/peer-group[name = "+
                          "current()]/peer-establish-mode = 'static'";
                     description
                       "Configure a name for a peer group. After a peer is "+
                       "deleted from the peer group, the peer is disabled from "+
                       "the address family. The object cannot be modified.";
                     ext:operation-exclude "update" {
                       description
                         "The node cannot be modified, when the peer already "+
                         "belongs to a peer-group.";
                     }
                   }
                   leaf default-route-advertise {
                     type "boolean";
                     default "false";
                     description
                       "Enable/disable a device to advertise the default route "+
                       "to its peers. This option enables a device to send a "+
                       "default route with the device as the next hop address to"+
                       " its peers, regardless of whether there is a default "+
                       "route in the local routing table.";
                   }
                   choice default-route-advertise-policy-type {
                     description
                       "Set default route advertise-policy.";
                     case rtp-ref {
                       description
                         "The default-route-advertise-policy.";
                       leaf default-route-advertise-policy {
                         when "../default-route-advertise='true'";
                         type "leafref" {
                           path "/rtp:routing-policy/rtp:policy-definitions/rtp:"+
                                "policy-definition/rtp:name";
                         }
                         description
                           "Specify the name of a used policy.";
                       }
                     }
                     case xpl-ref {
                       description
                         "The default-route-advertise-filter.";
                       container default-route-advertise-filter {
                         when "../default-route-advertise='true'";
                         description
                           "Configure the route-filter for default route "+
                           "advertise.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                   leaf import-ip-prefix {
                     type "leafref" {
                       path "/rtp:routing-policy/rtp:ipv4-prefix-filters/rtp:ipv"+
                            "4-prefix-filter/rtp:name";
                     }
                     description
                       "Specify the IPv4 filtering policy applied to the routes "+
                       "received from a specified peer. By default, no such "+
                       "policy is specified.";
                   }
                   leaf export-ip-prefix {
                     type "leafref" {
                       path "/rtp:routing-policy/rtp:ipv4-prefix-filters/rtp:ipv"+
                            "4-prefix-filter/rtp:name";
                     }
                     description
                       "Specify the IPv4 filtering policy applied to the routes "+
                       "to be advertised to a specified peer. By default, no "+
                       "such policy is specified.";
                   }
                   leaf import-as-path-filter {
                     type "leafref" {
                       path "/rtp:routing-policy/rtp:as-path-filters/rtp:as-path"+
                            "-filter/rtp:name";
                     }
                     description
                       "Apply an AS_Path-based filtering policy to the routes "+
                       "received from a specified peer. The policy can be "+
                       "identified with a name or number, and the number ranges "+
                       "from 1 to 256. By default, no such policy is specified. "+
                       "Therefore, all BGP routes can be accepted.";
                   }
                   leaf export-as-path-filter {
                     type "leafref" {
                       path "/rtp:routing-policy/rtp:as-path-filters/rtp:as-path"+
                            "-filter/rtp:name";
                     }
                     description
                       "Apply an AS_Path-based filtering policy to the routes to"+
                       " be advertised to a specified peer. The policy can be "+
                       "identified with a name or number, and the number ranges "+
                       "from 1 to 256. By default, no such policy is specified. "+
                       "Therefore, all BGP routes can be advertised.";
                   }
                   leaf import-acl-name-or-num {
                     type "leafref" {
                       path "/acl:acl/acl:groups/acl:group/acl:identity";
                     }
                     description
                       "Specifies the name of the import ACL policy.";
                   }
                   leaf export-acl-name-or-num {
                     type "leafref" {
                       path "/acl:acl/acl:groups/acl:group/acl:identity";
                     }
                     description
                       "Specifies the name of the export ACL policy.";
                   }
                   leaf advertise-ext-community {
                     type "boolean";
                     default "false";
                     description
                       "Enable/disable advertise the extended community "+
                       "attribute to a peer or peer group.";
                   }
                   leaf discard-ext-community {
                     type "boolean";
                     default "false";
                     description
                       "Enable/disable discard the extended community attribute "+
                       "in the routing information about a specified peer.";
                   }
                   leaf allow-as-loop {
                     type "uint32" {
                       range "1..10";
                     }
                     description
                       "Allow repetitive local AS numbers. By default, "+
                       "repetitive local AS numbers are not allowed.";
                   }
                   leaf nexthop-configure {
                     type "nexthop-configuration-type";
                     must "../nexthop-configure='local'";
                     description
                       "Both the next-hop-local mode and next-hop-invariable "+
                       "mode are available when the peer address family is the "+
                       "VPNv4/VPNV6/L2VPN AD address family. Only the next-hop-l"+
                       "ocal mode is available when the peer address family is "+
                       "not VPNv4/VPNV6/L2VPN AD address family. In next-hop-loc"+
                       "al mode, you can configure a BGP speaker to set its IP "+
                       "address of as the next hop of the routes to be "+
                       "advertised to IBGP peers or IBGP peer groups. In "+
                       "next-hop-invariable mode, you can configure PEs in "+
                       "different ASs not to change the next hop of routes when "+
                       "the PEs advertise the routes to their EBGP peers and use"+
                       " the next hop addresses of IGP routes to advertise "+
                       "imported IGP routes to IBGP peers. By default, when a "+
                       "BGP speaker advertises routes to EBGP peers and imported"+
                       " IGP routes to IBGP peers, the BGP speaker changes the "+
                       "next hop to its interface address.";
                   }
                   leaf advertise-community {
                     type "boolean";
                     default "false";
                     description
                       "Enable/disable advertise the community attribute to a "+
                       "peer or a peer group.";
                   }
                   leaf keep-all-routes {
                     when "/bgp:bgp/bgp:base-process/bgp:keep-all-routes='false'"+
                          "";
                     type "boolean";
                     default "false";
                     description
                       "Enable/disable saving all the updated information about "+
                       "BGP routes from a specified peer or peer group after a "+
                       "BGP connection is established, even though these BGP "+
                       "routes fail to match the routing policy on the ingress. "+
                       "By default, the updated information about BGP routes "+
                       "from a specified peer is saved only when the routes "+
                       "match the routing policy on the ingress. If a router "+
                       "supports route refreshing, this option is not required.";
                   }
                   choice import-policy-type {
                     description
                       "Set route policy or filter.";
                     case rtp-ref {
                       description
                         "Route policy.";
                       leaf import-policy {
                         type "leafref" {
                           path "/rtp:routing-policy/rtp:policy-definitions/rtp:"+
                                "policy-definition/rtp:name";
                         }
                         description
                           "Specify the filtering policy applied to the routes "+
                           "learned from a peer. By default, no such policy is "+
                           "specified.";
                       }
                     }
                     case xpl-ref {
                       description
                         "Route filter.";
                       container import-filter {
                         description
                           "Configure an import route-filter to filter the "+
                           "routes received from a peer group. By default, no "+
                           "route-filter is specified to filter the routes "+
                           "imported from a peer group.";
                         leaf name {
                           type "leafref" {
                             path "/xpl:xpl/xpl:route-filters/xpl:route-filter/x"+
                                  "pl:name";
                           }
                           description
                             "Specify an import route-filter name.";
                         }
                         leaf parameter {
                           when "../name";
                           type "xpl:filter-parameter-type";
                           description
                             "Specify an import route-filter parameter.";
                         }
                       }
                     }
                   }
                   choice export-policy-type {
                     description
                       "Set route policy or filter.";
                     case rtp-ref {
                       description
                         "Route policy.";
                       leaf export-policy {
                         type "leafref" {
                           path "/rtp:routing-policy/rtp:policy-definitions/rtp:"+
                                "policy-definition/rtp:name";
                         }
                         description
                           "Specify the filtering policy applied to the routes "+
                           "to be advertised to a peer. By default, no such "+
                           "policy is specified.";
                       }
                     }
                     case xpl-ref {
                       description
                         "Route filter.";
                       container export-filter {
                         description
                           "Configure an export route-filter to filter the "+
                           "routes to be advertised to a peer group. By default,"+
                           " no route-filter is specified to filter the routes "+
                           "to be advertised to a peer group.";
                         leaf name {
                           type "leafref" {
                             path "/xpl:xpl/xpl:route-filters/xpl:route-filter/x"+
                                  "pl:name";
                           }
                           description
                             "Specify an export route-filter name.";
                         }
                         leaf parameter {
                           when "../name";
                           type "xpl:filter-parameter-type";
                           description
                             "Specify an export route-filter parameter.";
                         }
                       }
                     }
                   }
                   leaf reflect-client {
                     type "boolean";
                     default "false";
                     description
                       "Enable/disable the local device as a route reflector "+
                       "(RR) and a peer or peer group as its client. This "+
                       "configuration is applicable between IBGP peers only. The"+
                       " configurations of RRs and its clients in an address "+
                       "family are valid only in this address family. Therefore,"+
                       " it is recommended to configure RRs and its clients in "+
                       "the specified address family that is required.";
                   }
                   leaf load-balancing-enable {
                     type "boolean";
                     default "false";
                     description
                       "Enable/disable a neighbour to participate in load "+
                       "balancing.";
                   }
                   choice load-balancing-ignore-as-type {
                     description
                       "Set load balancing as path type.";
                     case as-attribute {
                       description
                         "Ignore the as-path attribute.";
                       leaf load-balancing-as-path-ignore {
                         when "../load-balancing-enable='true'";
                         type "empty";
                         description
                           "Configure BGP to ignore the AS_Path attribute when "+
                           "selecting the equal route. After as-path-neglect is "+
                           "selected, BGP does not compare the AS_Path length.";
                       }
                     }
                     case same-length-as-attribute {
                       description
                         "Ignore comparison of as-path attributes with the same "+
                         "length.";
                       leaf load-balancing-as-path-relax {
                         when "../load-balancing-enable='true'";
                         type "empty";
                         description
                           "Configure BGP to ignore comparison of AS_Path "+
                           "attributes with the same length when selecting the "+
                           "equal route. After as-path-neglect is selected, BGP "+
                           "does not compare the AS_Path length.";
                       }
                     }
                   }
                   leaf advertise-large-community {
                     type "bgp:peer-comm-config-type";
                     default "default";
                     description
                       "Enable large-community attribute advertisement. The "+
                       "Link-state address family and the RPD address family do "+
                       "not support this element.";
                   }
                   leaf advertise-large-community-state {
                     type "boolean";
                     default "false";
                     config "false";
                     description
                       "Whether large-community attribute advertisement is "+
                       "enabled on a peer. The Link-state address family and the"+
                       " RPD address family do not support this element.";
                   }
                   leaf route-update-interval {
                     type "uint16" {
                       range "0..600";
                     }
                     units "s";
                     description
                       "Specify the minimum interval at which Update packets are"+
                       " sent. By default, the interval at which Update packets "+
                       "are sent to IBGP peers is 15s, \nand the interval at "+
                       "which Update packets are sent to EBGP peers is 30s. When"+
                       " routes change, a router will send Update packets to "+
                       "notify its peers. \nIf a route changes frequently, you "+
                       "can set an interval at which Update packets are sent to "+
                       "prevent the router from sending Update packets each time"+
                       " the route changes. \nThis configuration is valid only "+
                       "to the routes learned from peers.";
                     ext:dynamic-default;
                   }
                   leaf preferred-value {
                     type "uint32" {
                       range "0..65535";
                     }
                     default "0";
                     description
                       "Assign a preferred value for the routes learned from a "+
                       "specified peer. After a preferred value is configured "+
                       "for the routes learned from a specified peer,\nall the "+
                       "routes that learnt from this peer will use this "+
                       "preferred value. When multiple routes reach the same "+
                       "address prefix, the route with the largest preferred "+
                       "value will be selected.";
                   }
                   leaf update-group-independent {
                     type "bgp:peer-comm-config-type";
                     default "default";
                     description
                       "Enable/disable the peer which can reside in an "+
                       "independent peer group.";
                   }
                   leaf update-group-independent-state {
                     type "boolean";
                     config "false";
                     description
                       "Whether the peer can reside in an independent peer "+
                       "group.";
                   }
                   container route-limit {
                     description
                       "Configure parameters of routes limited from this peer.";
                     leaf number {
                       type "uint32" {
                         range "1..4294967295";
                       }
                       description
                         "Configure the maximum number of routes that can be "+
                         "accepted from a peer.";
                     }
                     leaf percent {
                       when "../number";
                       type "uint8" {
                         range "1..100";
                       }
                       default "75";
                       description
                         "Specify the percentage of routes when a router starts "+
                         "to generate an alarm.";
                     }
                     leaf type {
                       when "../number";
                       type "bgp:route-limit-type";
                       must "(../type='idle-timeout' and ../idle-timeout) or "+
                            "(../type!='idle-timeout')";
                       default "noparameter";
                       description
                         "Set the processing method as alert-only, idle-forever,"+
                         " or idle-timeout when the number of routes exceeds the"+
                         " set threshold. When alert-only is used, only an alarm"+
                         " is generated when the number of routes exceeds the "+
                         "threshold. In this case, new routes are no longer "+
                         "accepted. When idle-forever is used, connections are "+
                         "not automatically reestablished after being cut off "+
                         "until BGP connections are reset if the number of "+
                         "routes exceeds the set threshold. When idle-timeout is"+
                         " used and the idle-timeout timer is specified, the "+
                         "connections are automatically reestablished after "+
                         "being cut off if the number of routes exceeds the set "+
                         "threshold. You can reset BGP connections to reestablis"+
                         "h the connections before the idle-timeout times "+
                         "expires.";
                     }
                     leaf idle-timeout {
                       when "../type='idle-timeout'";
                       type "uint16" {
                         range "1..1200";
                       }
                       units "min";
                       description
                         "Specify the value of the idle-timeout timer to "+
                         "automatically reestablish the connections after they "+
                         "are cut off when the number of routes exceeds the set "+
                         "threshold.";
                     }
                   }
                   container public-as-only {
                     description
                       "Configure BGP Remove private AS number from outbound "+
                       "updates parameters.";
                     leaf enable {
                       type "boolean";
                       default "false";
                       description
                         "Enable/disable BGP to send Update packets carrying "+
                         "only public AS numbers.";
                     }
                     choice remove-private-as {
                       description
                         "Remove AS numbers except peer AS number from outbound "+
                         "updates.";
                       case all {
                         description
                           "Remove all private AS numbers.";
                         leaf force {
                           when "../enable='true'";
                           type "empty";
                           description
                             "Configures BGP to carry only the public AS number "+
                             "instead of the private AS number when BGP sends "+
                             "Update packets. By default, BGP can carry the "+
                             "private AS number when BGP sends Update packets.";
                         }
                       }
                       case left-most {
                         description
                           "Remove the left-most private AS numbers.";
                         leaf limited {
                           when "../enable='true'";
                           type "empty";
                           description
                             "When the BGP sends update packets, the left ends "+
                             "of both the local AS and public AS do not carry "+
                             "the private AS. By default, BGP can carry the "+
                             "private AS number when BGP sends Update packets.";
                         }
                       }
                     }
                     leaf replace {
                       when "../force or ../limited";
                       type "boolean";
                       default "false";
                       description
                         "Enable/disable the function to the private AS is "+
                         "replaced by the local AS when the BGP sends update "+
                         "packets.";
                     }
                     leaf no-skip-as {
                       when "../force or ../limited";
                       type "boolean";
                       default "false";
                       description
                         "Enable/disable the function to the neighbour AS is not"+
                         " processed when the BGP sends update packets.";
                     }
                   }
                   container public-as-only-import {
                     description
                       "Configure BGP remove private AS number in received BGP "+
                       "update messages parameters.";
                     leaf enable {
                       type "bgp:peer-comm-config-type";
                       default "default";
                       description
                         "Enable/disable BGP to receive update packets carrying "+
                         "only public AS numbers.";
                     }
                     choice remove-private-as {
                       description
                         "Remove private AS numbers in received BGP update "+
                         "messages.";
                       case all {
                         description
                           "Forcibly delete all the private AS numbers in the "+
                           "AS_Path list.";
                         leaf force {
                           when "../enable = 'enable'";
                           type "empty";
                           description
                             "Enable a device to forcibly remove all the private"+
                             " AS numbers in received BGP update messages in "+
                             "which the AS_Path list contains private AS "+
                             "numbers. By default, a device does not remove "+
                             "private AS numbers from the AS_Path list when "+
                             "receiving BGP update messages.";
                         }
                       }
                     }
                     leaf effect-enable {
                       type "boolean";
                       config "false";
                       description
                         "Flag indicating that the device is enabled to remove "+
                         "private AS numbers from the AS_Path list in received "+
                         "BGP update messages.";
                     }
                     leaf effect-force {
                       type "boolean";
                       config "false";
                       description
                         "Flag indicating that the device is enabled to forcibly"+
                         " remove all the private AS numbers from the AS_Path "+
                         "list in received BGP update messages.";
                     }
                   }
                   container path-attribute-treats {
                     description
                       "List of modes in which specified path attributes are "+
                       "processed.";
                     list path-attribute-treat {
                       must "discard-id-map or withdraw-id-map or unknown-id-map"+
                            "";
                       key "treat-type";
                       description
                         "Configure mode in which specified path attributes are "+
                         "processed.";
                       leaf treat-type {
                         type "bgp:path-attr-treat-type";
                         description
                           "Mode in which specified path attributes are "+
                           "processed.";
                       }
                       leaf discard-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a discard attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf withdraw-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify a withdraw attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                       leaf unknown-id-map {
                         type "pub-type:id-range" {
                           pattern "((25[0-5]|2[0-4][0-9]|1[0-9][0-9]|[1-9][0-9]"+
                                   "|[0-9])?(-(25[0-5]|2[0-4][0-9]|1[0-9][0-9]|["+
                                   "1-9][0-9]|[0-9]))?(,((25[0-5]|2[0-4][0-9]|1["+
                                   "0-9][0-9]|[1-9][0-9]|[0-9])(-(25[0-5]|2[0-4]"+
                                   "[0-9]|1[0-9][0-9]|[1-9][0-9]|[0-9]))?))*)|(("+
                                   "([\\+|\\-](25[0-5]|2[0-4][0-9]|1[0-9][0-"+
                                   "9]|[1-9][0-9]|[0-9]))|([\\+|\\-]\\((25"+
                                   "[0-5]|2[0-4][0-9]|1[0-9][0-9]|[1-9][0-9]|[0-"+
                                   "9])-(25[0-5]|2[0-4][0-9]|1[0-9][0-9]|[1-9][0"+
                                   "-9]|[0-9])\\)))?(,(([\\+|\\-](25[0-5]|"+
                                   "2[0-4][0-9]|1[0-9][0-9]|[1-9][0-9]|[0-9]))|("+
                                   "[\\+|\\-]\\((25[0-5]|2[0-4][0-9]|1[0-9"+
                                   "][0-9]|[1-9][0-9]|[0-9])-(25[0-5]|2[0-4][0-9"+
                                   "]|1[0-9][0-9]|[1-9][0-9]|[0-9])\\))))*)";
                           ext:value-range "0..255";
                         }
                         description
                           "Specify an unknown attribute ID list. The attribute "+
                           "IDs which are not supported as follows: 1 (ORIGIN), "+
                           "2 (AS_PATH), 3 (NEXT_HOP), 4 (MED), 5 (LOCAL_PREF), "+
                           "6 (ATOMICAGGREGATE), 7 (AGGREGATOR), 8 (COMMUNITY), "+
                           "9 (ORIGINATOR_ID), 10 (CLUSTER_LIST), 14 (MP_REACH_N"+
                           "LRI), 15 (MP_UNREACH_NLRI), 17 (AS4PATH), 18 "+
                           "(AS4AGGREGATOR).";
                       }
                     }
                   }
                 }
                 container state {
                   config "false";
                   description
                     "Operational state of peer information.";
                   leaf type {
                     type "peer-type-info";
                     config "false";
                     description
                       "Configures the type of BGP peers: IBGP or EBGP.";
                   }
                   leaf version {
                     type "uint8";
                     config "false";
                     description
                       "The current BGP version is BGP-4. BGP-4 provides a set "+
                       "of new mechanisms to support Classless Inter-Domain "+
                       "Routing (CIDR). The new mechanisms also support the "+
                       "network prefix-based advertisement, cancellation of the "+
                       "'class' concept for a BGP network during the network "+
                       "prefix-supported advertisements, and route summarization"+
                       " and AS path summarization.";
                   }
                   leaf remote-router-id {
                     type "inet:ipv4-address-no-zone";
                     config "false";
                     description
                       "Router ID for a peer.";
                   }
                   leaf current-state {
                     type "peer-state";
                     config "false";
                     description
                       "Current BGP state, which can be Idle, Active, Establishe"+
                       "d, Connect, OpenSent, or OpenConfirm.\nIdle: In this "+
                       "state, BGP denies all connection requests. This is the "+
                       "initial state of BGP.\nActive: In this state, BGP tries "+
                       "to establish TCP connections. This is the intermediate "+
                       "state of BGP.\nEstablished: In this state, BGP peers can"+
                       " exchange Update, Notification, and Keepalive packets "+
                       "with each other.\nConnect: In this state, BGP determines"+
                       " the subsequent operation after the TCP connections are "+
                       "established.\nOpenSent: In this state, BGP is waiting "+
                       "for the Open packet from the peer.\nOpenConfirm: In this"+
                       " state, BGP is waiting for a Notification packet and a "+
                       "Keepalive packet.";
                   }
                   leaf local-port {
                     type "uint32";
                     config "false";
                     description
                       "Local port number. BGP uses TCP as the transport layer "+
                       "protocol, and the port number of the TCP connection "+
                       "initiator is 179.";
                   }
                   leaf remote-port {
                     type "uint32" {
                       range "0..4294967295";
                     }
                     config "false";
                     description
                       "Port number for a peer to establish a peer relationship."+
                       "";
                   }
                   leaf current-event {
                     type "string" {
                       length "1..39";
                     }
                     config "false";
                     description
                       "Recent event that occurs on a peer.";
                   }
                   leaf last-state {
                     type "peer-state";
                     config "false";
                     description
                       "Last state of a peer, which can be Idle, Connect, "+
                       "Active, OpenSent, OpenConfirm, or Established.";
                   }
                   leaf up-down-duration {
                     type "string" {
                       length "1..49";
                     }
                     config "false";
                     description
                       "Duration in which a BGP peer is in the Up or Down "+
                       "state.\nThe Up state indicates the established state, "+
                       "and the Down state indicates a non-established state "+
                       "(including the Idle, Active, Connect, OpenSent and "+
                       "OpenConfirm state). When the state is switched between "+
                       "Up and Down, the upDownDuration timer is reset and "+
                       "starts from 0.";
                   }
                   leaf send-message {
                     type "uint32" {
                       range "0..4294967295";
                     }
                     config "false";
                     description
                       "Number of messages sent to the peer.";
                   }
                   leaf rpd-capability {
                     type "rpd-cap-type";
                     config "false";
                     description
                       "Peer route-policy distribute capability.";
                   }
                   leaf local-rpd-capability {
                     type "rpd-cap-type";
                     config "false";
                     description
                       "Local route-policy distribute capability.";
                   }
                   leaf negotiate-rpd-capability {
                     type "rpd-cap-type";
                     config "false";
                     description
                       "Negotiated route-policy distribute capability.";
                   }
                   leaf receive-message {
                     type "uint32" {
                       range "0..4294967295";
                     }
                     config "false";
                     description
                       "Number of messages received from the peer.";
                   }
                   leaf out-queue {
                     type "uint32" {
                       range "0..4294967295";
                     }
                     config "false";
                     description
                       "Number of messages to be sent in a queue.";
                   }
                   leaf receive-hold-time {
                     type "uint32" {
                       range "0..65535";
                     }
                     units "s";
                     config "false";
                     description
                       "Hold time of a peer.";
                   }
                   leaf receive-last-keepalive-time {
                     type "yang:date-and-time";
                     config "false";
                     description
                       "Last time when Keepalive packets were received from a "+
                       "peer.";
                   }
                   leaf negotiate-hold-time {
                     type "uint32" {
                       range "0..65535";
                     }
                     units "s";
                     config "false";
                     description
                       "Hold time negotiated by BGP peers.";
                   }
                   leaf negotiate-keepalive-time {
                     type "uint32" {
                       range "0..21845";
                     }
                     units "s";
                     config "false";
                     description
                       "Keepalive time negotiated by BGP peers.";
                   }
                   leaf receive-update-count {
                     type "uint32" {
                       range "0..4294967295";
                     }
                     config "false";
                     description
                       "Number of Update packets received from a peer.";
                   }
                   leaf receive-open-count {
                     type "uint32" {
                       range "0..4294967295";
                     }
                     config "false";
                     description
                       "Number of Open packets received from a peer.";
                   }
                   leaf receive-keepalive-count {
                     type "uint32" {
                       range "0..4294967295";
                     }
                     config "false";
                     description
                       "Number of Keepalive packets received from a peer.";
                   }
                   leaf receive-notification-count {
                     type "uint32" {
                       range "0..4294967295";
                     }
                     config "false";
                     description
                       "Number of Notification packets received from a peer.";
                   }
                   leaf receive-route-refresh-count {
                     type "uint32" {
                       range "0..4294967295";
                     }
                     config "false";
                     description
                       "Number of Route-Refresh packets received from a peer.";
                   }
                   leaf send-update-count {
                     type "uint32" {
                       range "0..4294967295";
                     }
                     config "false";
                     description
                       "Number of Update packets sent to a peer.";
                   }
                   leaf send-open-count {
                     type "uint32" {
                       range "0..4294967295";
                     }
                     config "false";
                     description
                       "Number of Open packets sent to a peer.";
                   }
                   leaf send-keepalive-count {
                     type "uint32" {
                       range "0..4294967295";
                     }
                     config "false";
                     description
                       "Number of Keepalive packets sent to a peer.";
                   }
                   leaf send-notification-count {
                     type "uint32" {
                       range "0..4294967295";
                     }
                     config "false";
                     description
                       "Number of Notification packets sent to a peer.";
                   }
                   leaf send-route-refresh-count {
                     type "uint32" {
                       range "0..4294967295";
                     }
                     config "false";
                     description
                       "Number of Route-Refresh packets sent to a peer.";
                   }
                   leaf send-graceful-restart-capability {
                     type "boolean";
                     config "false";
                     description
                       "Whether the local end supports the GR (Graceful Restart)"+
                       " capability.";
                   }
                   leaf receive-refresh-capability {
                     type "boolean";
                     config "false";
                     description
                       "Whether the peer supports RR.";
                   }
                   leaf receive-four-byte-as-capability {
                     type "boolean";
                     config "false";
                     description
                       "Whether the peer supports 4-byte AS numbers.";
                   }
                   leaf receive-multi-protocol-capability {
                     type "boolean";
                     config "false";
                     description
                       "Whether the peer supports MP.";
                   }
                   leaf receive-graceful-restart-capability {
                     type "boolean";
                     config "false";
                     description
                       "Whether the peer supports GR.";
                   }
                   leaf receive-add-path {
                     type "string" {
                       length "1..50";
                     }
                     config "false";
                     description
                       "Whether the peer supports Add-Path.";
                   }
                   leaf negotiate-add-path {
                     type "string" {
                       length "1..50";
                     }
                     config "false";
                     description
                       "Negotiated Add-Path.";
                   }
                   leaf receive-label-add-path {
                     type "string" {
                       length "1..50";
                     }
                     config "false";
                     description
                       "Whether the peer supports labeled Add-Path.";
                   }
                   leaf negotiate-label-add-path {
                     type "string" {
                       length "1..50";
                     }
                     config "false";
                     description
                       "Negotiated Label Add-Path.";
                   }
                   leaf receive-prefix {
                     type "uint32" {
                       range "0..4294967295";
                     }
                     config "false";
                     description
                       "Number of received route prefixes.";
                   }
                   leaf receive-active-prefix {
                     type "uint32" {
                       range "0..4294967295";
                     }
                     config "false";
                     description
                       "Number of received prefixes of active routes.";
                   }
                   leaf advertise-prefix {
                     type "uint32" {
                       range "0..4294967295";
                     }
                     config "false";
                     description
                       "Number of advertised route prefixes.";
                   }
                   leaf check-first-as {
                     type "first-as-state";
                     config "false";
                     description
                       "Check the first AS in the AS_Path of the update messages"+
                       " from EBGP peers.";
                   }
                   leaf extend-nexthop-capability {
                     type "boolean";
                     config "false";
                     description
                       "Peer extended next hop encoding capability.";
                   }
                   leaf egress-engineer-capability {
                     type "boolean";
                     config "false";
                     description
                       "Whether the peer supports EPE.";
                   }
                   leaf orf-capability {
                     type "boolean";
                     config "false";
                     description
                       "Whether the peer supports VPN orf capability.";
                   }
                   leaf remote-as {
                     type "string" {
                       length "1..11";
                     }
                     config "false";
                     description
                       "AS number of the BGP peer.";
                   }
                   leaf memory-priority {
                     type "memory-priority";
                     description
                       "Priority that is used to determine the disconnection "+
                       "order of a BGP peer relationship if memory overload "+
                       "occurs.";
                   }
                   leaf region-id {
                     ext:support-filter "true";
                     type "uint32" {
                       range "1..65535";
                     }
                     description
                       "Region ID.";
                   }
                   leaf region-confederation-id {
                     type "uint32" {
                       range "1..65535";
                     }
                     description
                       "Region confederation ID.";
                   }
                 }
               }
             }
           }
         }
         container peer-bfd-session-states {
           config "false";
           description
             "List of BFD sessions.";
           list peer-bfd-session-state {
             key "address";
             config "false";
             description
               "Operational state of BFD session.";
             leaf address {
               type "inet:ip-address-no-zone";
               config "false";
               description
                 "Peer address of the BFD session.";
             }
             leaf local-address {
               type "inet:ip-address-no-zone";
               config "false";
               description
                 "Local address of the BFD session.";
             }
             leaf if-name {
               type "pub-type:if-name";
               config "false";
               description
                 "Name of an interface of the BFD session.";
             }
             leaf tx-interval {
               type "uint32";
               units "ms";
               default "0";
               config "false";
               description
                 "Interval at which BFD packets are sent.";
             }
             leaf rx-interval {
               type "uint32";
               units "ms";
               default "0";
               config "false";
               description
                 "Interval at which BFD packets are received.";
             }
             leaf multiplier {
               type "uint32" {
                 range "0..50";
               }
               config "false";
               description
                 "Detection multiplier.";
             }
             leaf status {
               type "bfd-state";
               config "false";
               description
                 "State of the BFD session.";
             }
             leaf global-bfd-enable {
               type "boolean";
               config "false";
               description
                 "Global BFD state.";
             }
             leaf valid-ttl-hops {
               type "uint8" {
                 range "1..255";
               }
               config "false";
               description
                 "The valid TTL hops value.";
             }
           }
         }
         container egress-engineer-peer-sets {
           when "../../../ni:name='_public_'";
           description
             "List of peer set information under BGP instance.";
           list egress-engineer-peer-set {
             key "peer-set-name";
             description
               "Configure peer set information.";
             leaf peer-set-name {
               type "string" {
                 length "1..63";
               }
               description
                 "The name for peer set.";
             }
             leaf static-label {
               type "uint32" {
                 range "16..32783";
               }
               description
                 "The static label for peer set. The value range and default "+
                 "value are controlled by the PAF.";
             }
             leaf label-pop {
               when "../static-label";
               type "boolean";
               must "not(../relate-bfd='true' and ../label-pop='true')";
               default "false";
               description
                 "Enable/disable the BGP-EPE label popping function.";
             }
             leaf relate-bfd {
               type "boolean";
               must "not(../relate-bfd='true' and ../label-pop='true')";
               default "false";
               description
                 "Enable/disable association between the BGP-EPE label and BFD "+
                 "status.";
             }
           }
         }
       }
       container instance-processs {
         description
           "List of all BGP instances.";
         list instance-process {
           key "name";
           max-elements "1";
           description
             "Configure a BGP instance.";
           ext:generated-by "system" {
             description
               "The BGP public instance is generated automatically when BGP "+
               "instances is enabled.";
           }
           leaf name {
             type "leafref" {
               path "/bgp:bgp/bgp:instance-processs/bgp:instance-process/bgp:nam"+
                    "e";
             }
             description
               "Name of BGP Site.";
           }
           leaf router-id {
             type "inet:ipv4-address-no-zone";
             description
               "ID of a router that is in IPv4 address format. Certain dynamic "+
               "routing protocols require a router ID. If no router ID is "+
               "specified for a router when these protocols are enabled, the "+
               "router ID in the RM module is used by default. The default "+
               "router ID in the RM module is 0.0.0.0 when the router is not "+
               "configured with any interface. \nThe rules for selecting a "+
               "router ID are as follows:\n1. If you set a router ID through "+
               "this configuration, the set router ID is used. If the router ID "+
               "is not set, you need to select a router ID according to the "+
               "following rules:\n(1) If loopback interfaces configured with IP "+
               "addresses exist, the largest IP address among the IP addresses "+
               "of the loopback interfaces is selected as the router ID.\n(2) If"+
               " no loopback interface configured with an IP address exists, the"+
               " largest IP address among the IP addresses of other interfaces "+
               "is selected as the router ID, regardless of whether the "+
               "interface is Up.\nThe router ID is reselected only when the "+
               "interface address that is selected as the router ID is deleted "+
               "or changed. The router ID is not reselected in any of the "+
               "following cases:\na. The interface is Down.\nb. A loopback "+
               "interface is configured when the IP address of a non-loopback "+
               "interface is selected as the router ID.\nc. A larger IP address "+
               "of an interface is configured.\n2. Each VPN instance selects the"+
               " router ID from the addresses of the interfaces of the VPN "+
               "instance according to the preceding rules.\n3. When both the AMB"+
               " and SMB exist on the router, the system backs up the router ID "+
               "set through the related command and the router ID that is "+
               "selected from IP addresses of the interfaces. After the "+
               "active/standby switchover is performed, the system checks the "+
               "validity of the router ID selected from the interface addresses."+
               " If the router ID is invalid, the system reselects a router ID.";
           }
           leaf effect-router-id {
             type "inet:ipv4-address-no-zone";
             default "0.0.0.0";
             config "false";
             description
               "Router ID that takes effect.";
           }
           container afs {
             description
               "List of BGP address family instances.";
             list af {
               key "type";
               description
                 "Configure BGP address family instance.";
               leaf type {
                 type "enumeration" {
                   enum "ipv4uni" {
                     value "1";
                     description
                       "IPv4 unicast address family.";
                   }
                   enum "ipv4vpn" {
                     value "3";
                     description
                       "IPv4 VPN address family.";
                   }
                 }
                 description
                   "Address family type of a BGP instance.";
               }
               container ipv4-unicast {
                 when "../type = 'ipv4uni' and ../../../../../../ni:name!='_publ"+
                      "ic_'";
                 must "../../../../../../l3vpn:afs/l3vpn:af[l3vpn:type='ipv4-uni"+
                      "cast']";
                 description
                   "Configure IPv4 unicast options.";
                 container common {
                   description
                     "Configure IPv4 unicast common options.";
                   leaf route-select-delay {
                     type "uint16" {
                       range "0..3600";
                     }
                     units "s";
                     default "0";
                     description
                       "Route selection delay.";
                   }
                   choice reflector-type {
                     description
                       "Set IPv4 address or id.";
                     case address {
                       description
                         "IPv4 address.";
                       leaf reflector-cluster-ipv4 {
                         type "inet:ipv4-address-no-zone";
                         description
                           "Set a cluster ID. The value is expressed in the "+
                           "format of an IPv4 address. Configuring multiple RRs "+
                           "in a cluster can enhance the stability of the "+
                           "network. If a cluster has more than one RR, select "+
                           "this option to set the same cluster ID for all the "+
                           "RRs to avoid routing loops. To allow clients to "+
                           "receive routes from RRs, ensure that the cluster ID "+
                           "of the RRs is different from the router ID of any "+
                           "client. If the cluster ID of the RRs is the same as "+
                           "the router ID of a client, the client will discard "+
                           "received routes.";
                       }
                     }
                     case id {
                       description
                         "Set value.";
                       leaf reflector-cluster-id {
                         type "uint32" {
                           range "1..4294967295";
                         }
                         description
                           "Set a cluster ID. Configuring multiple RRs in a "+
                           "cluster can enhance the stability of the network. If"+
                           " a cluster has more than one RR, select this option "+
                           "to set the same cluster ID for all the RRs to avoid "+
                           "routing loops. To allow clients to receive routes "+
                           "from RRs, ensure that the cluster ID of the RRs is "+
                           "different from the router ID of any client. If the "+
                           "cluster ID of the RRs is the same as the router ID "+
                           "of a client, the client will discard received "+
                           "routes.";
                       }
                     }
                   }
                   leaf reflect-change-path {
                     type "boolean";
                     default "false";
                     description
                       "Enable/disable an RR to use an export policy to change "+
                       "route AS_Path.";
                   }
                   leaf always-compare-med {
                     type "boolean";
                     default "false";
                     description
                       "Enable/disable BGP to compare the MEDs of routes from "+
                       "peers in different ASs in route selection. If \nthere "+
                       "are multiple reachable routes to the same destination, "+
                       "the route with the smallest MED is preferred. Do not use"+
                       " this option unless different ASs use the same IGP and "+
                       "route selection mode.";
                   }
                   leaf default-med {
                     type "uint32";
                     default "0";
                     description
                       "Specify the Multi-Exit-Discriminator (MED) of BGP "+
                       "routes. The value is an integer. This value is valid "+
                       "only for the imported routes and BGP summarized routes "+
                       "on the local router.";
                   }
                   leaf nexthop-third-party {
                     type "boolean";
                     default "false";
                     description
                       "Enable/disable BGP third-party next hop.";
                   }
                   leaf default-local-preference {
                     type "uint32" {
                       range "0..4294967295";
                     }
                     default "100";
                     description
                       "The local preference of BGP routes.";
                   }
                   leaf default-route-import {
                     type "boolean";
                     default "false";
                     description
                       "Enable/disable the function to import default routes "+
                       "into the BGP routing table. Default-route-imported must "+
                       "be used with import-routes so that default routes can be"+
                       " imported to the BGP routing table. If only import-route"+
                       "s is used, no default routes can be added to the BGP "+
                       "routing table. In addition, default-route-imported can "+
                       "only import the default routes in the routing table into"+
                       " the BGP routing table.";
                   }
                   leaf routerid-neglect {
                     type "boolean";
                     default "false";
                     description
                       "Enable/disable BGP to ignore router IDs when selecting "+
                       "the optimal route. Comparing router IDs is the last "+
                       "resort in route selection. This means that if one "+
                       "optimal route must be selected and no other parameters "+
                       "can be used to break the tie, router IDs can be used. If"+
                       " this option is selected, the first received route will "+
                       "be selected as the optimal route, and BGP will ignore "+
                       "the router ID and peer address in route selection.";
                   }
                   leaf reflect-between-client {
                     type "boolean";
                     default "true";
                     description
                       "Enable/disable route reflection between clients. If "+
                       "clients of a route reflector (RR) are fully meshed, you "+
                       "can disable route reflection among clients to reduce the"+
                       " cost.";
                   }
                   leaf ext-community-change {
                     type "boolean";
                     default "false";
                     description
                       "Enable/disable the function to change the extended "+
                       "community attribute.";
                   }
                   leaf active-route-advertise {
                     type "boolean";
                     default "false";
                     description
                       "Enable/disable the function to advertise the optimal "+
                       "routes in the RM module to peers.";
                   }
                   leaf ebgp-interface-sensitive {
                     type "boolean";
                     default "true";
                     description
                       "Enable/disable the function of EBGP interface fast "+
                       "sensing. If this function is enabled, the sessions of "+
                       "directly connected EBGP peers are immediately cleared "+
                       "from the associated interface when the interface becomes"+
                       " down.";
                   }
                   leaf auto-frr {
                     type "boolean";
                     default "false";
                     description
                       "Enable/disable BGP Auto FRR. If IP FRR, VPN FRR, and "+
                       "Auto FRR are all enabled, IP FRR and VPN FRR take "+
                       "precedence over Auto FRR. If a route fails to match the "+
                       "routing policy of IP FRR or VPN FRR, Auto FRR takes "+
                       "effect.";
                   }
                   leaf nexthop-resolve-aigp {
                     type "boolean";
                     default "false";
                     description
                       "Enable/disable route with AIGP attribute for route "+
                       "selection.";
                   }
                   leaf summary-automatic {
                     type "boolean";
                     default "false";
                     description
                       "Enable/disable automatic summarization for imported "+
                       "routes. Manual summarization takes precedence over "+
                       "automatic summarization. After automatic summarization "+
                       "is enabled, BGP summarizes routes based on the natural "+
                       "network segment (for example, 10.1.1.1/24 and 10.2.1.1/2"+
                       "4 are summarized into 10.0.0.0/8, a Class A address), "+
                       "and sends only the summarized route to peers. This "+
                       "reduces the number of routes.";
                   }
                   leaf supernet-unicast-advertise {
                     type "boolean";
                     default "false";
                     description
                       "Enable/disable the function to advertise supernet "+
                       "unicast routes.";
                   }
                   leaf supernet-label-advertise {
                     type "boolean";
                     default "true";
                     description
                       "Enable/disable the function to advertise supernet "+
                       "labeled routes.";
                   }
                   leaf label-free-delay {
                     type "uint8" {
                       range "0..180";
                     }
                     units "s";
                     default "0";
                     description
                       "Label Free Delay.";
                   }
                   leaf attribute-set-enable {
                     type "boolean";
                     default "false";
                     description
                       "Enable/disable the capability of processing attribute "+
                       "set.";
                   }
                   leaf attribute-set-mode {
                     when "../attribute-set-enable='true'";
                     type "bgp:attribute-set-type";
                     default "both";
                     description
                       "The processing mode of attribute set.";
                   }
                   leaf best-route-bit-error-detection {
                     type "boolean";
                     default "false";
                     description
                       "Enable/disable the function to reroute traffic when a "+
                       "bit error event occurs.";
                   }
                   leaf bestroute-med-plus-igp {
                     type "boolean";
                     must "not(../bestroute-igp-metric-ignore='true' and "+
                          "../bestroute-med-plus-igp='true')";
                     default "false";
                     description
                       "Enable/disable the function to add the IGP cost to the "+
                       "next-hop destination to the MED before comparing MED "+
                       "values for path selection.";
                   }
                   leaf bestroute-med-multiplier {
                     when "../bestroute-med-plus-igp='true'";
                     type "uint16" {
                       range "1..1000";
                     }
                     default "1";
                     description
                       "Value of med product factor.";
                   }
                   leaf bestroute-igp-multiplier {
                     when "../bestroute-med-plus-igp='true'";
                     type "uint16" {
                       range "1..1000";
                     }
                     default "1";
                     description
                       "Value of IGP cost product factor.";
                   }
                   leaf bestroute-igp-metric-ignore {
                     type "boolean";
                     default "false";
                     description
                       "Enable/disable BGP to ignore the IGP cost of each BGP "+
                       "route to the next hop in route selection. By default, a "+
                       "BGP route with a smaller IGP cost to the next hop is "+
                       "preferred.";
                     must "not(../bestroute-igp-metric-ignore='true' and "+
                          "../bestroute-med-plus-igp='true')";
                   }
                   leaf bestroute-router-id-prior-clusterlist {
                     type "boolean";
                     default "false";
                     description
                       "Enable/disable BGP to compare originator before "+
                       "clusterlist in route selection.";
                   }
                   leaf bestroute-med-none-as-maximum {
                     type "boolean";
                     default "false";
                     description
                       "Enable/disable BGP considers its MED as the largest MED "+
                       "value (4294967295). If a route does not carry MED, BGP "+
                       "considers its MED as the default value (0) during route "+
                       "selection.";
                   }
                   leaf maximum-load-balancing-ibgp {
                     type "uint16" {
                       range "1..128";
                     }
                     must "not (../maximum-load-balancing>1 or ../maximum-load-b"+
                          "alancing-eibgp or ../load-balancing-eibgp-enable='tru"+
                          "e') or ../maximum-load-balancing-ibgp=1";
                     default "1";
                     description
                       "Specify the maximum number of equal-cost IBGP routes. "+
                       "The value range and default value are controlled by the "+
                       "PAF.";
                   }
                   leaf maximum-load-balancing-ebgp {
                     type "uint16" {
                       range "1..128";
                     }
                     must "not (../maximum-load-balancing>1 or ../maximum-load-b"+
                          "alancing-eibgp or ../load-balancing-eibgp-enable='tru"+
                          "e') or ../maximum-load-balancing-ebgp=1";
                     default "1";
                     description
                       "Specify the maximum number of equal-cost EBGP routes. "+
                       "The value range and default value are controlled by the "+
                       "PAF.";
                   }
                   leaf bestroute-as-path-ignore {
                     type "boolean";
                     must "../bestroute-as-path-ignore = 'false' or ../load-bala"+
                          "nc-as-path-ignore ='false'";
                     default "false";
                     description
                       "Enable/disable BGP to ignore the AS_Path attribute when "+
                       "selecting the optimal route. By default, BGP uses the "+
                       "AS_Path attribute as one of route selection rules, and a"+
                       " route with a shorter AS_Path is preferred. After "+
                       "bestroute-as-path-ignore is selected, BGP does not "+
                       "compare the AS_Path length.";
                   }
                   leaf load-balanc-igp-metric-ignore {
                     type "boolean";
                     default "false";
                     description
                       "Enable/disable BGP to ignore the IGP cost of each BGP "+
                       "route to the next hop when selecting routes for load "+
                       "balancing. By default, only the routes with the same IGP"+
                       " cost can participate in load balancing.";
                   }
                   leaf load-balanc-as-path-ignore {
                     type "boolean";
                     must "../load-balanc-as-path-ignore ='false' or (../load-ba"+
                          "lanc-as-path-relax ='false' and ../bestroute-as-path-"+
                          "ignore ='false')";
                     default "false";
                     description
                       "Enable/disable BGP to ignore the AS_Path of each BGP "+
                       "route to the next hop when selecting routes for load "+
                       "balancing. By default, only the routes with the same "+
                       "AS_Path can participate in load balancing.";
                   }
                   leaf load-balanc-as-path-relax {
                     type "boolean";
                     must "../load-balanc-as-path-relax ='false' or ../load-bala"+
                          "nc-as-path-ignore ='false'";
                     default "false";
                     description
                       "Enable/disable BGP to ignore comparison of AS_Path "+
                       "attributes with the same length. By default, only the "+
                       "routes with the same AS_Path can participate in load "+
                       "balancing.";
                   }
                   leaf maximum-load-balancing {
                     type "uint16" {
                       range "1..128";
                     }
                     must "not (../maximum-load-balancing-ibgp>1 or ../maximum-l"+
                          "oad-balancing-ebgp>1 or ../maximum-load-balancing-eib"+
                          "gp) or ../maximum-load-balancing=1";
                     default "1";
                     description
                       "Specify the maximum number of equal-cost routes in the "+
                       "BGP routing table. The value can be 1 or an integer "+
                       "greater than 1. The value depends on the associated "+
                       "license. Equal-cost BGP routes can be generated for load"+
                       " balancing only when the BGP routes meet the first nine "+
                       "rules of the route-selection policy and have the same "+
                       "AS-Path attribute. The value range and default value are"+
                       " controlled by the PAF.";
                   }
                   leaf ebgp-ecmp-nexthop-changed {
                     when "../maximum-load-balancing-ebgp and ../maximum-load-ba"+
                          "lancing-ebgp>1";
                     type "boolean";
                     default "false";
                     description
                       "Enable/disable next hop of equal-cost EBGP routes is "+
                       "changed. When equal-cost EBGP routes are load-balancing "+
                       "traffic, the next hop of these routes is changed to a "+
                       "local interface before these routes are advertised. This"+
                       " function can be enabled only when the maximum number of"+
                       " equal-cost EBGP routes is greater than 1.";
                   }
                   leaf ibgp-ecmp-nexthop-changed {
                     when "../maximum-load-balancing-ibgp and ../maximum-load-ba"+
                          "lancing-ibgp>1";
                     type "boolean";
                     default "false";
                     description
                       "Enable/disable next hop of equal-cost IBGP routes is "+
                       "changed. When equal-cost IBGP routes are load-balancing "+
                       "traffic, the next hop of these routes is changed to a "+
                       "local interface before these routes are advertised. This"+
                       " function can be enabled only when the maximum number of"+
                       " equal-cost IBGP routes is greater than 1.";
                   }
                   leaf ecmp-nexthop-changed {
                     when "../maximum-load-balancing and ../maximum-load-balanci"+
                          "ng>1";
                     type "boolean";
                     default "false";
                     description
                       "Enable/disable next hop of equal-cost routes is changed."+
                       " When equal-cost BGP routes are load-balancing traffic, "+
                       "the next hop of these routes is changed to a local "+
                       "interface before these routes are advertised. This "+
                       "function can be enabled only when the maximum number of "+
                       "equal-cost BGP routes is greater than 1.";
                   }
                   leaf maximum-load-balancing-eibgp {
                     type "uint16" {
                       range "1..128";
                     }
                     must "../maximum-load-balancing-ibgp=1 and ../maximum-load-"+
                          "balancing-ebgp=1 and ../maximum-load-balancing=1 and "+
                          "../load-balancing-eibgp-enable='false'";
                     description
                       "Specify the maximum number of equal-cost EBGP routes and"+
                       " IBGP routes. After the attribute is set, load balancing"+
                       " is performed among equal-cost BGP VPN routes, "+
                       "regardless of the route type, EBGP or IBGP. The value "+
                       "range and default value are controlled by the PAF.";
                   }
                   leaf eibgp-ecmp-nexthop-changed {
                     when "../maximum-load-balancing-eibgp";
                     type "boolean";
                     default "false";
                     description
                       "Enable/disable next hop of equal-cost EBGP and IBGP "+
                       "routes is changed. When equal-cost EBGP and IBGP routes "+
                       "are load-balancing traffic, the next hop of these routes"+
                       " is changed to a local interface before these routes are"+
                       " advertised.";
                   }
                   leaf load-balancing-eibgp-enable {
                     type "boolean";
                     must "not (../maximum-load-balancing-ibgp>1 or ../maximum-l"+
                          "oad-balancing-ebgp>1 or ../maximum-load-balancing-eib"+
                          "gp) or ../load-balancing-eibgp-enable='false'";
                     default "false";
                     description
                       "Enable/disable EIBGP route load balancing.";
                   }
                   leaf advertise-route-mode {
                     type "bgp-advertise-route-mode";
                     default "all";
                     description
                       "VPN advertise route mode.";
                   }
                   leaf import-rib-nexthop-invariable {
                     type "boolean";
                     default "false";
                     description
                       "Enable/disable the function to advertise the route "+
                       "without modifying the next-hop.";
                   }
                   leaf determin-med {
                     type "boolean";
                     default "false";
                     description
                       "Enable/disable deterministic MED so that the route "+
                       "selection result is relevant to the sequence in which "+
                       "routes are received.";
                   }
                 }
                 container preference {
                   description
                     "Configure parameters relating to options for BGP routes "+
                     "preference.";
                   choice set-value-or-policy {
                     default "set-value";
                     description
                       "Set BGP routes preference by value or policy.";
                     case set-value {
                       description
                         "Set BGP routes preference by value.";
                       leaf external {
                         type "uint8" {
                           range "1..255";
                         }
                         default "255";
                         description
                           "Set the protocol priority of EBGP routes. The value "+
                           "is an integer. An EBGP route is the optimal route "+
                           "learned from a peer outside the local AS.";
                       }
                       leaf internal {
                         type "uint8" {
                           range "1..255";
                         }
                         default "255";
                         description
                           "Set the protocol priority of IBGP routes. The value "+
                           "is an integer. An IBGP route is a route learned from"+
                           " a peer inside the local AS.";
                       }
                       leaf local {
                         type "uint8" {
                           range "1..255";
                         }
                         default "255";
                         description
                           "Set the protocol priority of a local BGP route. A "+
                           "local route refers to an automatically or manually "+
                           "summarized route.";
                       }
                     }
                     case rtp-ref {
                       description
                         "Set BGP routes preference by route policy.";
                       leaf route-policy {
                         type "leafref" {
                           path "/rtp:routing-policy/rtp:policy-definitions/rtp:"+
                                "policy-definition/rtp:name";
                         }
                         description
                           "Specify a routing policy to filter routes so that a "+
                           "configured priority is applied to the routes that "+
                           "match the specified policy.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
                 container nexthop-recursive-lookup {
                   description
                     "Configure next hop iteration.";
                   container common {
                     description
                       "Configure next hop iteration common options.";
                     leaf restrain {
                       type "boolean";
                       default "true";
                       description
                         "Enable/disable the function to restrain next hop "+
                         "iteration in case of next hop flapping.";
                     }
                     choice policy-type {
                       description
                         "Set route-policy or route-filter.";
                       case rtp-ref {
                         description
                           "Route policy.";
                         leaf route-policy {
                           type "leafref" {
                             path "/rtp:routing-policy/rtp:policy-definitions/rt"+
                                  "p:policy-definition/rtp:name";
                           }
                           description
                             "Specify the name of a routing policy.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                   container delay {
                     description
                       "Configure time of next hop change responding delay.";
                     leaf time {
                       type "uint8" {
                         range "1..100";
                       }
                       units "s";
                       description
                         "Specify the delay in responding to the next hop "+
                         "change.";
                     }
                     leaf no-critical-event-time {
                       type "uint8" {
                         range "0..100";
                       }
                       units "s";
                       default "10";
                       description
                         "Specify the delay in responding to the next hop change"+
                         " on non critical relay change event.";
                     }
                   }
                 }
                 container import-routes {
                   description
                     "List of imported routes.";
                   list import-route {
                     key "protocol process-id";
                     description
                       "Configure route import. Routes of other protocol types "+
                       "can be imported by BGP. By default, BGP does not import "+
                       "routes of other protocol types.";
                     leaf protocol {
                       type "enumeration" {
                         enum "direct" {
                           value "1";
                           description
                             "Import direct routes.";
                         }
                         enum "ospf" {
                           value "2";
                           description
                             "Import OSPF routes.";
                         }
                         enum "isis" {
                           value "3";
                           description
                             "Import IS-IS routes.";
                         }
                         enum "static" {
                           value "4";
                           description
                             "Import static routes.";
                         }
                         enum "rip" {
                           value "5";
                           description
                             "Import RIP routes.";
                         }
                         enum "unr" {
                           value "11";
                           description
                             "Import UNR routes.";
                         }
                       }
                       description
                         "Routing protocol from which routes can be imported.";
                     }
                     leaf process-id {
                       type "uint32" {
                         range "0..4294967295";
                       }
                       description
                         "Process ID of an imported routing protocol. The "+
                         "process ID is 0, if the imported routing protocol is "+
                         "direct routes, static routes, UNRs, or OP-routes. The "+
                         "process ID must be specified range from 1 to "+
                         "4294967295, if the imported routing protocol is RIP, "+
                         "OSPF, ISIS.";
                       must "((../protocol='ospf' or ../protocol='isis' or "+
                            "../protocol='rip') and ../process-id!=0) or "+
                            "(../protocol!='ospf' and ../protocol!='isis' and "+
                            "../protocol!='rip' and ../process-id=0)";
                     }
                     leaf med {
                       type "uint32";
                       description
                         "Specifies the MED metric of the imported route.";
                     }
                     choice policy-type {
                       description
                         "Set route policy or filter.";
                       case rtp-ref {
                         description
                           "Route policy.";
                         leaf policy-name {
                           type "leafref" {
                             path "/rtp:routing-policy/rtp:policy-definitions/rt"+
                                  "p:policy-definition/rtp:name";
                           }
                           description
                             "When routes are imported from other routing "+
                             "protocols, the route-policy filter can be used to "+
                             "filter the routes and change route attributes.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                 }
                 container aggregate-routes {
                   description
                     "List of summarized routes.";
                   list aggregate-route {
                     key "address mask-length";
                     description
                       "Configure a summarized route in the BGP routing table. "+
                       "The local outbound interface of the summarized route is "+
                       "Null0. When another router receives the route, the route"+
                       " adds an outbound interface to the route. If the Origin "+
                       "attributes of the specific routes for the route "+
                       "summarization are different, the Origin attribute of the"+
                       " summarized route is that with the highest priority. "+
                       "Origin attributes are arranged in the priority order of "+
                       "complete > egp > igp. A summarized route carries the "+
                       "community attribute of each specific route.";
                     leaf address {
                       type "inet:ip-address-no-zone";
                       description
                         "Specify the IPv4 address or IPv6 address of a "+
                         "summarized route. Only IPv4 summarized routes can be "+
                         "configured in the IPv4 address family and only IPv6 "+
                         "summarized routes can be configured in the IPv6 "+
                         "address family.";
                       must "not(contains(../address,':'))";
                     }
                     leaf mask-length {
                       type "uint8" {
                         range "1..128";
                       }
                       description
                         "Specify the mask length of a summarized address.";
                       must "../mask-length<=32";
                     }
                     leaf as-set {
                       type "boolean";
                       default "false";
                       description
                         "Enable/disable the generation of routes with the "+
                         "AS-SET attribute. This option can be used to create a "+
                         "summarized route. The AS_Path attribute of the "+
                         "summarized route contains the AS-Path attributes of "+
                         "the specific routes for the route summarization. "+
                         "Exercise caution when using this option if multiple "+
                         "AS_Paths need to be summarized to prevent route "+
                         "flapping.";
                     }
                     leaf detail-suppressed {
                       type "boolean";
                       default "false";
                       description
                         "Enable/disable detail-suppressed. Suppress the "+
                         "advertisement of specific routes for the route "+
                         "summarization. Only the summarized route is advertised"+
                         ".";
                     }
                     choice policy-type {
                       description
                         "Set route policy or filter.";
                       case rtp-ref {
                         description
                           "Route policy.";
                         leaf attribute-policy {
                           type "leafref" {
                             path "/rtp:routing-policy/rtp:policy-definitions/rt"+
                                  "p:policy-definition/rtp:name";
                           }
                           description
                             "Specify an attribute of summarized routes. If "+
                             "apply as-path is used to configure the AS_Path "+
                             "attribute that is used in the route Summarization "+
                             "policy, and the as-set keyword is set, the AS_Path"+
                             " attribute in the policy does not take effect. "+
                             "This parameter and any of the following parameters"+
                             " overwrite each other: suppressFilter, originFilte"+
                             "r, and attributeFilter.";
                         }
                         leaf origin-policy {
                           type "leafref" {
                             path "/rtp:routing-policy/rtp:policy-definitions/rt"+
                                  "p:policy-definition/rtp:name";
                           }
                           description
                             "Specify the name of a policy for generating "+
                             "summarized routes. Summarized routes are generated"+
                             " only when the routes match route-policy. This "+
                             "parameter and any of the following parameters "+
                             "overwrite each other: suppressFilter, originFilter"+
                             ", and attributeFilter.";
                         }
                         leaf suppress-policy {
                           type "leafref" {
                             path "/rtp:routing-policy/rtp:policy-definitions/rt"+
                                  "p:policy-definition/rtp:name";
                           }
                           description
                             "Specify a policy for suppressing the advertisement"+
                             " of specified routes. The routes matching the "+
                             "policy are not advertised, and other routes are "+
                             "advertised. This parameter and any of the "+
                             "following parameters overwrite each other: "+
                             "suppressFilter, originFilter, and attributeFilter."+
                             "";
                         }
                       }
                       case xpl-ref {
                         description
                           "Route filter.";
                         leaf attribute-filter-name {
                           type "leafref" {
                             path "/xpl:xpl/xpl:route-filters/xpl:route-filter/x"+
                                  "pl:name";
                           }
                           description
                             "Specify a route-filter name.";
                         }
                         leaf attribute-filter-parameter {
                           when "../attribute-filter-name";
                           type "xpl:filter-parameter-type";
                           description
                             "Specify a route-filter parameter.";
                         }
                         leaf origin-filter-name {
                           type "leafref" {
                             path "/xpl:xpl/xpl:route-filters/xpl:route-filter/x"+
                                  "pl:name";
                           }
                           description
                             "Specify a route-filter name.";
                         }
                         leaf origin-filter-parameter {
                           when "../origin-filter-name";
                           type "xpl:filter-parameter-type";
                           description
                             "Specify a route-filter parameter.";
                         }
                         leaf suppress-filter-name {
                           type "leafref" {
                             path "/xpl:xpl/xpl:route-filters/xpl:route-filter/x"+
                                  "pl:name";
                           }
                           description
                             "Specify a route-filter name.";
                         }
                         leaf suppress-filter-parameter {
                           when "../suppress-filter-name";
                           type "xpl:filter-parameter-type";
                           description
                             "Specify a route-filter parameter.";
                         }
                       }
                     }
                   }
                 }
                 container aggregate-default-route {
                   description
                     "Configure aggregate default route.";
                   leaf origin-ip-prefix {
                     type "leafref" {
                       path "/rtp:routing-policy/rtp:ipv4-prefix-filters/rtp:ipv"+
                            "4-prefix-filter/rtp:name";
                     }
                     description
                       "Specify the name of an IPv4 prefix list for a summary "+
                       "default route. Only the name of an IPv4 prefix list can "+
                       "be configured in a BGP IPv4 address family.";
                   }
                   leaf attribute-policy {
                     when "../origin-ip-prefix";
                     type "leafref" {
                       path "/rtp:routing-policy/rtp:policy-definitions/rtp:poli"+
                            "cy-definition/rtp:name";
                     }
                     description
                       "Specify an attribute policy of a summary default route.";
                   }
                 }
                 container network-routes {
                   description
                     "List of network routes.";
                   list network-route {
                     key "address mask-length";
                     description
                       "Configure a network route in the BGP routing table.";
                     leaf address {
                       type "inet:ipv4-address-no-zone";
                       description
                         "Specify the IP address advertised by BGP. An IPv4 "+
                         "address can be configured in the IPv4 address family. "+
                         "Note: During the configuration of a network route, the"+
                         " IP address is adjusted based on the mask. It is "+
                         "recommended that you click Synchronize All after "+
                         "creating a network route.";
                     }
                     leaf mask-length {
                       type "uint8" {
                         range "0..32";
                       }
                       description
                         "Specify the mask length of an IP address.";
                     }
                     choice policy-type {
                       description
                         "Specify the route-policy or filter for route "+
                         "advertisement.";
                       case rtp-ref {
                         description
                           "Specify the route policy.";
                         leaf policy-name {
                           type "leafref" {
                             path "/rtp:routing-policy/rtp:policy-definitions/rt"+
                                  "p:policy-definition/rtp:name";
                           }
                           description
                             "Specify the route policy.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                 }
                 container import-ribs {
                   description
                     "List of imported RIBs configuration.";
                   list import-rib {
                     key "source-vpn source-address-family";
                     description
                       "Configure imported RIBs.";
                     leaf source-vpn {
                       type "leafref" {
                         path "/ni:network-instance/ni:instances/ni:instance/ni:"+
                              "name";
                       }
                       must "../../../../../../../../../ni:name != current()";
                       description
                         "Source VPN name.";
                     }
                     leaf source-address-family {
                       type "bgp:vrf-import-rib-ipv4-safi-type";
                       description
                         "Source address family type.";
                     }
                     leaf valid-route {
                       type "boolean";
                       default "false";
                       description
                         "Enable/disable imported valid route.";
                     }
                     leaf include-label-route {
                       when "../source-address-family='ipv4uni'";
                       type "boolean";
                       default "false";
                       description
                         "Enable/disable imported include label route.";
                     }
                     choice policy-type {
                       description
                         "Set policy or filter.";
                       case rtp-ref {
                         description
                           "Specify the route policy.";
                         leaf policy-name {
                           type "leafref" {
                             path "/rtp:routing-policy/rtp:policy-definitions/rt"+
                                  "p:policy-definition/rtp:name";
                           }
                           description
                             "Specify the route policy.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                 }
                 container import-filter-policy {
                   description
                     "Configure a filtering policy. It is used to filter the "+
                     "routes received from a peer. By default, routes are not "+
                     "filtered.";
                   choice ipv4-import-filter-protocol-policy-type {
                     description
                       "Set IPv4 filter protocol policy.";
                     case acl-ref {
                       description
                         "ACL Route Policy.";
                       leaf acl-name-or-num {
                         type "leafref" {
                           path "/acl:acl/acl:groups/acl:group/acl:identity";
                         }
                         description
                           "Specify the name or number of an ACL Rule. The "+
                           "number value ranges from 2000 to 2999 and is used by"+
                           " basic ACL rules. The name must start with a letter,"+
                           " and the name is case-sensitive.";
                       }
                     }
                     case ip-prefix-ref {
                       description
                         "IP prefix Policy.";
                       leaf ipv4-prefix-filter {
                         type "leafref" {
                           path "/rtp:routing-policy/rtp:ipv4-prefix-filters/rtp"+
                                ":ipv4-prefix-filter/rtp:name";
                         }
                         description
                           "Specify the IPv4 prefix list name.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
                 container export-filter-policys {
                   description
                     "List of filtering policies.";
                   list export-filter-policy {
                     key "protocol process-id";
                     description
                       "Apply a filtering policy. It is used to filter the "+
                       "routes to be advertised to the peer. By default, routes "+
                       "are not filtered.";
                     leaf protocol {
                       type "enumeration" {
                         enum "noprotocol" {
                           value "0";
                           description
                             "Import routes of all protocols.";
                         }
                         enum "direct" {
                           value "1";
                           description
                             "Import direct routes.";
                         }
                         enum "ospf" {
                           value "2";
                           description
                             "Import OSPF routes.";
                         }
                         enum "isis" {
                           value "3";
                           description
                             "Import IS-IS routes.";
                         }
                         enum "static" {
                           value "4";
                           description
                             "Import static routes.";
                         }
                         enum "rip" {
                           value "5";
                           description
                             "Import RIP routes.";
                         }
                       }
                       description
                         "Specify the name of a routing protocol. The routing "+
                         "protocol takes effect only on the routes to be "+
                         "advertised. The IPv4 address family supports the "+
                         "direct, IS-IS, OSPF, RIP, and static routing "+
                         "protocols. The IPv6 unicast address family of a public"+
                         " network instance supports the direct, IS-IS, OSPFv3, "+
                         "RIPng, and static routing protocols. The IPv6 address "+
                         "family of a VPNv6 instance supports the direct, IS-IS,"+
                         " RIPng, and static routing protocols.";
                     }
                     leaf process-id {
                       type "uint32" {
                         range "0..4294967295";
                       }
                       description
                         "Specify the process ID required to be matched. The "+
                         "value is an integer ranging from 0 to 4294967295. If "+
                         "direct or static routes need to be filtered, no "+
                         "process ID is required.";
                       must "((../protocol='ospf' or ../protocol='isis' or "+
                            "../protocol='rip') and ../process-id!=0) or "+
                            "(../protocol!='ospf' and ../protocol!='isis' and "+
                            "../protocol!='rip' and ../process-id=0)";
                     }
                     choice ipv4-filter-protocol-policy-type {
                       mandatory "true";
                       description
                         "Set IPv4 filter protocol policy.";
                       case acl-ref {
                         description
                           "ACL Route Policy.";
                         leaf acl-name-or-num {
                           type "leafref" {
                             path "/acl:acl/acl:groups/acl:group/acl:identity";
                           }
                           description
                             "Specify the name or number of an ACL Rule. The "+
                             "number value ranges from 2000 to 2999 and is used "+
                             "by basic ACL rules. The name must start with a "+
                             "letter, and the name is case-sensitive.";
                         }
                       }
                       case ip-prefix-ref {
                         description
                           "IP prefix Policy.";
                         leaf ipv4-prefix-filter {
                           type "leafref" {
                             path "/rtp:routing-policy/rtp:ipv4-prefix-filters/r"+
                                  "tp:ipv4-prefix-filter/rtp:name";
                           }
                           description
                             "Specify the IPv4 prefix list name.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                 }
                 container dampening-routes {
                   description
                     "List of route dampening.";
                   list dampening-route {
                     must "reuse < suppress and suppress < ceiling";
                     key "peer-type";
                     description
                       "Configure BGP route dampening or modify various BGP "+
                       "route dampening parameters. If a suppression policy for "+
                       "route dampening is configured, routes are preferentially"+
                       " matched against the suppression parameters defined in "+
                       "the suppression policy. If no parameter is configured, "+
                       "the default value of each parameter is used. The four "+
                       "route dampening parameters are mutually dependent. If "+
                       "you configure one of the parameters, the other "+
                       "parameters also need to be configured. When you "+
                       "configure BGP route dampening, the values of reuse "+
                       "threshold, suppress threshold, and penalty ceiling must "+
                       "meet the inequality of reuse threshold < suppress "+
                       "threshold < penalty ceiling. If Maximum suppression time"+
                       " obtained by using the formula of Maximum suppression "+
                       "time = Half life (of reachable routes) x 60 x (ln "+
                       "(Penalty ceiling/Reuse threshold)/ln(2)) is smaller than"+
                       " 1, suppression cannot be performed. Ensure that the "+
                       "value of the maximum suppression time is equal to or "+
                       "greater than 1. This means that the value of the penalty"+
                       " ceiling/reuse threshold must be great enough.";
                     leaf peer-type {
                       type "dampening-route-peer-type";
                       description
                         "Configure the peer type.";
                     }
                     leaf half-life-time {
                       type "uint16" {
                         range "1..45";
                       }
                       units "min";
                       default "15";
                       description
                         "Configure a half-life for reachable routes.";
                     }
                     leaf reuse {
                       type "uint16" {
                         range "1..20000";
                       }
                       default "750";
                       description
                         "Configure a threshold for a route to be unsuppressed. "+
                         "If the penalty value of the route falls below the "+
                         "threshold, the route is reused.";
                     }
                     leaf suppress {
                       type "uint16" {
                         range "1..20000";
                       }
                       default "2000";
                       description
                         "Configure a threshold for a route to be suppressed. "+
                         "When the penalty value of the route exceeds the "+
                         "suppression threshold, the route is suppressed. The "+
                         "configured suppression threshold must be greater than "+
                         "the reuse threshold.";
                     }
                     leaf ceiling {
                       type "uint16" {
                         range "1001..20000";
                       }
                       default "16000";
                       description
                         "Configure the penalty ceiling. The configured "+
                         "threshold must be greater than the suppression "+
                         "threshold.";
                     }
                     leaf update-standard {
                       type "boolean";
                       default "false";
                       description
                         "Enable/disable update standard.";
                     }
                     choice policy-type {
                       description
                         "Set route-policy or route-filter.";
                       case rtp-ref {
                         description
                           "Route policy.";
                         leaf route-policy {
                           type "leafref" {
                             path "/rtp:routing-policy/rtp:policy-definitions/rt"+
                                  "p:policy-definition/rtp:name";
                           }
                           description
                             "Specify the name of a routing policy.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                 }
                 container slow-peer {
                   description
                     "Configure peer advertising routes slowly.";
                   leaf detection {
                     type "boolean";
                     default "true";
                     description
                       "Enable/disable detect slow peers.";
                   }
                   leaf detection-threshold {
                     type "uint16" {
                       range "120..3600";
                     }
                     units "s";
                     default "300";
                     description
                       "Specify the time in seconds lagging behind average when "+
                       "a peer is determined to be a slow peer.";
                   }
                   leaf absolute-detection {
                     type "boolean";
                     default "true";
                     description
                       "Enable/disable absolute-detect slow peers.";
                   }
                   leaf absolute-detection-threshold {
                     type "uint16" {
                       range "3..3600";
                     }
                     units "s";
                     default "9";
                     description
                       "Specify the packet send delay time in second when a peer"+
                       " is determined to be a slow peer.";
                   }
                 }
                 container qos {
                   description
                     "Configure QoS.";
                   choice local-id-policy {
                     description
                       "Configure QoS local ID.";
                     case value {
                       description
                         "Specify the QoS local ID value.";
                       leaf local-id {
                         type "uint8" {
                           range "1..255";
                         }
                         description
                           "Specify the QoS local ID value.";
                       }
                     }
                     case rtp-ref {
                       description
                         "Route policy.";
                       leaf local-id-policy-name {
                         type "leafref" {
                           path "/rtp:routing-policy/rtp:policy-definitions/rtp:"+
                                "policy-definition/rtp:name";
                         }
                         description
                           "Set a routing policy to filter routes so that a "+
                           "configured QoS ID is applied to the routes that "+
                           "match the specified policy.";
                       }
                     }
                     case xpl-ref {
                       description
                         "Route filter.";
                       leaf local-id-filter-name {
                         type "leafref" {
                           path "/xpl:xpl/xpl:route-filters/xpl:route-filter/xpl"+
                                ":name";
                         }
                         description
                           "Specify a route-filter name.";
                       }
                       leaf local-id-filter-parameter {
                         when "../local-id-filter-name";
                         type "xpl:filter-parameter-type";
                         description
                           "Specify a route-filter parameter.";
                       }
                     }
                   }
                 }
               }
               container ipv4-vpn {
                 when "../type = 'ipv4vpn' and ../../../../../../ni:name='_publi"+
                      "c_'";
                 description
                   "Configure IPv4 VPNv4 options.";
                 leaf policy-vpntarget {
                   type "boolean";
                   default "true";
                   description
                     "Enable/disable VPN target-based filtering for the received"+
                     " VPN routes. Only the VPN route whose Export RT attribute "+
                     "matches the local Import RT attribute can be added to the "+
                     "routing table. This option can be used in the inter-AS VPN"+
                     " Option B solution and the ASBR MP-EBGP inter-AS L2VPN "+
                     "solution in Kompella mode.";
                 }
                 choice reflector-type {
                   description
                     "Set IPv4 address or id.";
                   case address {
                     description
                       "IPv4 address.";
                     leaf reflector-cluster-ipv4 {
                       type "inet:ipv4-address-no-zone";
                       description
                         "Set a cluster ID. The value is expressed in the format"+
                         " of an IPv4 address. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                   case id {
                     description
                       "Set value.";
                     leaf reflector-cluster-id {
                       type "uint32" {
                         range "1..4294967295";
                       }
                       description
                         "Set a cluster ID. Configuring multiple RRs in a "+
                         "cluster can enhance the stability of the network. If a"+
                         " cluster has more than one RR, select this option to "+
                         "set the same cluster ID for all the RRs to avoid "+
                         "routing loops. To allow clients to receive routes from"+
                         " RRs, ensure that the cluster ID of the RRs is "+
                         "different from the router ID of any client. If the "+
                         "cluster ID of the RRs is the same as the router ID of "+
                         "a client, the client will discard received routes.";
                     }
                   }
                 }
                 leaf reflect-change-path {
                   type "boolean";
                   default "false";
                   description
                     "Enable/disable an RR to use an export policy to change "+
                     "route AS_Path.";
                 }
                 leaf auto-frr {
                   type "boolean";
                   default "false";
                   description
                     "Enable/disable BGP Auto FRR. If IP FRR, VPN FRR, and Auto "+
                     "FRR are all enabled, IP FRR and VPN FRR take precedence "+
                     "over Auto FRR. If a route fails to match the routing "+
                     "policy of IP FRR or VPN FRR, Auto FRR takes effect.";
                 }
                 leaf tunnel-selector-name {
                   type "leafref" {
                     path "/rtp:routing-policy/rtp:tunnel-selectors/rtp:tunnel-s"+
                          "elector/rtp:name";
                   }
                   description
                     "Configure a tunnel selector and apply it to the BGP IPv4 "+
                     "unicast, BGP VPNv4 address families and BGP VPNv6 address "+
                     "families so that IPv4,VPNv4 and VPNv6 labeled routes can "+
                     "be iterated to tunnels based on the tunnel selector.";
                 }
                 leaf route-select-delay {
                   type "uint16" {
                     range "0..3600";
                   }
                   units "s";
                   default "0";
                   description
                     "Route selection delay.";
                 }
                 leaf apply-label-mode {
                   type "apply-label-type";
                   default "per-route";
                   description
                     "Method of distributing labels to VPNV4 and VPNV6 routes. "+
                     "The way which assigns the label depends on the paf value. "+
                     "If there are a large number of routes, assign a label for "+
                     "the routes that have same nexthop and out-label. This "+
                     "allows all routes which have same nexthop and out-label to"+
                     " use one label.";
                 }
                 leaf nexthop-select-depend-type {
                   type "select-depend-type-ext";
                   default "depend-ip";
                   description
                     "Specify the route iteration mode: IP or tunnel. In tunnel "+
                     "mode, the labeled BGP IPv4 route can participate in route "+
                     "selection only after its next hop is iterated to an LSP. "+
                     "In IP \nmode, the labeled BGP IPv4 route can participate "+
                     "in route selection only after its next hop is iterated to "+
                     "an IP address. By default, the labeled BGP IPv4 route can "+
                     "participate in route selection \nif its next hop can be "+
                     "iterated to an IP address, regardless of whether the LSP "+
                     "of the next hop exists. This allows the RR that is not "+
                     "enabled with MPLS to forward labeled routes. In non-RR "+
                     "\nnetworking or RR networking where the BGP next hop is "+
                     "changed, BGP needs to check whether there is an LSP "+
                     "destined for the next hop. If such an LSP is not found, "+
                     "BGP needs to establish an LSP in \nadvance. If the default"+
                     " setting is adopted, a labeled BGP IPv4 unicast route may "+
                     "be selected prior to LSP establishment. As a result, "+
                     "services are incorrectly switched before LSP establishment"+
                     " and \nservice stability is affected. Therefore, allow "+
                     "route selection only after the labeled BGP IPv4 route is "+
                     "iterated to an LSP.";
                 }
                 leaf default-med {
                   type "uint32";
                   default "0";
                   description
                     "Specify the Multi-Exit-Discriminator (MED) of BGP routes. "+
                     "The value is an integer. This value is valid only for the "+
                     "imported routes and BGP summarized routes on the local "+
                     "router.";
                 }
                 leaf best-external {
                   type "boolean";
                   default "false";
                   description
                     "Enable/disable best external route selection.";
                 }
                 leaf label-free-delay {
                   type "uint8" {
                     range "0..180";
                   }
                   units "s";
                   default "0";
                   description
                     "Label free delay.";
                 }
                 leaf add-path-select-num {
                   type "uint8" {
                     range "2..64";
                   }
                   description
                     "Number of Add-Path routes.";
                 }
                 leaf default-local-preference {
                   type "uint32" {
                     range "0..4294967295";
                   }
                   default "100";
                   description
                     "The local preference of BGP routes.";
                 }
                 leaf bestroute-med-plus-igp {
                   type "boolean";
                   must "not(../bestroute-igp-metric-ignore='true' and "+
                        "../bestroute-med-plus-igp='true')";
                   default "false";
                   description
                     "Enable/disable the function to add the IGP cost to the "+
                     "next-hop destination to the MED before comparing MED "+
                     "values for path selection.";
                 }
                 leaf bestroute-med-multiplier {
                   when "../bestroute-med-plus-igp='true'";
                   type "uint16" {
                     range "1..1000";
                   }
                   default "1";
                   description
                     "Value of med product factor.";
                 }
                 leaf bestroute-igp-multiplier {
                   when "../bestroute-med-plus-igp='true'";
                   type "uint16" {
                     range "1..1000";
                   }
                   default "1";
                   description
                     "Value of IGP cost product factor.";
                 }
                 leaf bestroute-igp-metric-ignore {
                   type "boolean";
                   default "false";
                   description
                     "Enable/disable BGP to ignore the IGP cost of each BGP "+
                     "route to the next hop in route selection. By default, a "+
                     "BGP route with a smaller IGP cost to the next hop is "+
                     "preferred.";
                 }
                 leaf bestroute-router-id-prior-clusterlist {
                   type "boolean";
                   default "false";
                   description
                     "Enable/disable BGP to compare originator before clusterlis"+
                     "t in route selection.";
                 }
                 leaf reflect-between-client {
                   type "boolean";
                   default "true";
                   description
                     "Enable/disable route reflection between clients. If "+
                     "clients of a route reflector (RR) are fully meshed, you "+
                     "can disable route reflection among clients to reduce the "+
                     "cost.";
                 }
                 leaf activate-route-tag {
                   type "boolean";
                   default "false";
                   description
                     "Enable/disable tag-based filtering.";
                 }
                 leaf route-reflector-ext-community-filter {
                   type "leafref" {
                     path "/rtp:routing-policy/rtp:ext-community-filters/rtp:ext"+
                          "-community-filter/rtp:name";
                   }
                   description
                     "Set the name of the extended community filter supported by"+
                     " an RR group. For the purpose of load balancing, only the "+
                     "IBGP route whose route-target extended community attribute"+
                     " meets the matching rules can be reflected.";
                 }
                 container dampening-routes {
                   description
                     "List of route dampening.";
                   list dampening-route {
                     must "reuse < suppress and suppress < ceiling";
                     key "peer-type";
                     description
                       "Configure BGP route dampening or modify various BGP "+
                       "route dampening parameters. If a suppression policy for "+
                       "route dampening is configured, routes are preferentially"+
                       " matched against the suppression parameters defined in "+
                       "the suppression policy. If no parameter is configured, "+
                       "the default value of each parameter is used. The four "+
                       "route dampening parameters are mutually dependent. If "+
                       "you configure one of the parameters, the other "+
                       "parameters also need to be configured. When you "+
                       "configure BGP route dampening, the values of reuse "+
                       "threshold, suppress threshold, and penalty ceiling must "+
                       "meet the inequality of reuse threshold < suppress "+
                       "threshold < penalty ceiling. If Maximum suppression time"+
                       " obtained by using the formula of Maximum suppression "+
                       "time = Half life (of reachable routes) x 60 x (ln "+
                       "(Penalty ceiling/Reuse threshold)/ln(2)) is smaller than"+
                       " 1, suppression cannot be performed. Ensure that the "+
                       "value of the maximum suppression time is equal to or "+
                       "greater than 1. This means that the value of the penalty"+
                       " ceiling/reuse threshold must be great enough.";
                     leaf peer-type {
                       type "bgp:dampening-route-ext-peer-type";
                       description
                         "Configure the peer type.";
                     }
                     leaf half-life-time {
                       type "uint16" {
                         range "1..45";
                       }
                       units "min";
                       default "15";
                       description
                         "Configure a half-life for reachable routes.";
                     }
                     leaf reuse {
                       type "uint16" {
                         range "1..20000";
                       }
                       default "750";
                       description
                         "Configure a threshold for a route to be unsuppressed. "+
                         "If the penalty value of the route falls below the "+
                         "threshold, the route is reused.";
                     }
                     leaf suppress {
                       type "uint16" {
                         range "1..20000";
                       }
                       default "2000";
                       description
                         "Configure a threshold for a route to be suppressed. "+
                         "When the penalty value of the route exceeds the "+
                         "suppression threshold, the route is suppressed. The "+
                         "configured suppression threshold must be greater than "+
                         "the reuse threshold.";
                     }
                     leaf ceiling {
                       type "uint16" {
                         range "1001..20000";
                       }
                       default "16000";
                       description
                         "Configure the penalty ceiling. The configured "+
                         "threshold must be greater than the suppression "+
                         "threshold.";
                     }
                     leaf update-standard {
                       type "boolean";
                       default "false";
                       description
                         "Enable/disable update standard.";
                     }
                     choice policy-type {
                       description
                         "Set route-policy or route-filter.";
                       case rtp-ref {
                         description
                           "Route policy.";
                         leaf route-policy {
                           type "leafref" {
                             path "/rtp:routing-policy/rtp:policy-definitions/rt"+
                                  "p:policy-definition/rtp:name";
                           }
                           description
                             "Specify the name of a routing policy.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                 }
                 container nexthop-recursive-lookup {
                   description
                     "Configure next hop iteration.";
                   container common {
                     description
                       "Configure next hop iteration common options.";
                     leaf restrain {
                       type "boolean";
                       default "true";
                       description
                         "Enable/disable the function to restrain next hop "+
                         "iteration in case of next hop flapping.";
                     }
                     choice policy-type {
                       description
                         "Set route-policy or route-filter.";
                       case rtp-ref {
                         description
                           "Route policy.";
                         leaf route-policy {
                           type "leafref" {
                             path "/rtp:routing-policy/rtp:policy-definitions/rt"+
                                  "p:policy-definition/rtp:name";
                           }
                           description
                             "Specify the name of a routing policy.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                   container delay {
                     description
                       "Configure time of next hop change responding delay.";
                     leaf time {
                       type "uint8" {
                         range "1..100";
                       }
                       units "s";
                       description
                         "Specify the delay in responding to the next hop "+
                         "change.";
                     }
                     leaf no-critical-event-time {
                       type "uint8" {
                         range "0..100";
                       }
                       units "s";
                       default "10";
                       description
                         "Specify the delay in responding to the next hop change"+
                         " on non critical relay change event.";
                     }
                   }
                   container bit-error-detection {
                     description
                       "Configure BGP bit-error detection parameters.";
                     leaf enable {
                       type "boolean";
                       must "(../enable='false') or (../enable='true' and "+
                            "(../med or ../local-preference))";
                       default "false";
                       description
                         "Enable/disable association between bit error events "+
                         "and the adjustment of route attributes.";
                     }
                     leaf med {
                       when "../enable='true'";
                       type "uint32" {
                         range "1..4294967295";
                       }
                       description
                         "Specify the MED adjustment for BGP routes used when a "+
                         "bit error event occurs.";
                     }
                     leaf local-preference {
                       when "../enable='true'";
                       type "uint32" {
                         range "1..4294967295";
                       }
                       description
                         "Specify the local preference adjustment for BGP routes"+
                         " used when a bit error event occurs.";
                     }
                     choice policy-type {
                       when "enable='true'";
                       description
                         "Set route-policy or route-filter for bit-error-trigger"+
                         "ed protection switching.";
                       case rtp-ref {
                         description
                           "Route policy.";
                         leaf route-policy {
                           type "leafref" {
                             path "/rtp:routing-policy/rtp:policy-definitions/rt"+
                                  "p:policy-definition/rtp:name";
                           }
                           description
                             "Specify the name of route-policy for bit-error-tri"+
                             "ggered protection switching. The MED or local "+
                             "preference of only the routes that match the "+
                             "route-policy is adjusted.";
                         }
                       }
                       case xpl-ref {
                         description
                           "Route filter.";
                         leaf filter-name {
                           type "leafref" {
                             path "/xpl:xpl/xpl:route-filters/xpl:route-filter/x"+
                                  "pl:name";
                           }
                           description
                             "Specify a route-filter name.";
                         }
                         leaf filter-parameter {
                           when "../filter-name";
                           type "xpl:filter-parameter-type";
                           description
                             "Specify a route-filter parameter.";
                         }
                       }
                     }
                   }
                 }
                 container import-filter-policy {
                   description
                     "Configure a filtering policy. It is used to filter the "+
                     "routes received from a peer. By default, routes are not "+
                     "filtered.";
                   choice ipv4-import-filter-protocol-policy-type {
                     description
                       "Set IPv4 filter protocol policy.";
                     case acl-ref {
                       description
                         "ACL Route Policy.";
                       leaf acl-name-or-num {
                         type "leafref" {
                           path "/acl:acl/acl:groups/acl:group/acl:identity";
                         }
                         description
                           "Specify the name or number of an ACL Rule. The "+
                           "number value ranges from 2000 to 2999 and is used by"+
                           " basic ACL rules. The name must start with a letter,"+
                           " and the name is case-sensitive.";
                       }
                     }
                     case ip-prefix-ref {
                       description
                         "IP prefix Policy.";
                       leaf ipv4-prefix-filter {
                         type "leafref" {
                           path "/rtp:routing-policy/rtp:ipv4-prefix-filters/rtp"+
                                ":ipv4-prefix-filter/rtp:name";
                         }
                         description
                           "Specify the IPv4 prefix list name.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
                 container export-filter-policy {
                   description
                     "Configure a filtering policy. It is used to filter the "+
                     "routes received from a peer. By default, routes are not "+
                     "filtered.";
                   choice ipv4-import-filter-protocol-policy-type {
                     description
                       "Set IPv4 filter protocol policy.";
                     case acl-ref {
                       description
                         "ACL Route Policy.";
                       leaf acl-name-or-num {
                         type "leafref" {
                           path "/acl:acl/acl:groups/acl:group/acl:identity";
                         }
                         description
                           "Specify the name or number of an ACL Rule. The "+
                           "number value ranges from 2000 to 2999 and is used by"+
                           " basic ACL rules. The name must start with a letter,"+
                           " and the name is case-sensitive.";
                       }
                     }
                     case ip-prefix-ref {
                       description
                         "IP prefix Policy.";
                       leaf ipv4-prefix-filter {
                         type "leafref" {
                           path "/rtp:routing-policy/rtp:ipv4-prefix-filters/rtp"+
                                ":ipv4-prefix-filter/rtp:name";
                         }
                         description
                           "Specify the IPv4 prefix list name.";
                       }
                     }
                     case xpl-ref {
                       description
                         "Route filter.";
                       leaf filter-name {
                         type "leafref" {
                           path "/xpl:xpl/xpl:route-filters/xpl:route-filter/xpl"+
                                ":name";
                         }
                         description
                           "Specify a route-filter name.";
                       }
                       leaf filter-parameter {
                         when "../filter-name";
                         type "xpl:filter-parameter-type";
                         description
                           "Specify a route-filter parameter.";
                       }
                     }
                   }
                 }
                 container slow-peer {
                   description
                     "Configure peer advertising routes slowly.";
                   leaf detection {
                     type "boolean";
                     default "true";
                     description
                       "Enable/disable detect slow peers.";
                   }
                   leaf detection-threshold {
                     type "uint16" {
                       range "120..3600";
                     }
                     units "s";
                     default "300";
                     description
                       "Specify the time in seconds lagging behind average when "+
                       "a peer is determined to be a slow peer.";
                   }
                   leaf absolute-detection {
                     type "boolean";
                     default "true";
                     description
                       "Enable/disable absolute-detect slow peers.";
                   }
                   leaf absolute-detection-threshold {
                     type "uint16" {
                       range "3..3600";
                     }
                     units "s";
                     default "9";
                     description
                       "Specify the packet send delay time in second when a peer"+
                       " is determined to be a slow peer.";
                   }
                 }
               }
             }
           }
           container vpn-as-number {
             when "../../../../ni:name!='_public_'";
             description
               "Configure BGP vpn as-number.";
             leaf local-ipv4 {
               type "as-number-validate";
               description
                 "IPv4 as-number.";
             }
             leaf local-ipv6 {
               type "as-number-validate";
               description
                 "IPv6 as-number.";
             }
           }
           container peer-groups {
             description
               "List of BGP peer groups. The BGP peer groups can help you "+
               "simplify the configurations. If you want to perform the same "+
               "configuration for several peers, you can create a peer group and"+
               " then configure the peer group. After you add these peers to the"+
               " peer group, all these peers will have the same configurations "+
               "as the peer group.";
             list peer-group {
               key "name";
               description
                 "Configure information about a BGP peer group.";
               leaf name {
                 type "string" {
                   length "1..47";
                   pattern "([^\\? ]+)";
                 }
                 description
                   "Specify the name of a peer group. The value is a string of "+
                   "characters, spaces not supported.";
               }
               leaf type {
                 type "group-type";
                 mandatory "true";
                 description
                   "Specify the type of a peer group. The value can be IBGP or "+
                   "EBGP.The object cannot be modified.";
                 ext:operation-exclude "update" {
                   description
                     "The node cannot be modified, when node is already "+
                     "configured.";
                 }
               }
               leaf local-if-name {
                 type "leafref" {
                   path "/ifm:ifm/ifm:interfaces/ifm:interface/ifm:name";
                 }
                 description
                   "Name of a source interface that sends BGP packets. By "+
                   "default, the outbound interface of a BGP packet serves as "+
                   "the source interface of a BGP packet. To ensure that a "+
                   "router can send BGP packets when a physical interface fails,"+
                   " you can configure the source interface that sends BGP "+
                   "packets as a loopback interface. When using the loopback "+
                   "interface as the source interface, note the following "+
                   "points: 1. The address of the loopback interface of the BGP "+
                   "peer must be reachable. 2. For an EBGP connection, configure"+
                   " the maximum number of hops and allow EBGP peer relationship"+
                   "s to be established in indirect mode.";
               }
               leaf local-if-address {
                 type "inet:ip-address-no-zone";
                 description
                   "Name of a source interface that sends BGP packets. By "+
                   "default, the outbound interface of a BGP packet serves as "+
                   "the source interface of a BGP packet. To ensure that a "+
                   "router can send BGP packets when a physical interface fails,"+
                   " you can configure the source interface that sends BGP "+
                   "packets as a loopback interface. When using the loopback "+
                   "interface as the source interface, note the following "+
                   "points:\n1. The address of the loopback interface of the BGP"+
                   " peer must be reachable.\n2. For an EBGP connection, "+
                   "configure the maximum number of hops and allow EBGP peer "+
                   "relationships to be established in indirect mode.";
               }
               leaf password-type {
                 type "bgp:password-type";
                 must "not((../password-type and ../password-type!='null') and "+
                      "(../key-chain-name or ../tcp-ao-name))";
                 must "(not(../password-type and ../password-type!='null') and "+
                      "not(../password-text)) or (../password-type and "+
                      "../password-type!='null' and ../password-text)";
                 default "null";
                 description
                   "Enable BGP peers to establish a TCP connection and perform "+
                   "the Message Digest 5 (MD5) authentication for BGP messages. "+
                   "Plaintexts and ciphertexts are supported.";
               }
               leaf password-text {
                 when "../password-type and ../password-type!='null'";
                 type "pub-type:password-extend";
                 mandatory "true";
                 description
                   "Enable BGP peers to establish a TCP connection and perform "+
                   "the Message Digest 5 (MD5) authentication for BGP messages. "+
                   "The character string in a password identifies the contents "+
                   "of the password, spaces not supported. The TCP connection "+
                   "can be established only when the same MD5 authentication "+
                   "password is set on both ends. If a plaintext is used, the "+
                   "maximum password length is 255. If a ciphertext is used, the"+
                   " maximum password length is 432. If the length is set to 0, "+
                   "no password is set.";
               }
               leaf key-chain-name {
                 type "string" {
                   length "1..47";
                   pattern "[^A-Z]+";
                 }
                 must "not(../password-type!='null' or ../tcp-ao-name)";
                 description
                   "Specify the Keychain authentication name used when BGP peers"+
                   " establish a TCP connection. The value is a string, spaces "+
                   "not supported. By default, the Keychain authentication is "+
                   "not configured. Keychain authentication mode and password "+
                   "authentication mode are mutually exclusive. Configuring "+
                   "Keychain authentication can enhance the security of the TCP "+
                   "connections between BGP peers. Keychain authentication using"+
                   " the same encryption algorithm and password must be "+
                   "configured on the two ends of BGP peers to establish a TCP "+
                   "connection and exchange BGP packets. Before configuring BGP "+
                   "Keychain authentication, you need to configure Keychain "+
                   "according to keychain name. Otherwise, the TCP connections "+
                   "between the BGP peers cannot be established.";
                 ext:case-sensitivity "lower-only";
               }
               leaf tcp-ao-name {
                 type "leafref" {
                   path "/socket:socket/socket:tcp-aos/socket:tcp-ao/socket:name"+
                        "";
                 }
                 must "not(../password-type!='null' or ../key-chain-name)";
                 description
                   "Specify TCP-AO authentication for establishing the TCP "+
                   "connection between BGP peers.";
               }
               leaf description {
                 type "string" {
                   length "1..255";
                   pattern "([^?]*)";
                 }
                 description
                   "Specify the description of a peer group. The value is a "+
                   "string, which can be letters or digits, spaces supported. By"+
                   " default, no description is configured.";
               }
               leaf group-as {
                 when "not(../type='ibgp')";
                 type "as-number-validate";
                 description
                   "Specify the AS number of a peer group. The AS number is in "+
                   "either a 2-byte or 4-byte format. \nThe two-byte format is "+
                   "X. X is an integer ranging from 1 to 65535.\nThe four-byte "+
                   "format is X.Y and X. When the format is X.Y, X and Y are "+
                   "both integers, with the value of X ranging from 1 to 65535, "+
                   "and the value of Y ranging from 0 to 65535; when the format "+
                   "is X, X is an interger, with the value of X ranging from 1 "+
                   "to 4294967295.";
               }
               leaf ebgp-max-hop {
                 when "../type='ebgp'";
                 type "uint32" {
                   range "1..255";
                 }
                 must "not(../valid-ttl-hops) or (../valid-ttl-hops>=1 and "+
                      "not(../valid-ttl-hops>255) and ../ebgp-max-hop=1)";
                 default "1";
                 description
                   "Maximum number of hops in an indirect EBGP connection. By "+
                   "default, EBGP connections can be established only between "+
                   "directly connected peers. The function must be configured on"+
                   " both ends.";
               }
               leaf valid-ttl-hops {
                 type "uint16" {
                   range "1..255";
                 }
                 must "not(../ebgp-max-hop and ../ebgp-max-hop>1)";
                 description
                   "Enable GTSM on a peer or peer group. The valid-TTL-Value "+
                   "parameter is used to specify the number of TTL hops to be "+
                   "detected. If the value is configured as hops, the valid TTL "+
                   "range of the detected packet is [255-hops+1, 255].";
               }
               leaf tracking-enable {
                 type "boolean";
                 default "false";
                 description
                   "Enable/disable peer tracking, After peer tracking is "+
                   "enabled, the device can fast detect the unreachability of a "+
                   "peer and reset the session.";
               }
               leaf tracking-delay-time {
                 when "../tracking-enable='true'";
                 type "uint16";
                 units "s";
                 default "0";
                 description
                   "Specify the delay to reset the session.";
               }
               leaf conventional {
                 type "boolean";
                 default "false";
                 description
                   "Enable/disable general router functions on peers. In "+
                   "conventional mode, not all the extended router functions, "+
                   "such as, route refreshing, GR, and multi-address family "+
                   "negotiation, are available. Therefore, the router of a new "+
                   "version can be compatible with the routers of earlier "+
                   "versions.";
               }
               leaf route-refresh {
                 type "boolean";
                 default "true";
                 description
                   "Enable/disable BGP to advertise Refresh messages to peers.";
               }
               leaf four-byte-as {
                 type "boolean";
                 default "true";
                 description
                   "Enable/disable BGP to advertise routes carrying 4-byte AS "+
                   "numbers to peers. After the 4-byte AS number function is "+
                   "disabled, Open packets will not carry 4-byte AS number "+
                   "capability flag, and peer ends will not know that local ends"+
                   " have the 4-byte AS number function. The 4-byte AS number "+
                   "function cannot be disabled from peers (peer groups) if a "+
                   "4-byte AS number, fake AS number, or confederation ID is "+
                   "configured on a router and the AS number of a peer is "+
                   "4-byte. If the 4-byte AS number function is disabled in such"+
                   " a situation, BGP sessions may fail to be established, and "+
                   "route transmission may be affected.";
               }
               leaf ignore {
                 type "boolean";
                 default "false";
                 description
                   "Enable/disable the function to tear down sessions between "+
                   "peers and clear all related routing information.";
               }
               leaf connect-mode {
                 type "connect-mode";
                 default "null";
                 description
                   "The value can be Connect-only, Listen-only, or Both. If the "+
                   "value is Connect-only, the specified peer or peer group only"+
                   " initiatively sends connection requests, instead of "+
                   "listening to connection requests. If the value is Listen-onl"+
                   "y, the specified peer or peer group only listens to "+
                   "connection requests, instead of initiatively sending "+
                   "connection requests. If the value is Both, the specified "+
                   "peer or peer group not only initiatively sends connection "+
                   "requests, but also listens to connection requests. The "+
                   "default value is Both.";
               }
               leaf log-change {
                 type "boolean";
                 default "true";
                 description
                   "Enable/disable BGP to record the session status and events "+
                   "of the specified peer or peer group.";
               }
               leaf check-first-as {
                 when "../type='ebgp'";
                 type "peer-cap-config-state";
                 default "default";
                 description
                   "Check the first AS in the AS_Path of the update messages "+
                   "from EBGP peers.";
               }
               leaf memory-priority {
                 type "memory-priority";
                 default "medium";
                 description
                   "Set a priority that determines the disconnection order of "+
                   "each BGP peer relationship in a peer group if memory "+
                   "overload occurs.";
               }
               leaf oscillation-dampening {
                 type "boolean";
                 default "true";
                 description
                   "Enable/disable BGP to suppress the establishment of a "+
                   "specified peer group's peer relationships that flap "+
                   "continuously. By default, the capability is enabled.";
               }
               container fake-as-parameter {
                 when "../../../../../../ni:name!='_public_'";
                 description
                   "Configure BGP fake-as parameters.";
                 leaf fake-as {
                   when "../../bgp:type='ebgp'";
                   type "bgp:as-number-validate";
                   description
                     "Fake AS number that is specified for a local peer. By "+
                     "default, a peer uses the actual AS number of the local "+
                     "end.\nAn AS number can be in either two-byte format or "+
                     "four-byte format:\nThe two-byte format is X. X is an "+
                     "integer ranging from 1 to 65535.\nThe four-byte format is "+
                     "X.Y and X. When the format is X.Y, X and Y are both "+
                     "integers, with the value of X ranging from 1 to 65535, and"+
                     " the value of Y ranging from 0 to 65535; when the format "+
                     "is X, X is an interger, with the value of X ranging from 1"+
                     " to 4294967295.";
                 }
                 leaf dual-as {
                   when "../fake-as";
                   type "boolean";
                   default "false";
                   description
                     "Enable/disable the function to the remote EBGP peer can "+
                     "use the actual or fake AS number when specifying the AS "+
                     "number for a local peer. The local peer uses the fake and "+
                     "actual AS numbers to establish a BGP peer relationship "+
                     "with the remote end and identifies the AS number "+
                     "configured by the remote end through the error code (OPEN "+
                     "Message Error) and sub-error code (Bad Peer AS) of the "+
                     "Notification message from the remote end.";
                 }
                 leaf prepend-global-as {
                   when "../fake-as";
                   type "boolean";
                   default "false";
                   description
                     "Enable/disable the function to add the global AS number to"+
                     " the Update packets to be advertised.";
                 }
                 leaf prepend-fake-as {
                   when "../fake-as";
                   type "boolean";
                   default "false";
                   description
                     "Enable/disable the function to add the Fake AS number to "+
                     "received Update packets.";
                 }
               }
               container timer {
                 description
                   "Configure BGP peer timer parameters.";
                 leaf keep-alive-time {
                   type "uint32" {
                     range "0..21845";
                   }
                   units "s";
                   must "(../keep-alive-time != 0 and (../hold-time>=../keep-ali"+
                        "ve-time * 3) and ../hold-time != ../keep-alive-time ) "+
                        "or (../hold-time = 0 and ../keep-alive-time = 0)";
                   default "60";
                   description
                     "If the value of a timer changes, the BGP peer relationship"+
                     " between the routers is disconnected. This is because the "+
                     "peers need to re-negotiate the Keepalive time and hold "+
                     "time. Therefore, confirm the action before you change the "+
                     "value of the timer. The Keepalive time should be at least "+
                     "three times of the hold time.";
                 }
                 leaf hold-time {
                   type "uint32" {
                     range "0 | 3..65535";
                   }
                   units "s";
                   must "(((../hold-time>=../keep-alive-time * 3) and ../hold-ti"+
                        "me != ../keep-alive-time ) or (../hold-time = 0 and "+
                        "../keep-alive-time = 0)) and ../hold-time>=../min-hold-"+
                        "time";
                   default "180";
                   description
                     "Hold time. When setting keepalive-time and hold-time, note"+
                     " the following:\n1. The values of keepalive-time and "+
                     "hold-time cannot both be 0. Otherwise, the BGP timer "+
                     "becomes invalid. That is, BGP does not detect link faults "+
                     "according to the timer.\n2. The value of hold-time is much"+
                     " greater than that of keepalive-time, such as, keepalive 1"+
                     " and hold 65535. If the value of hold-time is too large, "+
                     "BGP cannot detect link faults timely.\nThe priority of a "+
                     "timer is lower than that of a peer timer.\nAfter a "+
                     "connection is established between peers, the values of "+
                     "keepalive-time and hold-time are negotiated by the peers. "+
                     "The smaller value of hold-time contained in Open packets "+
                     "of both peers is taken as the value of hold-time. The "+
                     "smaller value of the locally set value of keepalive-time "+
                     "and one third of the value of hold-time is taken as the "+
                     "value of keepalive-time.";
                 }
                 leaf min-hold-time {
                   type "uint32" {
                     range "0 | 20..65535";
                   }
                   units "s";
                   must "../hold-time>=../min-hold-time";
                   default "0";
                   description
                     "The default value of zero means that the minimum hold time"+
                     " check does not take effect. If the value is changed, the "+
                     "new value takes effect since the next peer relationship "+
                     "establishment. During the peer relationship establishment,"+
                     " the local device checks the hold time of the remote end. "+
                     "If the hold time is less than the minimum hold time, the "+
                     "local device sends an error packet with error code 02 and "+
                     "subcode 06, and the peer relationship fails to be "+
                     "established.";
                 }
                 leaf connect-retry-time {
                   type "uint16" {
                     range "1..65535";
                   }
                   units "s";
                   default "32";
                   description
                     "ConnectRetry interval.";
                 }
               }
               container bfd-parameter {
                 description
                   "Configure BFD.";
                 leaf enable {
                   type "boolean";
                   default "false";
                   description
                     "Enable/disable BFD.";
                 }
                 choice mode-type {
                   description
                     "Set bfd mode.";
                   case single {
                     description
                       "Single hop mode.";
                     leaf single-hop {
                       when "../enable='true'";
                       type "empty";
                       description
                         "The single hop mode is preferred during the BFD "+
                         "session establishment between IBGP peers.";
                     }
                     leaf compatible {
                       when "../enable='true'";
                       type "empty";
                       description
                         "Compatible.";
                     }
                   }
                 }
                 leaf multiplier {
                   type "uint32" {
                     range "3..50";
                   }
                   default "3";
                   description
                     "Specify the detection multiplier.";
                 }
                 leaf min-rx-interval {
                   type "uint32" {
                     range "3..20000";
                   }
                   units "ms";
                   description
                     "Specify the minimum interval at which BFD packets are "+
                     "received. The value range and default value are controlled"+
                     " by the PAF.";
                 }
                 leaf min-tx-interval {
                   type "uint32" {
                     range "3..20000";
                   }
                   units "ms";
                   description
                     "Specify the minimum interval at which BFD packets are "+
                     "sent. The value range and default value are controlled by "+
                     "the PAF.";
                 }
                 leaf valid-ttl-hops {
                   type "uint8" {
                     range "1..255";
                   }
                   description
                     "Specify the valid TTL hops value.";
                 }
               }
               container graceful-restart {
                 description
                   "Configure graceful restart.";
                 leaf enable {
                   type "boolean";
                   default "false";
                   description
                     "Enable/disable graceful restart capability.";
                 }
                 leaf time-wait-for-rib {
                   type "uint32" {
                     range "3..3000";
                   }
                   units "s";
                   default "600";
                   description
                     "Period of waiting for the End-of-RIB flag. The value is an"+
                     " integer. When a BGP session is established or re-establis"+
                     "hed, the router enabled with GR should receive the "+
                     "End-of-RIB flag in this period. If the router does not "+
                     "receive the End-of-RIB flag in this period, ensure that "+
                     "the router can exit from the GR process.";
                 }
                 leaf restart-time {
                   type "uint16" {
                     range "3..3600";
                   }
                   units "s";
                   default "150";
                   description
                     "Specifies the maximum time during which a peer waits for a"+
                     " BGP session reestablishment.";
                 }
                 leaf peer-reset {
                   type "boolean";
                   default "false";
                   description
                     "Enable/disable reseting BGP peer graceful.";
                 }
               }
               container local-graceful-restart {
                 description
                   "Configure local graceful restart.";
                 leaf enable {
                   type "boolean";
                   default "false";
                   description
                     "Enable/disable graceful restart capability.";
                 }
                 leaf time-wait-for-rib {
                   type "uint32" {
                     range "3..3000";
                   }
                   units "s";
                   default "600";
                   description
                     "Period of waiting for the End-of-RIB flag. The value is an"+
                     " integer. When a BGP session is established or re-establis"+
                     "hed, the router enabled with GR should receive the "+
                     "End-of-RIB flag in this period. If the router does not "+
                     "receive the End-of-RIB flag in this period, ensure that "+
                     "the router can exit from the GR process.";
                 }
                 leaf restart-time {
                   type "uint16" {
                     range "3..3600";
                   }
                   units "s";
                   default "150";
                   description
                     "Specifies the maximum time during which a peer waits for a"+
                     " BGP session reestablishment.";
                 }
               }
               container afs {
                 description
                   "List of all peer groups that are enabled in a specified "+
                   "address family.";
                 list af {
                   key "type";
                   description
                     "Configure peer group enabled in a specified address "+
                     "family.";
                   leaf type {
                     type "enumeration" {
                       enum "ipv4uni" {
                         value "1";
                         description
                           "IPv4 unicast address family.";
                       }
                       enum "ipv4vpn" {
                         value "3";
                         description
                           "IPv4 VPN address family.";
                       }
                     }
                     must "../../../../../afs/af[type = current()]";
                     description
                       "Address family type of a BGP instance.";
                   }
                   container ipv4-unicast {
                     when "../type = 'ipv4uni' and ../../../../../../../../ni:na"+
                          "me!='_public_'";
                     must "../../../../../../../../l3vpn:afs/l3vpn:af[l3vpn:type"+
                          "='ipv4-unicast']";
                     description
                       "Configure IPv4 unicast options.";
                     leaf reflect-client {
                       when "../../../../bgp:type='ibgp'";
                       type "boolean";
                       default "false";
                       description
                         "Enable/disable the local device as a route reflector "+
                         "(RR) and a peer or peer group as its client. This "+
                         "configuration is applicable between IBGP peers only. "+
                         "The configurations of RRs and its clients in an "+
                         "address family are valid only in this address family. "+
                         "Therefore, it is recommended to configure RRs and its "+
                         "clients in the specified address family that is "+
                         "required.";
                     }
                     leaf label-route-capability {
                       type "boolean";
                       default "false";
                       description
                         "Enable/disable a device to exchange labeled routes.";
                     }
                     leaf check-tunnel-reachable {
                       when "../label-route-capability='true'";
                       type "boolean";
                       default "false";
                       description
                         "Enable/disable tunnel reachability check.";
                     }
                     leaf nexthop-configure {
                       type "vrf-nexthop-configuration-type";
                       description
                         "Both the next-hop-local mode and next-hop-invariable "+
                         "mode are available when the peer address family is the"+
                         " VPNv4/VPNv6/L2VPN AD address family. Only the "+
                         "next-hop-local mode is available when the peer address"+
                         " family is not VPNv4/VPNV6/L2VPN AD address family. In"+
                         " next-hop-local mode, you can configure a BGP speaker "+
                         "to set its IP address of as the next hop of the routes"+
                         " to be advertised to IBGP peers or IBGP peer groups. "+
                         "In next-hop-invariable mode, you can configure PEs in "+
                         "different ASs not to change the next hop of routes "+
                         "when the PEs advertise the routes to their EBGP peers "+
                         "and use the next hop addresses of IGP routes to "+
                         "advertise imported IGP routes to IBGP peers. By "+
                         "default, when a BGP speaker advertises routes to EBGP "+
                         "peers and imported IGP routes to IBGP peers, the BGP "+
                         "speaker changes the next hop to its interface "+
                         "address.";
                     }
                     choice import-policy-type {
                       description
                         "Set route policy or filter.";
                       case rtp-ref {
                         description
                           "Route policy.";
                         leaf import-policy {
                           type "leafref" {
                             path "/rtp:routing-policy/rtp:policy-definitions/rt"+
                                  "p:policy-definition/rtp:name";
                           }
                           description
                             "Specify the filtering policy applied to the routes"+
                             " learned from a peer. By default, no such policy "+
                             "is specified.";
                         }
                       }
                       case xpl-ref {
                         description
                           "Route filter.";
                         container import-filter {
                           description
                             "Configure an import route-filter to filter the "+
                             "routes received from a peer group. By default, no "+
                             "route-filter is specified to filter the routes "+
                             "imported from a peer group.";
                           leaf name {
                             type "leafref" {
                               path "/xpl:xpl/xpl:route-filters/xpl:route-filter"+
                                    "/xpl:name";
                             }
                             description
                               "Specify an import route-filter name.";
                           }
                           leaf parameter {
                             when "../name";
                             type "xpl:filter-parameter-type";
                             description
                               "Specify an import route-filter parameter.";
                           }
                         }
                       }
                     }
                     choice export-policy-type {
                       description
                         "Set route policy or filter.";
                       case rtp-ref {
                         description
                           "Route policy.";
                         leaf export-policy {
                           type "leafref" {
                             path "/rtp:routing-policy/rtp:policy-definitions/rt"+
                                  "p:policy-definition/rtp:name";
                           }
                           description
                             "Specify the filtering policy applied to the routes"+
                             " to be advertised to a peer. By default, no such "+
                             "policy is specified.";
                         }
                       }
                       case xpl-ref {
                         description
                           "Route filter.";
                         container export-filter {
                           description
                             "Configure an export route-filter to filter the "+
                             "routes to be advertised to a peer group. By "+
                             "default, no route-filter is specified to filter "+
                             "the routes to be advertised to a peer group.";
                           leaf name {
                             type "leafref" {
                               path "/xpl:xpl/xpl:route-filters/xpl:route-filter"+
                                    "/xpl:name";
                             }
                             description
                               "Specify an export route-filter name.";
                           }
                           leaf parameter {
                             when "../name";
                             type "xpl:filter-parameter-type";
                             description
                               "Specify an export route-filter parameter.";
                           }
                         }
                       }
                     }
                     leaf allow-as-loop {
                       type "uint32" {
                         range "1..10";
                       }
                       description
                         "Allow repetitive local AS numbers. By default, "+
                         "repetitive local AS numbers are not allowed.";
                     }
                     leaf import-ip-prefix {
                       type "leafref" {
                         path "/rtp:routing-policy/rtp:ipv4-prefix-filters/rtp:i"+
                              "pv4-prefix-filter/rtp:name";
                       }
                       description
                         "Specify the IPv4 filtering policy applied to the "+
                         "routes received from a specified peer. By default, no "+
                         "such policy is specified.";
                     }
                     leaf export-ip-prefix {
                       type "leafref" {
                         path "/rtp:routing-policy/rtp:ipv4-prefix-filters/rtp:i"+
                              "pv4-prefix-filter/rtp:name";
                       }
                       description
                         "Specify the IPv4 filtering policy applied to the "+
                         "routes to be advertised to a specified peer. By "+
                         "default, no such policy is specified.";
                     }
                     leaf import-as-path-filter {
                       type "leafref" {
                         path "/rtp:routing-policy/rtp:as-path-filters/rtp:as-pa"+
                              "th-filter/rtp:name";
                       }
                       description
                         "Apply an AS_Path-based filtering policy to the routes "+
                         "received from a specified peer. The policy can be "+
                         "identified with a name or number, and the number "+
                         "ranges from 1 to 256. By default, no such policy is "+
                         "specified. Therefore, all BGP routes can be accepted.";
                     }
                     leaf export-as-path-filter {
                       type "leafref" {
                         path "/rtp:routing-policy/rtp:as-path-filters/rtp:as-pa"+
                              "th-filter/rtp:name";
                       }
                       description
                         "Apply an AS_Path-based filtering policy to the routes "+
                         "to be advertised to a specified peer. The policy can "+
                         "be identified with a name or number, and the number "+
                         "ranges from 1 to 256. By default, no such policy is "+
                         "specified. Therefore, all BGP routes can be advertised"+
                         ".";
                     }
                     leaf import-acl-name-or-num {
                       type "leafref" {
                         path "/acl:acl/acl:groups/acl:group/acl:identity";
                       }
                       description
                         "Specifies the name of the import ACL policy.";
                     }
                     leaf export-acl-name-or-num {
                       type "leafref" {
                         path "/acl:acl/acl:groups/acl:group/acl:identity";
                       }
                       description
                         "Specifies the name of the export ACL policy.";
                     }
                     leaf default-route-advertise {
                       type "boolean";
                       default "false";
                       description
                         "Enable/disable a device to advertise the default route"+
                         " to its peers. This option enables a device to send a "+
                         "default route with the device as the next hop address "+
                         "to its peers, regardless of whether there is a default"+
                         " route in the local routing table.";
                     }
                     choice default-route-advertise-policy-type {
                       description
                         "Set default route advertise-policy.";
                       case rtp-ref {
                         description
                           "The default-route-advertise-policy.";
                         leaf default-route-advertise-policy {
                           when "../default-route-advertise='true'";
                           type "leafref" {
                             path "/rtp:routing-policy/rtp:policy-definitions/rt"+
                                  "p:policy-definition/rtp:name";
                           }
                           description
                             "Specify the name of a used policy.";
                         }
                       }
                       case xpl-ref {
                         description
                           "The default-route-advertise-filter.";
                         container default-route-advertise-filter {
                           when "../default-route-advertise='true'";
                           description
                             "Configure the route-filter for default route "+
                             "advertise.";
                           leaf filter-name {
                             type "leafref" {
                               path "/xpl:xpl/xpl:route-filters/xpl:route-filter"+
                                    "/xpl:name";
                             }
                             description
                               "Specify a route-filter name.";
                           }
                           leaf filter-parameter {
                             when "../filter-name";
                             type "xpl:filter-parameter-type";
                             description
                               "Specify a route-filter parameter.";
                           }
                         }
                       }
                     }
                     leaf default-route-match-mode {
                       when "../default-route-advertise='true'";
                       type "cra-match-mode";
                       default "null";
                       description
                         "Configure the matching mode of default route "+
                         "advertisement, which can be disabling of route "+
                         "advertisement conditions, enabling of all route "+
                         "advertisement conditions, and enabling of part route "+
                         "advertisement conditions. Enabling of all route "+
                         "advertisement conditions indicates that a default "+
                         "route can be advertised only when it matches all the "+
                         "conditions. Enabling of part route advertisement "+
                         "conditions indicates that a default route can be "+
                         "advertised only when it matches one condition.";
                     }
                     leaf route-update-interval {
                       type "uint16" {
                         range "0..600";
                       }
                       units "s";
                       description
                         "Specify the minimum interval at which Update packets "+
                         "are sent. By default, the interval at which Update "+
                         "packets are sent to IBGP peers is 15s, \nand the "+
                         "interval at which Update packets are sent to EBGP "+
                         "peers is 30s. When routes change, a router will send "+
                         "Update packets to notify its peers. \nIf a route "+
                         "changes frequently, you can set an interval at which "+
                         "Update packets are sent to prevent the router from "+
                         "sending Update packets each time the route changes. "+
                         "\nThis configuration is valid only to the routes "+
                         "learned from peers.";
                       ext:dynamic-default;
                     }
                     leaf preferred-value {
                       type "uint32" {
                         range "0..65535";
                       }
                       default "0";
                       description
                         "Assign a preferred value for the routes learned from a"+
                         " specified peer. After a preferred value is configured"+
                         " for the routes learned from a specified peer,\nall "+
                         "the routes that learnt from this peer will use this "+
                         "preferred value. When multiple routes reach the same "+
                         "address prefix, the route with the largest preferred "+
                         "value will be selected.";
                     }
                     leaf substitute-as-enable {
                       when "../../../../bgp:type='ebgp'";
                       type "boolean";
                       default "false";
                       description
                         "Enable/disable replace the AS number of a specified "+
                         "peer in the AS_Path attribute with the local AS "+
                         "number. On a PE where AS number replacement is "+
                         "enabled, if an AS number in the AS_Path attribute of a"+
                         " route is same as that of the CE to which the PE "+
                         "advertises the route, the PE replaces the AS number "+
                         "with its own AS number before advertising the route.";
                     }
                     leaf soo {
                       type "string" {
                         length "3..21";
                       }
                       description
                         "Configure the Site-of-Origin (SoO) extended community "+
                         "attribute. This attribute can be expressed in the "+
                         "following formats: X.X.X.X:number<0-65535>, number<0-6"+
                         "5535>:number<0-4294967295>, or number<0-65535>.number<"+
                         "0-65535>:number<0-65535> or <65536-4294967295>:<0-6553"+
                         "5>. 0:0 or 0.0:0 is not supported. \nTwo CEs are in "+
                         "the same site and can advertise routes to each other, "+
                         "and they are connected to a VPN through PEs. If the "+
                         "local routes of a CE are advertised to the other CE "+
                         "over the VPN, a routing loop may occur. \nThe SoO "+
                         "feature can prevent a route advertised by a site from "+
                         "being sent back to the site, preventing routing loops."+
                         " After SoO is enabled and a PE receives a route from a"+
                         " CE, the specified SoO attribute will be added to the "+
                         "route. Before advertising the route to the other CE, "+
                         "the PE checks the SoO attribute. If the SoO attribute "+
                         "is the same as the locally configured SoO attribute, "+
                         "the PE does not advertise the route, preventing "+
                         "routing loops.";
                     }
                     leaf keep-all-routes {
                       type "boolean";
                       default "false";
                       description
                         "Enable/disable saving all the updated information "+
                         "about BGP routes from a specified peer or peer group "+
                         "after a BGP connection is established, even though "+
                         "these BGP routes fail to match the routing policy on "+
                         "the ingress. By default, the updated information about"+
                         " BGP routes from a specified peer is saved only when "+
                         "the routes match the routing policy on the ingress. If"+
                         " a router supports route refreshing, this option is "+
                         "not required.";
                     }
                     leaf load-balancing-enable {
                       type "boolean";
                       default "false";
                       description
                         "Enable/disable a neighbour to participate in load "+
                         "balancing.";
                     }
                     choice load-balancing-ignore-as-type {
                       description
                         "Set load balancing as path type.";
                       case as-attribute {
                         description
                           "Ignore the as-path attribute.";
                         leaf load-balancing-as-path-ignore {
                           when "../load-balancing-enable='true'";
                           type "empty";
                           description
                             "Configure BGP to ignore the AS_Path attribute when"+
                             " selecting the equal route. After as-path-neglect "+
                             "is selected, BGP does not compare the AS_Path "+
                             "length.";
                         }
                       }
                       case same-length-as-attribute {
                         description
                           "Ignore comparison of as-path attributes with the "+
                           "same length.";
                         leaf load-balancing-as-path-relax {
                           when "../load-balancing-enable='true'";
                           type "empty";
                           description
                             "Configure BGP to ignore comparison of AS_Path "+
                             "attributes with the same length when selecting the"+
                             " equal route. After as-path-neglect is selected, "+
                             "BGP does not compare the AS_Path length.";
                         }
                       }
                     }
                     leaf update-group-independent {
                       type "boolean";
                       default "false";
                       description
                         "Enable/disable the peer which can reside in an "+
                         "independent peer group.";
                     }
                     leaf advertise-community {
                       type "boolean";
                       default "false";
                       description
                         "Enable/disable advertise the community attribute to a "+
                         "peer or a peer group.";
                     }
                     leaf advertise-ext-community {
                       type "boolean";
                       default "false";
                       description
                         "Enable/disable advertise the extended community "+
                         "attribute to a peer or peer group.";
                     }
                     leaf discard-ext-community {
                       type "boolean";
                       default "false";
                       description
                         "Enable/disable discard the extended community "+
                         "attribute in the routing information about a specified"+
                         " peer.";
                     }
                     container default-route-match-conditions {
                       when "../default-route-match-mode and ../default-route-ma"+
                            "tch-mode!='null'";
                       description
                         "List of condition matching to filter the default "+
                         "routes to be advertised. The value takes effect only "+
                         "when the default route matching mode is not null and "+
                         "more than one IPv4 default route matching condition "+
                         "lists are configured.";
                       list default-route-match-condition {
                         key "address mask";
                         min-elements "1";
                         max-elements "4";
                         description
                           "Configure the matching condition for default route "+
                           "advertisement.";
                         leaf address {
                           type "inet:ipv4-address-no-zone";
                           description
                             "Configure a prefix that is used to match default "+
                             "routes.";
                         }
                         leaf mask {
                           type "uint32" {
                             range "0..32";
                           }
                           description
                             "Configure a mask that is used to match default "+
                             "routes.";
                         }
                       }
                     }
                     container route-limit {
                       description
                         "Configure parameters of routes limited from this "+
                         "peer.";
                       leaf number {
                         type "uint32" {
                           range "1..4294967295";
                         }
                         description
                           "Configure the maximum number of routes that can be "+
                           "accepted from a peer.";
                       }
                       leaf accept-prefix {
                         when "../number";
                         type "boolean";
                         default "false";
                         description
                           "Enable/disable the device to keep receiving routes "+
                           "and the routes are valid if the maximum number of "+
                           "routes allowed have been received and the alert-only"+
                           " parameter is specified.";
                       }
                       leaf percent {
                         when "../number";
                         type "uint8" {
                           range "1..100";
                         }
                         default "75";
                         description
                           "Specify the percentage of routes when a router "+
                           "starts to generate an alarm.";
                       }
                       leaf type {
                         when "../number";
                         type "bgp:route-limit-type";
                         must "(../type='idle-timeout' and ../idle-timeout) or "+
                              "(../type!='idle-timeout')";
                         default "noparameter";
                         description
                           "Set the processing method as alert-only, idle-foreve"+
                           "r, or idle-timeout when the number of routes exceeds"+
                           " the set threshold. When alert-only is used, only an"+
                           " alarm is generated when the number of routes "+
                           "exceeds the threshold. In this case, new routes are "+
                           "no longer accepted. When idle-forever is used, "+
                           "connections are not automatically reestablished "+
                           "after being cut off until BGP connections are reset "+
                           "if the number of routes exceeds the set threshold. "+
                           "When idle-timeout is used and the idle-timeout timer"+
                           " is specified, the connections are automatically "+
                           "reestablished after being cut off if the number of "+
                           "routes exceeds the set threshold. You can reset BGP "+
                           "connections to reestablish the connections before "+
                           "the idle-timeout times expires.";
                       }
                       leaf idle-timeout {
                         when "../type='idle-timeout'";
                         type "uint16" {
                           range "1..1200";
                         }
                         units "min";
                         description
                           "Specify the value of the idle-timeout timer to "+
                           "automatically reestablish the connections after they"+
                           " are cut off when the number of routes exceeds the "+
                           "set threshold.";
                       }
                     }
                     container public-as-only {
                       description
                         "Configure BGP Remove private AS number from outbound "+
                         "updates parameters.";
                       leaf enable {
                         type "boolean";
                         default "false";
                         description
                           "Enable/disable BGP to send Update packets carrying "+
                           "only public AS numbers.";
                       }
                       choice remove-private-as {
                         description
                           "Remove AS numbers except peer AS number from "+
                           "outbound updates.";
                         case all {
                           description
                             "Remove all private AS numbers.";
                           leaf force {
                             when "../enable='true'";
                             type "empty";
                             description
                               "Configures BGP to carry only the public AS "+
                               "number instead of the private AS number when BGP"+
                               " sends Update packets. By default, BGP can carry"+
                               " the private AS number when BGP sends Update "+
                               "packets.";
                           }
                         }
                         case left-most {
                           description
                             "Remove the left-most private AS numbers.";
                           leaf limited {
                             when "../enable='true'";
                             type "empty";
                             description
                               "When the BGP sends update packets, the left ends"+
                               " of both the local AS and public AS do not carry"+
                               " the private AS. By default, BGP can carry the "+
                               "private AS number when BGP sends Update "+
                               "packets.";
                           }
                         }
                       }
                       leaf replace {
                         when "../force or ../limited";
                         type "boolean";
                         default "false";
                         description
                           "Enable/disable the function to the private AS is "+
                           "replaced by the local AS when the BGP sends update "+
                           "packets.";
                       }
                       leaf no-skip-as {
                         when "../force or ../limited";
                         type "boolean";
                         default "false";
                         description
                           "Enable/disable the function to the neighbour AS is "+
                           "not processed when the BGP sends update packets.";
                       }
                     }
                     container public-as-only-import {
                       description
                         "Configure BGP remove private AS number in received BGP"+
                         " update messages parameters.";
                       leaf enable {
                         type "boolean";
                         default "false";
                         description
                           "Enable/disable BGP to receive update packets "+
                           "carrying only public AS numbers.";
                       }
                       choice remove-private-as {
                         description
                           "Remove private AS numbers in received BGP update "+
                           "messages.";
                         case all {
                           description
                             "Forcibly delete all the private AS numbers in the "+
                             "AS_Path list.";
                           leaf force {
                             when "../enable = 'true'";
                             type "empty";
                             description
                               "Enable a device to forcibly remove all the "+
                               "private AS numbers in received BGP update "+
                               "messages in which the AS_Path list contains "+
                               "private AS numbers. By default, a device does "+
                               "not remove private AS numbers from the AS_Path "+
                               "list when receiving BGP update messages.";
                           }
                         }
                       }
                     }
                   }
                   container ipv4-vpn {
                     when "../type = 'ipv4vpn' and ../../../../../../../../ni:na"+
                          "me='_public_'";
                     description
                       "Configure IPv4 vpnv4 options.";
                     leaf advertise-community {
                       type "boolean";
                       default "false";
                       description
                         "Enable/disable advertise the community attribute to a "+
                         "peer or a peer group.";
                     }
                     leaf reflect-client {
                       when "../../../../bgp:type='ibgp'";
                       type "boolean";
                       default "false";
                       description
                         "Enable/disable the local device as a route reflector "+
                         "(RR) and a peer or peer group as its client. This "+
                         "configuration is applicable between IBGP peers only. "+
                         "The configurations of RRs and its clients in an "+
                         "address family are valid only in this address family. "+
                         "Therefore, it is recommended to configure RRs and its "+
                         "clients in the specified address family that is "+
                         "required.";
                     }
                     leaf nexthop-configure {
                       type "nexthop-configuration-type";
                       description
                         "Both the next-hop-local mode and next-hop-invariable "+
                         "mode are available when the peer address family is the"+
                         " VPNv4/VPNV6/L2VPN AD address family. Only the "+
                         "next-hop-local mode is available when the peer address"+
                         " family is not VPNv4/VPNV6/L2VPN AD address family. In"+
                         " next-hop-local mode, you can configure a BGP speaker "+
                         "to set its IP address of as the next hop of the routes"+
                         " to be advertised to IBGP peers or IBGP peer groups. "+
                         "In next-hop-invariable mode, you can configure PEs in "+
                         "different ASs not to change the next hop of routes "+
                         "when the PEs advertise the routes to their EBGP peers "+
                         "and use the next hop addresses of IGP routes to "+
                         "advertise imported IGP routes to IBGP peers. By "+
                         "default, when a BGP speaker advertises routes to EBGP "+
                         "peers and imported IGP routes to IBGP peers, the BGP "+
                         "speaker changes the next hop to its interface "+
                         "address.";
                     }
                     choice import-policy-type {
                       description
                         "Set route policy or filter.";
                       case rtp-ref {
                         description
                           "Route policy.";
                         leaf import-policy {
                           type "leafref" {
                             path "/rtp:routing-policy/rtp:policy-definitions/rt"+
                                  "p:policy-definition/rtp:name";
                           }
                           description
                             "Specify the filtering policy applied to the routes"+
                             " learned from a peer. By default, no such policy "+
                             "is specified.";
                         }
                       }
                       case xpl-ref {
                         description
                           "Route filter.";
                         container import-filter {
                           description
                             "Configure an import route-filter to filter the "+
                             "routes received from a peer group. By default, no "+
                             "route-filter is specified to filter the routes "+
                             "imported from a peer group.";
                           leaf name {
                             type "leafref" {
                               path "/xpl:xpl/xpl:route-filters/xpl:route-filter"+
                                    "/xpl:name";
                             }
                             description
                               "Specify an import route-filter name.";
                           }
                           leaf parameter {
                             when "../name";
                             type "xpl:filter-parameter-type";
                             description
                               "Specify an import route-filter parameter.";
                           }
                         }
                       }
                     }
                     choice export-policy-type {
                       description
                         "Set route policy or filter.";
                       case rtp-ref {
                         description
                           "Route policy.";
                         leaf export-policy {
                           type "leafref" {
                             path "/rtp:routing-policy/rtp:policy-definitions/rt"+
                                  "p:policy-definition/rtp:name";
                           }
                           description
                             "Specify the filtering policy applied to the routes"+
                             " to be advertised to a peer. By default, no such "+
                             "policy is specified.";
                         }
                       }
                       case xpl-ref {
                         description
                           "Route filter.";
                         container export-filter {
                           description
                             "Configure an export route-filter to filter the "+
                             "routes to be advertised to a peer group. By "+
                             "default, no route-filter is specified to filter "+
                             "the routes to be advertised to a peer group.";
                           leaf name {
                             type "leafref" {
                               path "/xpl:xpl/xpl:route-filters/xpl:route-filter"+
                                    "/xpl:name";
                             }
                             description
                               "Specify an export route-filter name.";
                           }
                           leaf parameter {
                             when "../name";
                             type "xpl:filter-parameter-type";
                             description
                               "Specify an export route-filter parameter.";
                           }
                         }
                       }
                     }
                     leaf allow-as-loop {
                       type "uint32" {
                         range "1..10";
                       }
                       description
                         "Allow repetitive local AS numbers. By default, "+
                         "repetitive local AS numbers are not allowed.";
                     }
                     leaf aigp {
                       type "boolean";
                       default "false";
                       description
                         "Enable/disable route with AIGP attribute advertisement"+
                         " to or from a peer.";
                     }
                     leaf add-path-mode {
                       when "../../../../bgp:type='ibgp'";
                       type "add-path-cap-type";
                       default "null";
                       description
                         "Enable Add-Path route advertisement to a peer.";
                     }
                     leaf import-ip-prefix {
                       type "leafref" {
                         path "/rtp:routing-policy/rtp:ipv4-prefix-filters/rtp:i"+
                              "pv4-prefix-filter/rtp:name";
                       }
                       description
                         "Specify the IPv4 filtering policy applied to the "+
                         "routes received from a specified peer. By default, no "+
                         "such policy is specified.";
                     }
                     leaf export-ip-prefix {
                       type "leafref" {
                         path "/rtp:routing-policy/rtp:ipv4-prefix-filters/rtp:i"+
                              "pv4-prefix-filter/rtp:name";
                       }
                       description
                         "Specify the IPv4 filtering policy applied to the "+
                         "routes to be advertised to a specified peer. By "+
                         "default, no such policy is specified.";
                     }
                     leaf import-as-path-filter {
                       type "leafref" {
                         path "/rtp:routing-policy/rtp:as-path-filters/rtp:as-pa"+
                              "th-filter/rtp:name";
                       }
                       description
                         "Apply an AS_Path-based filtering policy to the routes "+
                         "received from a specified peer. The policy can be "+
                         "identified with a name or number, and the number "+
                         "ranges from 1 to 256. By default, no such policy is "+
                         "specified. Therefore, all BGP routes can be accepted.";
                     }
                     leaf export-as-path-filter {
                       type "leafref" {
                         path "/rtp:routing-policy/rtp:as-path-filters/rtp:as-pa"+
                              "th-filter/rtp:name";
                       }
                       description
                         "Apply an AS_Path-based filtering policy to the routes "+
                         "to be advertised to a specified peer. The policy can "+
                         "be identified with a name or number, and the number "+
                         "ranges from 1 to 256. By default, no such policy is "+
                         "specified. Therefore, all BGP routes can be advertised"+
                         ".";
                     }
                     leaf import-acl-name-or-num {
                       type "leafref" {
                         path "/acl:acl/acl:groups/acl:group/acl:identity";
                       }
                       description
                         "Specifies the name of the import ACL policy.";
                     }
                     leaf export-acl-name-or-num {
                       type "leafref" {
                         path "/acl:acl/acl:groups/acl:group/acl:identity";
                       }
                       description
                         "Specifies the name of the export ACL policy.";
                     }
                     leaf route-update-interval {
                       type "uint16" {
                         range "0..600";
                       }
                       units "s";
                       description
                         "Specify the minimum interval at which Update packets "+
                         "are sent. By default, the interval at which Update "+
                         "packets are sent to IBGP peers is 15s, \nand the "+
                         "interval at which Update packets are sent to EBGP "+
                         "peers is 30s. When routes change, a router will send "+
                         "Update packets to notify its peers. \nIf a route "+
                         "changes frequently, you can set an interval at which "+
                         "Update packets are sent to prevent the router from "+
                         "sending Update packets each time the route changes. "+
                         "\nThis configuration is valid only to the routes "+
                         "learned from peers.";
                       ext:dynamic-default;
                     }
                     leaf preferred-value {
                       type "uint32" {
                         range "0..65535";
                       }
                       default "0";
                       description
                         "Assign a preferred value for the routes learned from a"+
                         " specified peer. After a preferred value is configured"+
                         " for the routes learned from a specified peer,\nall "+
                         "the routes that learnt from this peer will use this "+
                         "preferred value. When multiple routes reach the same "+
                         "address prefix, the route with the largest preferred "+
                         "value will be selected.";
                     }
                     leaf add-path-number {
                       when "../../../../bgp:type='ibgp'";
                       type "uint8" {
                         range "2..64";
                       }
                       description
                         "Number of Add-Path routes that can be advertised to a "+
                         "peer.";
                     }
                     leaf upe {
                       type "boolean";
                       default "false";
                       description
                         "Enable/disable the peer as an underlayer PE (UPE).";
                     }
                     leaf advertise-best-external {
                       when "../../../../bgp:type='ibgp'";
                       type "boolean";
                       must "../reflect-client='false' or ../advertise-best-exte"+
                            "rnal='false'";
                       must "../add-path-mode='null' or not(../add-path-mode) or"+
                            " ../advertise-best-external='false'";
                       must "not(../add-path-number and ../advertise-best-extern"+
                            "al='true')";
                       default "false";
                       description
                         "Enable/disable the device to advertise Best External "+
                         "routes to peers.";
                     }
                     leaf keep-all-routes {
                       type "boolean";
                       default "false";
                       description
                         "Enable/disable saving all the updated information "+
                         "about BGP routes from a specified peer or peer group "+
                         "after a BGP connection is established, even though "+
                         "these BGP routes fail to match the routing policy on "+
                         "the ingress. By default, the updated information about"+
                         " BGP routes from a specified peer is saved only when "+
                         "the routes match the routing policy on the ingress. If"+
                         " a router supports route refreshing, this option is "+
                         "not required.";
                     }
                     leaf update-group-independent {
                       type "boolean";
                       default "false";
                       description
                         "Enable/disable the peer which can reside in an "+
                         "independent peer group.";
                     }
                     leaf origin-as-validation {
                       when "../../../../bgp:type='ibgp'";
                       type "boolean";
                       default "false";
                       description
                         "Enable/disable the BGP peer origin validation.";
                     }
                     container default-route-originates {
                       description
                         "Configure advertised default VPNv4 routes.";
                       list default-route-originate {
                         key "vpn-name";
                         description
                           "Configure advertised default VPNv4 route.";
                         leaf vpn-name {
                           type "leafref" {
                             path "/ni:network-instance/ni:instances/ni:instance"+
                                  "/ni:name";
                           }
                           must "../vpn-name!='_public_'";
                           description
                             "VPN instance name. It uniquely identifies a VPN "+
                             "instance. The name is a string of case-sensitive "+
                             "characters.";
                         }
                       }
                     }
                     container route-limit {
                       description
                         "Configure parameters of routes limited from this "+
                         "peer.";
                       leaf number {
                         type "uint32" {
                           range "1..4294967295";
                         }
                         description
                           "Configure the maximum number of routes that can be "+
                           "accepted from a peer.";
                       }
                       leaf percent {
                         when "../number";
                         type "uint8" {
                           range "1..100";
                         }
                         default "75";
                         description
                           "Specify the percentage of routes when a router "+
                           "starts to generate an alarm.";
                       }
                       leaf type {
                         when "../number";
                         type "bgp:route-limit-type";
                         must "(../type='idle-timeout' and ../idle-timeout) or "+
                              "(../type!='idle-timeout')";
                         default "noparameter";
                         description
                           "Set the processing method as alert-only, idle-foreve"+
                           "r, or idle-timeout when the number of routes exceeds"+
                           " the set threshold. When alert-only is used, only an"+
                           " alarm is generated when the number of routes "+
                           "exceeds the threshold. In this case, new routes are "+
                           "no longer accepted. When idle-forever is used, "+
                           "connections are not automatically reestablished "+
                           "after being cut off until BGP connections are reset "+
                           "if the number of routes exceeds the set threshold. "+
                           "When idle-timeout is used and the idle-timeout timer"+
                           " is specified, the connections are automatically "+
                           "reestablished after being cut off if the number of "+
                           "routes exceeds the set threshold. You can reset BGP "+
                           "connections to reestablish the connections before "+
                           "the idle-timeout times expires.";
                       }
                       leaf idle-timeout {
                         when "../type='idle-timeout'";
                         type "uint16" {
                           range "1..1200";
                         }
                         units "min";
                         description
                           "Specify the value of the idle-timeout timer to "+
                           "automatically reestablish the connections after they"+
                           " are cut off when the number of routes exceeds the "+
                           "set threshold.";
                       }
                     }
                     container public-as-only {
                       description
                         "Configure BGP Remove private AS number from outbound "+
                         "updates parameters.";
                       leaf enable {
                         type "boolean";
                         default "false";
                         description
                           "Enable/disable BGP to send Update packets carrying "+
                           "only public AS numbers.";
                       }
                       choice remove-private-as {
                         description
                           "Remove AS numbers except peer AS number from "+
                           "outbound updates.";
                         case all {
                           description
                             "Remove all private AS numbers.";
                           leaf force {
                             when "../enable='true'";
                             type "empty";
                             description
                               "Configures BGP to carry only the public AS "+
                               "number instead of the private AS number when BGP"+
                               " sends Update packets. By default, BGP can carry"+
                               " the private AS number when BGP sends Update "+
                               "packets.";
                           }
                         }
                         case left-most {
                           description
                             "Remove the left-most private AS numbers.";
                           leaf limited {
                             when "../enable='true'";
                             type "empty";
                             description
                               "When the BGP sends update packets, the left ends"+
                               " of both the local AS and public AS do not carry"+
                               " the private AS. By default, BGP can carry the "+
                               "private AS number when BGP sends Update "+
                               "packets.";
                           }
                         }
                       }
                       leaf replace {
                         when "../force or ../limited";
                         type "boolean";
                         default "false";
                         description
                           "Enable/disable the function to the private AS is "+
                           "replaced by the local AS when the BGP sends update "+
                           "packets.";
                       }
                       leaf no-skip-as {
                         when "../force or ../limited";
                         type "boolean";
                         default "false";
                         description
                           "Enable/disable the function to the neighbour AS is "+
                           "not processed when the BGP sends update packets.";
                       }
                     }
                     container public-as-only-import {
                       description
                         "Configure BGP remove private AS number in received BGP"+
                         " update messages parameters.";
                       leaf enable {
                         type "boolean";
                         default "false";
                         description
                           "Enable/disable BGP to receive update packets "+
                           "carrying only public AS numbers.";
                       }
                       choice remove-private-as {
                         description
                           "Remove private AS numbers in received BGP update "+
                           "messages.";
                         case all {
                           description
                             "Forcibly delete all the private AS numbers in the "+
                             "AS_Path list.";
                           leaf force {
                             when "../enable = 'true'";
                             type "empty";
                             description
                               "Enable a device to forcibly remove all the "+
                               "private AS numbers in received BGP update "+
                               "messages in which the AS_Path list contains "+
                               "private AS numbers. By default, a device does "+
                               "not remove private AS numbers from the AS_Path "+
                               "list when receiving BGP update messages.";
                           }
                         }
                       }
                     }
                   }
                 }
               }
             }
           }
           container peers {
             description
               "List of BGP peers.";
             list peer {
               key "address";
               description
                 "Configure a single BGP peer.";
               leaf address {
                 type "inet:ip-address-no-zone";
                 description
                   "Connection address of a peer, which can be an IPv4 or IPv6 "+
                   "address.";
               }
               leaf remote-as {
                 type "as-number-validate";
                 mandatory "true";
                 description
                   "AS number of a peer, which must be selected or group name "+
                   "when creating, and which can be in either two-byte format or"+
                   " four-byte format:\nThe two-byte format is X. X is an "+
                   "integer ranging from 1 to 65535.\nThe four-byte format is "+
                   "X.Y and X. When the format is X.Y, X and Y are both "+
                   "integers, with the value of X ranging from 1 to 65535, and "+
                   "the value of Y ranging from 0 to 65535; when the format is "+
                   "X, X is an interger, with the value of X ranging from 1 to "+
                   "4294967295.\nThe object cannot be modified.";
                 ext:operation-exclude "update" {
                   description
                     "The node cannot be modified, when node is already "+
                     "configured.";
                 }
               }
               leaf group-name {
                 type "leafref" {
                   path "../../../peer-groups/peer-group/name";
                 }
                 description
                   "Specify the name of a peer group that BGP peers need to "+
                   "join. That must be selected group name or AS when creating, "+
                   "and the value is a string, spaces not supported. By default,"+
                   " BGP peers join no peer group. BGP peers distinguish the "+
                   "peer group type when joining a peer group. IBGP peers cannot"+
                   " join an EBGP peer group. BGP peers will be deleted when "+
                   "they leave a peer group. The object cannot be modified.";
                 ext:operation-exclude "update" {
                   description
                     "The node cannot be modified, when the peer already belongs"+
                     " to a peer-group.";
                 }
               }
               leaf local-if-name {
                 type "leafref" {
                   path "/ifm:ifm/ifm:interfaces/ifm:interface/ifm:name";
                 }
                 description
                   "Name of a source interface that sends BGP packets. By "+
                   "default, the outbound interface of a BGP packet serves as "+
                   "the source interface of a BGP packet. To ensure that a "+
                   "router can send BGP packets when a physical interface fails,"+
                   " you can configure the source interface that sends BGP "+
                   "packets as a loopback interface. When using the loopback "+
                   "interface as the source interface, note the following "+
                   "points: 1. The address of the loopback interface of the BGP "+
                   "peer must be reachable. 2. For an EBGP connection, configure"+
                   " the maximum number of hops and allow EBGP peer relationship"+
                   "s to be established in indirect mode.";
               }
               leaf local-if-address {
                 type "inet:ip-address-no-zone";
                 description
                   "Name of a source interface that sends BGP packets. By "+
                   "default, the outbound interface of a BGP packet serves as "+
                   "the source interface of a BGP packet. To ensure that a "+
                   "router can send BGP packets when a physical interface fails,"+
                   " you can configure the source interface that sends BGP "+
                   "packets as a loopback interface. When using the loopback "+
                   "interface as the source interface, note the following "+
                   "points:\n1. The address of the loopback interface of the BGP"+
                   " peer must be reachable.\n2. For an EBGP connection, "+
                   "configure the maximum number of hops and allow EBGP peer "+
                   "relationships to be established in indirect mode.";
                 must "not(contains(., ':'))";
               }
               leaf password-type {
                 type "bgp:password-type";
                 must "not((../password-type and ../password-type!='null') and "+
                      "(../key-chain-name or ../tcp-ao-name))";
                 must "(not(../password-type and ../password-type!='null') and "+
                      "not(../password-text)) or (../password-type and "+
                      "../password-type!='null' and ../password-text)";
                 default "null";
                 description
                   "Enable BGP peers to establish a TCP connection and perform "+
                   "the Message Digest 5 (MD5) authentication for BGP messages. "+
                   "Plaintexts and ciphertexts are supported.";
               }
               leaf password-text {
                 when "../password-type and ../password-type!='null'";
                 type "pub-type:password-extend";
                 mandatory "true";
                 description
                   "Enable BGP peers to establish a TCP connection and perform "+
                   "the Message Digest 5 (MD5) authentication for BGP messages. "+
                   "The character string in a password identifies the contents "+
                   "of the password, spaces not supported. The TCP connection "+
                   "can be established only when the same MD5 authentication "+
                   "password is set on both ends. If a plaintext is used, the "+
                   "maximum password length is 255. If a ciphertext is used, the"+
                   " maximum password length is 432. If the length is set to 0, "+
                   "no password is set.";
               }
               leaf key-chain-name {
                 type "string" {
                   length "1..47";
                   pattern "[^A-Z]+";
                 }
                 must "not(../password-type!='null' or ../tcp-ao-name)";
                 description
                   "Specify the Keychain authentication name used when BGP peers"+
                   " establish a TCP connection. The value is a string, spaces "+
                   "not supported. By default, the Keychain authentication is "+
                   "not configured. Keychain authentication mode and password "+
                   "authentication mode are mutually exclusive. Configuring "+
                   "Keychain authentication can enhance the security of the TCP "+
                   "connections between BGP peers. Keychain authentication using"+
                   " the same encryption algorithm and password must be "+
                   "configured on the two ends of BGP peers to establish a TCP "+
                   "connection and exchange BGP packets. Before configuring BGP "+
                   "Keychain authentication, you need to configure Keychain "+
                   "according to keychain name. Otherwise, the TCP connections "+
                   "between the BGP peers cannot be established.";
                 ext:case-sensitivity "lower-only";
               }
               leaf tcp-ao-disable {
                 type "empty";
                 description
                   "Disable the TCP-AO authentication for establishing the TCP "+
                   "connection between BGP peers.";
               }
               leaf tcp-ao-name {
                 when "not(../tcp-ao-disable)";
                 type "leafref" {
                   path "/socket:socket/socket:tcp-aos/socket:tcp-ao/socket:name"+
                        "";
                 }
                 must "not(../password-type!='null' or ../key-chain-name)";
                 description
                   "Specify TCP-AO authentication for establishing the TCP "+
                   "connection between BGP peers.";
               }
               leaf description {
                 type "string" {
                   length "1..255";
                   pattern "([^?]*)";
                 }
                 description
                   "Description of a peer, which can be letters or digits. The "+
                   "description is a string, spaces supported. By default, no "+
                   "description is configured for a peer.";
               }
               leaf ebgp-max-hop {
                 type "uint32" {
                   range "1..255";
                 }
                 must "not(../valid-ttl-hops) or (../valid-ttl-hops>=1 and "+
                      "../valid-ttl-hops<=255 and ../ebgp-max-hop=1)";
                 description
                   "Maximum number of hops in an indirect EBGP connection. By "+
                   "default, EBGP connections can be established only between "+
                   "directly connected peers. The function must be configured on"+
                   " both ends. By default, value is determined by the neighbor "+
                   "type, the default value of EBGP is 1 and the default value "+
                   "of IBGP is 0.";
               }
               leaf tracking-enable {
                 type "boolean";
                 default "false";
                 description
                   "Enable/disable peer tracking, After peer tracking is "+
                   "enabled, the device can fast detect the unreachability of a "+
                   "peer and reset the session.";
               }
               leaf tracking-delay-time {
                 when "../tracking-enable='true'";
                 type "uint16";
                 units "s";
                 default "0";
                 description
                   "Specify the delay to reset the session.";
               }
               leaf conventional {
                 type "boolean";
                 default "false";
                 description
                   "Enable/disable general router functions on peers. In "+
                   "conventional mode, not all the extended router functions, "+
                   "such as, route refreshing, GR, and multi-address family "+
                   "negotiation, are available. Therefore, the router of a new "+
                   "version can be compatible with the routers of earlier "+
                   "versions.";
               }
               leaf route-refresh {
                 type "boolean";
                 default "true";
                 description
                   "Enable/disable BGP to advertise Refresh messages to peers.";
               }
               leaf four-byte-as {
                 type "boolean";
                 default "true";
                 description
                   "Enable/disable BGP to advertise routes carrying 4-byte AS "+
                   "numbers to peers. After the 4-byte AS number function is "+
                   "disabled, Open packets will not carry 4-byte AS number "+
                   "capability flag, and peer ends will not know that local ends"+
                   " have the 4-byte AS number function. The 4-byte AS number "+
                   "function cannot be disabled from peers (peer groups) if a "+
                   "4-byte AS number, fake AS number, or confederation ID is "+
                   "configured on a router and the AS number of a peer is "+
                   "4-byte. If the 4-byte AS number function is disabled in such"+
                   " a situation, BGP sessions may fail to be established, and "+
                   "route transmission may be affected.";
               }
               leaf ignore {
                 type "boolean";
                 default "false";
                 description
                   "Enable/disable the function to tear down sessions between "+
                   "peers and clear all related routing information.";
               }
               leaf valid-ttl-hops {
                 type "uint16" {
                   range "1..255";
                 }
                 must "not(../ebgp-max-hop and ../ebgp-max-hop>1)";
                 description
                   "Enable GTSM on a peer or peer group. The valid-TTL-Value "+
                   "parameter is used to specify the number of TTL hops to be "+
                   "detected. If the value is configured as hops, the valid TTL "+
                   "range of the detected packet is [255-hops+1, 255].";
               }
               leaf connect-mode {
                 type "connect-mode";
                 default "null";
                 description
                   "The value can be Connect-only, Listen-only, or Both. If the "+
                   "value is Connect-only, the specified peer or peer group only"+
                   " initiatively sends connection requests, instead of "+
                   "listening to connection requests. If the value is Listen-onl"+
                   "y, the specified peer or peer group only listens to "+
                   "connection requests, instead of initiatively sending "+
                   "connection requests. If the value is Both, the specified "+
                   "peer or peer group not only initiatively sends connection "+
                   "requests, but also listens to connection requests. The "+
                   "default value is Both.";
               }
               leaf log-change {
                 type "boolean";
                 default "true";
                 description
                   "Enable/disable BGP to record the session status and events "+
                   "of the specified peer or peer group.";
               }
               leaf check-first-as {
                 type "peer-cap-config-state";
                 default "default";
                 description
                   "Check the first AS in the AS_Path of the update messages "+
                   "from EBGP peers.";
               }
               leaf memory-priority {
                 type "peer-memory-priority";
                 default "default";
                 description
                   "Set a priority that determines the disconnection order of a "+
                   "BGP peer relationship if memory overload occurs.";
               }
               leaf memory-priority-capability {
                 type "memory-priority";
                 config "false";
                 description
                   "Priority that is used to determine the disconnection order "+
                   "of a BGP peer relationship if memory overload occurs.";
               }
               leaf oscillation-dampening {
                 type "peer-attr-enable-type";
                 description
                   "Enable/disable BGP to suppress the establishment of a "+
                   "specified peer relationship that flaps continuously. By "+
                   "default, the capability is enabled.";
               }
               container fake-as-parameter {
                 when "../../../../../../ni:name!='_public_'";
                 description
                   "Configure BGP fake-as parameters.";
                 leaf fake-as {
                   type "bgp:as-number-validate";
                   description
                     "Fake AS number that is specified for a local peer. By "+
                     "default, a peer uses the actual AS number of the local "+
                     "end.\nAn AS number can be in either two-byte format or "+
                     "four-byte format:\nThe two-byte format is X. X is an "+
                     "integer ranging from 1 to 65535.\nThe four-byte format is "+
                     "X.Y and X. When the format is X.Y, X and Y are both "+
                     "integers, with the value of X ranging from 1 to 65535, and"+
                     " the value of Y ranging from 0 to 65535; when the format "+
                     "is X, X is an interger, with the value of X ranging from 1"+
                     " to 4294967295.";
                 }
                 leaf dual-as {
                   when "../fake-as";
                   type "boolean";
                   default "false";
                   description
                     "Enable/disable the function to the remote EBGP peer can "+
                     "use the actual or fake AS number when specifying the AS "+
                     "number for a local peer. The local peer uses the fake and "+
                     "actual AS numbers to establish a BGP peer relationship "+
                     "with the remote end and identifies the AS number "+
                     "configured by the remote end through the error code (OPEN "+
                     "Message Error) and sub-error code (Bad Peer AS) of the "+
                     "Notification message from the remote end.";
                 }
                 leaf prepend-global-as {
                   when "../fake-as";
                   type "boolean";
                   default "false";
                   description
                     "Enable/disable the function to add the global AS number to"+
                     " the update packets to be advertised.";
                 }
                 leaf prepend-fake-as {
                   when "../fake-as";
                   type "boolean";
                   default "false";
                   description
                     "Enable/disable the function to add the fake AS number to "+
                     "received update packets.";
                 }
               }
               container timer {
                 description
                   "Configure BGP peer timer parameters.";
                 leaf keep-alive-time {
                   type "uint32" {
                     range "0..21845";
                   }
                   units "s";
                   must "(../keep-alive-time != 0 and (../hold-time>=../keep-ali"+
                        "ve-time * 3) and ../hold-time != ../keep-alive-time ) "+
                        "or (../hold-time = 0 and ../keep-alive-time = 0)";
                   default "60";
                   description
                     "If the value of a timer changes, the BGP peer relationship"+
                     " between the routers is disconnected. This is because the "+
                     "peers need to re-negotiate the Keepalive time and hold "+
                     "time. Therefore, confirm the action before you change the "+
                     "value of the timer. The Keepalive time should be at least "+
                     "three times of the hold time.";
                 }
                 leaf hold-time {
                   type "uint32" {
                     range "0 | 3..65535";
                   }
                   units "s";
                   must "(((../hold-time>=../keep-alive-time * 3) and ../hold-ti"+
                        "me != ../keep-alive-time ) or (../hold-time = 0 and "+
                        "../keep-alive-time = 0)) and ../hold-time>=../min-hold-"+
                        "time";
                   default "180";
                   description
                     "Hold time. When setting keepalive-time and hold-time, note"+
                     " the following:\n1. The values of keepalive-time and "+
                     "hold-time cannot both be 0. Otherwise, the BGP timer "+
                     "becomes invalid. That is, BGP does not detect link faults "+
                     "according to the timer.\n2. The value of hold-time is much"+
                     " greater than that of keepalive-time, such as, keepalive 1"+
                     " and hold 65535. If the value of hold-time is too large, "+
                     "BGP cannot detect link faults timely.\nThe priority of a "+
                     "timer is lower than that of a peer timer.\nAfter a "+
                     "connection is established between peers, the values of "+
                     "keepalive-time and hold-time are negotiated by the peers. "+
                     "The smaller value of hold-time contained in Open packets "+
                     "of both peers is taken as the value of hold-time. The "+
                     "smaller value of the locally set value of keepalive-time "+
                     "and one third of the value of hold-time is taken as the "+
                     "value of keepalive-time.";
                 }
                 leaf min-hold-time {
                   type "uint32" {
                     range "0 | 20..65535";
                   }
                   units "s";
                   must "../hold-time>=../min-hold-time";
                   default "0";
                   description
                     "The default value of zero means that the minimum hold time"+
                     " check does not take effect. If the value is changed, the "+
                     "new value takes effect since the next peer relationship "+
                     "establishment. During the peer relationship establishment,"+
                     " the local device checks the hold time of the remote end. "+
                     "If the hold time is less than the minimum hold time, the "+
                     "local device sends an error packet with error code 02 and "+
                     "subcode 06, and the peer relationship fails to be "+
                     "established.";
                 }
                 leaf connect-retry-time {
                   type "uint16" {
                     range "1..65535";
                   }
                   units "s";
                   default "32";
                   description
                     "ConnectRetry interval.";
                 }
               }
               container bfd-parameter {
                 description
                   "Configure BFD.";
                 leaf block {
                   type "boolean";
                   must "not(../block='true' and ../enable='true')";
                   default "false";
                   description
                     "Enable/disable preventing a BGP peer from inheriting the "+
                     "BFD configuration of the BGP peer group.";
                 }
                 leaf enable {
                   type "boolean";
                   must "not(../block='true' and ../enable='true')";
                   default "false";
                   description
                     "Enable/disable BFD.";
                 }
                 choice mode-type {
                   description
                     "Set bfd mode.";
                   case single {
                     description
                       "Single hop mode.";
                     leaf single-hop {
                       when "../enable='true'";
                       type "empty";
                       description
                         "The single hop mode is preferred during the BFD "+
                         "session establishment between IBGP peers.";
                     }
                     leaf compatible {
                       when "../enable='true'";
                       type "empty";
                       description
                         "Compatible.";
                     }
                   }
                 }
                 leaf multiplier {
                   type "uint32" {
                     range "3..50";
                   }
                   default "3";
                   description
                     "Specify the detection multiplier.";
                 }
                 leaf min-rx-interval {
                   type "uint32" {
                     range "3..20000";
                   }
                   units "ms";
                   description
                     "Specify the minimum interval at which BFD packets are "+
                     "received. The value range and default value are controlled"+
                     " by the PAF.";
                 }
                 leaf min-tx-interval {
                   type "uint32" {
                     range "3..20000";
                   }
                   units "ms";
                   description
                     "Specify the minimum interval at which BFD packets are "+
                     "sent. The value range and default value are controlled by "+
                     "the PAF.";
                 }
                 leaf valid-ttl-hops-operation {
                   type "enumeration" {
                     enum "enable" {
                       value "1";
                       description
                         "Enable:";
                     }
                     enum "disable" {
                       value "2";
                       description
                         "Disable:";
                     }
                   }
                   description
                     "Control specify the valid TTL hops value operation.";
                 }
                 leaf valid-ttl-hops {
                   when "../valid-ttl-hops-operation='enable'";
                   type "uint8" {
                     range "1..255";
                   }
                   mandatory "true";
                   description
                     "Specify the valid TTL hops value.";
                 }
               }
               container bfd-parameter-state {
                 config "false";
                 description
                   "Statistics of BFD Parameter State.";
                 leaf valid-ttl-hops {
                   type "uint8" {
                     range "1..255";
                   }
                   description
                     "The valid TTL hops value.";
                 }
               }
               container graceful-restart {
                 description
                   "Configure graceful restart.";
                 leaf enable {
                   type "peer-comm-config-type";
                   default "default";
                   description
                     "Enable/disable graceful restart capability.";
                 }
                 leaf time-wait-for-rib {
                   type "uint32" {
                     range "3..3000";
                   }
                   units "s";
                   description
                     "Period of waiting for the End-of-RIB flag. The value is an"+
                     " integer. When a BGP session is established or re-establis"+
                     "hed, the router enabled with GR should receive the "+
                     "End-of-RIB flag in this period. If the router does not "+
                     "receive the End-of-RIB flag in this period, ensure that "+
                     "the router can exit from the GR process.";
                 }
                 leaf restart-time {
                   type "uint16" {
                     range "3..3600";
                   }
                   units "s";
                   description
                     "Specifies the maximum time during which a peer waits for a"+
                     " BGP session reestablishment.";
                 }
                 leaf effect-restart-time {
                   type "uint16" {
                     range "3..3600";
                   }
                   units "s";
                   config "false";
                   description
                     "The maximum time during which a peer waits for a BGP "+
                     "session reestablishment.";
                 }
                 leaf effect-time-wait-for-rib {
                   type "uint32" {
                     range "3..3000";
                   }
                   units "s";
                   config "false";
                   description
                     "Period of waiting for the End-of-RIB flag.";
                 }
                 leaf effect-enable {
                   type "boolean";
                   config "false";
                   description
                     "Whether enable/disable graceful restart capability.";
                 }
                 leaf peer-reset {
                   type "peer-comm-config-type";
                   default "default";
                   description
                     "Enable/disable reseting BGP peer graceful.";
                 }
                 leaf effect-peer-reset {
                   type "boolean";
                   config "false";
                   description
                     "Whether enable/disable reseting BGP peer graceful.";
                 }
               }
               container local-graceful-restart {
                 description
                   "Configure local graceful restart.";
                 leaf enable {
                   type "peer-comm-config-type";
                   default "default";
                   description
                     "Enable/disable graceful restart capability.";
                 }
                 leaf time-wait-for-rib {
                   type "uint32" {
                     range "3..3000";
                   }
                   units "s";
                   description
                     "Period of waiting for the End-of-RIB flag. The value is an"+
                     " integer. When a BGP session is established or re-establis"+
                     "hed, the router enabled with GR should receive the "+
                     "End-of-RIB flag in this period. If the router does not "+
                     "receive the End-of-RIB flag in this period, ensure that "+
                     "the router can exit from the GR process.";
                 }
                 leaf restart-time {
                   type "uint16" {
                     range "3..3600";
                   }
                   units "s";
                   description
                     "Specifies the maximum time during which a peer waits for a"+
                     " BGP session reestablishment.";
                 }
                 leaf effect-restart-time {
                   type "uint16" {
                     range "3..3600";
                   }
                   units "s";
                   config "false";
                   description
                     "The maximum time during which a peer waits for a BGP "+
                     "session reestablishment.";
                 }
                 leaf effect-time-wait-for-rib {
                   type "uint32" {
                     range "3..3000";
                   }
                   units "s";
                   config "false";
                   description
                     "Period of waiting for the End-of-RIB flag.";
                 }
                 leaf effect-enable {
                   type "boolean";
                   config "false";
                   description
                     "Whether enable/disable graceful restart capability.";
                 }
               }
               container afs {
                 description
                   "List of peers in a specified address family.";
                 list af {
                   key "type";
                   description
                     "Configure peer in a specified address family.";
                   leaf type {
                     type "enumeration" {
                       enum "ipv4uni" {
                         value "1";
                         description
                           "IPv4 unicast address family.";
                       }
                       enum "ipv4vpn" {
                         value "3";
                         description
                           "IPv4 VPN address family.";
                       }
                     }
                     must "../../../../../afs/af[type = current()]";
                     description
                       "Specify the address family type to set the peer enable.";
                   }
                   container ipv4-unicast {
                     when "../type='ipv4uni' and ../../../../../../../../ni:name"+
                          "!='_public_'";
                     must "../../../../../../../../l3vpn:afs/l3vpn:af[l3vpn:type"+
                          "='ipv4-unicast']";
                     description
                       "Configure IPv4 unicast options.";
                     leaf group-name {
                       type "leafref" {
                         path "../../../../../../peer-groups/peer-group/name";
                       }
                       must "../../../../../../peer-groups/peer-group[name = "+
                            "current()]/afs/af[type = 'ipv4uni']";
                       description
                         "Configure a name for a peer group. After a peer is "+
                         "deleted from the peer group, the peer is disabled from"+
                         " the address family. The object cannot be modified.";
                       ext:operation-exclude "update" {
                         description
                           "The node cannot be modified, when the peer already "+
                           "belongs to a peer-group.";
                       }
                     }
                     leaf reflect-client {
                       type "boolean";
                       default "false";
                       description
                         "Enable/disable the local device as a route reflector "+
                         "(RR) and a peer or peer group as its client. This "+
                         "configuration is applicable between IBGP peers only. "+
                         "The configurations of RRs and its clients in an "+
                         "address family are valid only in this address family. "+
                         "Therefore, it is recommended to configure RRs and its "+
                         "clients in the specified address family that is "+
                         "required.";
                     }
                     leaf label-route-capability {
                       type "boolean";
                       default "false";
                       description
                         "Enable/disable a device to exchange labeled routes.";
                     }
                     leaf check-tunnel-reachable {
                       when "../label-route-capability='true'";
                       type "boolean";
                       default "false";
                       description
                         "Enable/disable tunnel reachability check.";
                     }
                     leaf nexthop-configure {
                       type "vrf-nexthop-configuration-type";
                       description
                         "Both the next-hop-local mode and next-hop-invariable "+
                         "mode are available when the peer address family is the"+
                         " VPNv4/VPNV6/L2VPN AD address family. Only the "+
                         "next-hop-local mode is available when the peer address"+
                         " family is not VPNv4/VPNV6/L2VPN AD address family. In"+
                         " next-hop-local mode, you can configure a BGP speaker "+
                         "to set its IP address of as the next hop of the routes"+
                         " to be advertised to IBGP peers or IBGP peer groups. "+
                         "In next-hop-invariable mode, you can configure PEs in "+
                         "different ASs not to change the next hop of routes "+
                         "when the PEs advertise the routes to their EBGP peers "+
                         "and use the next hop addresses of IGP routes to "+
                         "advertise imported IGP routes to IBGP peers. By "+
                         "default, when a BGP speaker advertises routes to EBGP "+
                         "peers and imported IGP routes to IBGP peers, the BGP "+
                         "speaker changes the next hop to its interface "+
                         "address.";
                     }
                     choice import-policy-type {
                       description
                         "Set route policy or filter.";
                       case rtp-ref {
                         description
                           "Route policy.";
                         leaf import-policy {
                           type "leafref" {
                             path "/rtp:routing-policy/rtp:policy-definitions/rt"+
                                  "p:policy-definition/rtp:name";
                           }
                           description
                             "Specify the filtering policy applied to the routes"+
                             " learned from a peer. By default, no such policy "+
                             "is specified.";
                         }
                       }
                       case xpl-ref {
                         description
                           "Route filter.";
                         container import-filter {
                           description
                             "Configure an import route-filter to filter the "+
                             "routes received from a peer group. By default, no "+
                             "route-filter is specified to filter the routes "+
                             "imported from a peer group.";
                           leaf name {
                             type "leafref" {
                               path "/xpl:xpl/xpl:route-filters/xpl:route-filter"+
                                    "/xpl:name";
                             }
                             description
                               "Specify an import route-filter name.";
                           }
                           leaf parameter {
                             when "../name";
                             type "xpl:filter-parameter-type";
                             description
                               "Specify an import route-filter parameter.";
                           }
                         }
                       }
                     }
                     choice export-policy-type {
                       description
                         "Set route policy or filter.";
                       case rtp-ref {
                         description
                           "Route policy.";
                         leaf export-policy {
                           type "leafref" {
                             path "/rtp:routing-policy/rtp:policy-definitions/rt"+
                                  "p:policy-definition/rtp:name";
                           }
                           description
                             "Specify the filtering policy applied to the routes"+
                             " to be advertised to a peer. By default, no such "+
                             "policy is specified.";
                         }
                       }
                       case xpl-ref {
                         description
                           "Route filter.";
                         container export-filter {
                           description
                             "Configure an export route-filter to filter the "+
                             "routes to be advertised to a peer group. By "+
                             "default, no route-filter is specified to filter "+
                             "the routes to be advertised to a peer group.";
                           leaf name {
                             type "leafref" {
                               path "/xpl:xpl/xpl:route-filters/xpl:route-filter"+
                                    "/xpl:name";
                             }
                             description
                               "Specify an export route-filter name.";
                           }
                           leaf parameter {
                             when "../name";
                             type "xpl:filter-parameter-type";
                             description
                               "Specify an export route-filter parameter.";
                           }
                         }
                       }
                     }
                     leaf allow-as-loop {
                       type "uint32" {
                         range "1..10";
                       }
                       description
                         "Allow repetitive local AS numbers. By default, "+
                         "repetitive local AS numbers are not allowed.";
                     }
                     leaf default-route-advertise {
                       type "boolean";
                       default "false";
                       description
                         "Enable/disable a device to advertise the default route"+
                         " to its peers. This option enables a device to send a "+
                         "default route with the device as the next hop address "+
                         "to its peers, regardless of whether there is a default"+
                         " route in the local routing table.";
                     }
                     choice default-route-advertise-policy-type {
                       description
                         "Set default route advertise-policy.";
                       case rtp-ref {
                         description
                           "The default-route-advertise-policy.";
                         leaf default-route-advertise-policy {
                           when "../default-route-advertise='true'";
                           type "leafref" {
                             path "/rtp:routing-policy/rtp:policy-definitions/rt"+
                                  "p:policy-definition/rtp:name";
                           }
                           description
                             "Specify the name of a used policy.";
                         }
                       }
                       case xpl-ref {
                         description
                           "The default-route-advertise-filter.";
                         container default-route-advertise-filter {
                           when "../default-route-advertise='true'";
                           description
                             "Configure the route-filter for default route "+
                             "advertise.";
                           leaf filter-name {
                             type "leafref" {
                               path "/xpl:xpl/xpl:route-filters/xpl:route-filter"+
                                    "/xpl:name";
                             }
                             description
                               "Specify a route-filter name.";
                           }
                           leaf filter-parameter {
                             when "../filter-name";
                             type "xpl:filter-parameter-type";
                             description
                               "Specify a route-filter parameter.";
                           }
                         }
                       }
                     }
                     leaf default-route-match-mode {
                       when "../default-route-advertise='true'";
                       type "cra-match-mode";
                       default "null";
                       description
                         "Configure the matching mode of default route "+
                         "advertisement, which can be disabling of route "+
                         "advertisement conditions, enabling of all route "+
                         "advertisement conditions, and enabling of part route "+
                         "advertisement conditions. Enabling of all route "+
                         "advertisement conditions indicates that a default "+
                         "route can be advertised only when it matches all the "+
                         "conditions. Enabling of part route advertisement "+
                         "conditions indicates that a default route can be "+
                         "advertised only when it matches one condition.";
                     }
                     leaf import-ip-prefix {
                       type "leafref" {
                         path "/rtp:routing-policy/rtp:ipv4-prefix-filters/rtp:i"+
                              "pv4-prefix-filter/rtp:name";
                       }
                       description
                         "Specify the IPv4 filtering policy applied to the "+
                         "routes received from a specified peer. By default, no "+
                         "such policy is specified.";
                     }
                     leaf export-ip-prefix {
                       type "leafref" {
                         path "/rtp:routing-policy/rtp:ipv4-prefix-filters/rtp:i"+
                              "pv4-prefix-filter/rtp:name";
                       }
                       description
                         "Specify the IPv4 filtering policy applied to the "+
                         "routes to be advertised to a specified peer. By "+
                         "default, no such policy is specified.";
                     }
                     leaf import-as-path-filter {
                       type "leafref" {
                         path "/rtp:routing-policy/rtp:as-path-filters/rtp:as-pa"+
                              "th-filter/rtp:name";
                       }
                       description
                         "Apply an AS_Path-based filtering policy to the routes "+
                         "received from a specified peer. The policy can be "+
                         "identified with a name or number, and the number "+
                         "ranges from 1 to 256. By default, no such policy is "+
                         "specified. Therefore, all BGP routes can be accepted.";
                     }
                     leaf export-as-path-filter {
                       type "leafref" {
                         path "/rtp:routing-policy/rtp:as-path-filters/rtp:as-pa"+
                              "th-filter/rtp:name";
                       }
                       description
                         "Apply an AS_Path-based filtering policy to the routes "+
                         "to be advertised to a specified peer. The policy can "+
                         "be identified with a name or number, and the number "+
                         "ranges from 1 to 256. By default, no such policy is "+
                         "specified. Therefore, all BGP routes can be advertised"+
                         ".";
                     }
                     leaf import-acl-name-or-num {
                       type "leafref" {
                         path "/acl:acl/acl:groups/acl:group/acl:identity";
                       }
                       description
                         "Specifies the name of the import ACL policy.";
                     }
                     leaf export-acl-name-or-num {
                       type "leafref" {
                         path "/acl:acl/acl:groups/acl:group/acl:identity";
                       }
                       description
                         "Specifies the name of the export ACL policy.";
                     }
                     leaf route-update-interval {
                       type "uint16" {
                         range "0..600";
                       }
                       units "s";
                       description
                         "Specify the minimum interval at which Update packets "+
                         "are sent. By default, the interval at which Update "+
                         "packets are sent to IBGP peers is 15s, \nand the "+
                         "interval at which Update packets are sent to EBGP "+
                         "peers is 30s. When routes change, a router will send "+
                         "Update packets to notify its peers. \nIf a route "+
                         "changes frequently, you can set an interval at which "+
                         "Update packets are sent to prevent the router from "+
                         "sending Update packets each time the route changes. "+
                         "\nThis configuration is valid only to the routes "+
                         "learned from peers.";
                       ext:dynamic-default;
                     }
                     leaf preferred-value {
                       type "uint32" {
                         range "0..65535";
                       }
                       default "0";
                       description
                         "Assign a preferred value for the routes learned from a"+
                         " specified peer. After a preferred value is configured"+
                         " for the routes learned from a specified peer,\nall "+
                         "the routes that learnt from this peer will use this "+
                         "preferred value. When multiple routes reach the same "+
                         "address prefix, the route with the largest preferred "+
                         "value will be selected.";
                     }
                     leaf substitute-as-enable {
                       type "boolean";
                       default "false";
                       description
                         "Enable/disable replace the AS number of a specified "+
                         "peer in the AS_Path attribute with the local AS "+
                         "number. On a PE where AS number replacement is "+
                         "enabled, if an AS number in the AS_Path attribute of a"+
                         " route is same as that of the CE to which the PE "+
                         "advertises the route, the PE replaces the AS number "+
                         "with its own AS number before advertising the route.";
                     }
                     leaf soo {
                       type "string" {
                         length "3..21";
                       }
                       description
                         "Configure the Site-of-Origin (SoO) extended community "+
                         "attribute. This attribute can be expressed in the "+
                         "following formats: X.X.X.X:number<0-65535>, number<0-6"+
                         "5535>:number<0-4294967295>, or number<0-65535>.number<"+
                         "0-65535>:number<0-65535> or <65536-4294967295>:<0-6553"+
                         "5>. 0:0 or 0.0:0 is not supported. \nTwo CEs are in "+
                         "the same site and can advertise routes to each other, "+
                         "and they are connected to a VPN through PEs. If the "+
                         "local routes of a CE are advertised to the other CE "+
                         "over the VPN, a routing loop may occur. \nThe SoO "+
                         "feature can prevent a route advertised by a site from "+
                         "being sent back to the site, preventing routing loops."+
                         " After SoO is enabled and a PE receives a route from a"+
                         " CE, the specified SoO attribute will be added to the "+
                         "route. Before advertising the route to the other CE, "+
                         "the PE checks the SoO attribute. If the SoO attribute "+
                         "is the same as the locally configured SoO attribute, "+
                         "the PE does not advertise the route, preventing "+
                         "routing loops.";
                     }
                     leaf keep-all-routes {
                       type "boolean";
                       default "false";
                       description
                         "Enable/disable saving all the updated information "+
                         "about BGP routes from a specified peer or peer group "+
                         "after a BGP connection is established, even though "+
                         "these BGP routes fail to match the routing policy on "+
                         "the ingress. By default, the updated information about"+
                         " BGP routes from a specified peer is saved only when "+
                         "the routes match the routing policy on the ingress. If"+
                         " a router supports route refreshing, this option is "+
                         "not required.";
                     }
                     leaf load-balancing-enable {
                       type "boolean";
                       default "false";
                       description
                         "Enable/disable a neighbour to participate in load "+
                         "balancing.";
                     }
                     choice load-balancing-ignore-as-type {
                       description
                         "Set load balancing as path type.";
                       case as-attribute {
                         description
                           "Ignore the as-path attribute.";
                         leaf load-balancing-as-path-ignore {
                           when "../load-balancing-enable='true'";
                           type "empty";
                           description
                             "Configure BGP to ignore the AS_Path attribute when"+
                             " selecting the equal route. After as-path-neglect "+
                             "is selected, BGP does not compare the AS_Path "+
                             "length.";
                         }
                       }
                       case same-length-as-attribute {
                         description
                           "Ignore comparison of as-path attributes with the "+
                           "same length.";
                         leaf load-balancing-as-path-relax {
                           when "../load-balancing-enable='true'";
                           type "empty";
                           description
                             "Configure BGP to ignore comparison of AS_Path "+
                             "attributes with the same length when selecting the"+
                             " equal route. After as-path-neglect is selected, "+
                             "BGP does not compare the AS_Path length.";
                         }
                       }
                     }
                     leaf advertise-community {
                       type "boolean";
                       default "false";
                       description
                         "Enable/disable advertise the community attribute to a "+
                         "peer or a peer group.";
                     }
                     leaf advertise-ext-community {
                       type "boolean";
                       default "false";
                       description
                         "Enable/disable advertise the extended community "+
                         "attribute to a peer or peer group.";
                     }
                     leaf discard-ext-community {
                       type "boolean";
                       default "false";
                       description
                         "Enable/disable discard the extended community "+
                         "attribute in the routing information about a specified"+
                         " peer.";
                     }
                     leaf advertise-large-community {
                       type "bgp:peer-comm-config-type";
                       default "default";
                       description
                         "Enable large-community attribute advertisement. The "+
                         "Link-state address family and the RPD address family "+
                         "do not support this element.";
                     }
                     leaf advertise-large-community-state {
                       type "boolean";
                       default "false";
                       config "false";
                       description
                         "Whether large-community attribute advertisement is "+
                         "enabled on a peer. The Link-state address family and "+
                         "the RPD address family do not support this element.";
                     }
                     leaf update-group-independent {
                       type "bgp:peer-comm-config-type";
                       default "default";
                       description
                         "Enable/disable the peer which can reside in an "+
                         "independent peer group.";
                     }
                     leaf update-group-independent-state {
                       type "boolean";
                       config "false";
                       description
                         "Whether the peer can reside in an independent peer "+
                         "group.";
                     }
                     container default-route-match-conditions {
                       when "../default-route-match-mode and ../default-route-ma"+
                            "tch-mode!='null'";
                       description
                         "List of condition matching to filter the default "+
                         "routes to be advertised. The value takes effect only "+
                         "when the default route matching mode is not null and "+
                         "more than one IPv4 default route matching condition "+
                         "lists are configured.";
                       list default-route-match-condition {
                         key "address mask";
                         min-elements "1";
                         max-elements "4";
                         description
                           "Configure the matching condition for default route "+
                           "advertisement.";
                         leaf address {
                           type "inet:ipv4-address-no-zone";
                           description
                             "Configure a prefix that is used to match default "+
                             "routes.";
                         }
                         leaf mask {
                           type "uint32" {
                             range "0..32";
                           }
                           description
                             "Configure a mask that is used to match default "+
                             "routes.";
                         }
                       }
                     }
                     container route-limit {
                       description
                         "Configure parameters of routes limited from this "+
                         "peer.";
                       leaf number {
                         type "uint32" {
                           range "1..4294967295";
                         }
                         description
                           "Configure the maximum number of routes that can be "+
                           "accepted from a peer.";
                       }
                       leaf accept-prefix {
                         when "../number";
                         type "boolean";
                         default "false";
                         description
                           "Enable/disable the device to keep receiving routes "+
                           "and the routes are valid if the maximum number of "+
                           "routes allowed have been received and the alert-only"+
                           " parameter is specified.";
                       }
                       leaf percent {
                         when "../number";
                         type "uint8" {
                           range "1..100";
                         }
                         default "75";
                         description
                           "Specify the percentage of routes when a router "+
                           "starts to generate an alarm.";
                       }
                       leaf type {
                         when "../number";
                         type "bgp:route-limit-type";
                         must "(../type='idle-timeout' and ../idle-timeout) or "+
                              "(../type!='idle-timeout')";
                         default "noparameter";
                         description
                           "Set the processing method as alert-only, idle-foreve"+
                           "r, or idle-timeout when the number of routes exceeds"+
                           " the set threshold. When alert-only is used, only an"+
                           " alarm is generated when the number of routes "+
                           "exceeds the threshold. In this case, new routes are "+
                           "no longer accepted. When idle-forever is used, "+
                           "connections are not automatically reestablished "+
                           "after being cut off until BGP connections are reset "+
                           "if the number of routes exceeds the set threshold. "+
                           "When idle-timeout is used and the idle-timeout timer"+
                           " is specified, the connections are automatically "+
                           "reestablished after being cut off if the number of "+
                           "routes exceeds the set threshold. You can reset BGP "+
                           "connections to reestablish the connections before "+
                           "the idle-timeout times expires.";
                       }
                       leaf idle-timeout {
                         when "../type='idle-timeout'";
                         type "uint16" {
                           range "1..1200";
                         }
                         units "min";
                         description
                           "Specify the value of the idle-timeout timer to "+
                           "automatically reestablish the connections after they"+
                           " are cut off when the number of routes exceeds the "+
                           "set threshold.";
                       }
                     }
                     container public-as-only {
                       description
                         "Configure BGP Remove private AS number from outbound "+
                         "updates parameters.";
                       leaf enable {
                         type "boolean";
                         default "false";
                         description
                           "Enable/disable BGP to send Update packets carrying "+
                           "only public AS numbers.";
                       }
                       choice remove-private-as {
                         description
                           "Remove AS numbers except peer AS number from "+
                           "outbound updates.";
                         case all {
                           description
                             "Remove all private AS numbers.";
                           leaf force {
                             when "../enable='true'";
                             type "empty";
                             description
                               "Configures BGP to carry only the public AS "+
                               "number instead of the private AS number when BGP"+
                               " sends Update packets. By default, BGP can carry"+
                               " the private AS number when BGP sends Update "+
                               "packets.";
                           }
                         }
                         case left-most {
                           description
                             "Remove the left-most private AS numbers.";
                           leaf limited {
                             when "../enable='true'";
                             type "empty";
                             description
                               "When the BGP sends update packets, the left ends"+
                               " of both the local AS and public AS do not carry"+
                               " the private AS. By default, BGP can carry the "+
                               "private AS number when BGP sends Update "+
                               "packets.";
                           }
                         }
                       }
                       leaf replace {
                         when "../force or ../limited";
                         type "boolean";
                         default "false";
                         description
                           "Enable/disable the function to the private AS is "+
                           "replaced by the local AS when the BGP sends update "+
                           "packets.";
                       }
                       leaf no-skip-as {
                         when "../force or ../limited";
                         type "boolean";
                         default "false";
                         description
                           "Enable/disable the function to the neighbour AS is "+
                           "not processed when the BGP sends update packets.";
                       }
                     }
                     container public-as-only-import {
                       description
                         "Configure BGP remove private AS number in received BGP"+
                         " update messages parameters.";
                       leaf enable {
                         type "bgp:peer-comm-config-type";
                         default "default";
                         description
                           "Enable/disable BGP to receive update packets "+
                           "carrying only public AS numbers.";
                       }
                       choice remove-private-as {
                         description
                           "Remove private AS numbers in received BGP update "+
                           "messages.";
                         case all {
                           description
                             "Forcibly delete all the private AS numbers in the "+
                             "AS_Path list.";
                           leaf force {
                             when "../enable = 'enable'";
                             type "empty";
                             description
                               "Enable a device to forcibly remove all the "+
                               "private AS numbers in received BGP update "+
                               "messages in which the AS_Path list contains "+
                               "private AS numbers. By default, a device does "+
                               "not remove private AS numbers from the AS_Path "+
                               "list when receiving BGP update messages.";
                           }
                         }
                       }
                       leaf effect-enable {
                         type "boolean";
                         config "false";
                         description
                           "Flag indicating that the device is enabled to remove"+
                           " private AS numbers from the AS_Path list in "+
                           "received BGP update messages.";
                       }
                       leaf effect-force {
                         type "boolean";
                         config "false";
                         description
                           "Flag indicating that the device is enabled to "+
                           "forcibly remove all the private AS numbers from the "+
                           "AS_Path list in received BGP update messages.";
                       }
                     }
                     container path-attribute-treats {
                       description
                         "List of modes in which specified path attributes are "+
                         "processed.";
                       list path-attribute-treat {
                         must "discard-id-map or withdraw-id-map or unknown-id-m"+
                              "ap";
                         key "treat-type";
                         description
                           "Configure mode in which specified path attributes "+
                           "are processed.";
                         leaf treat-type {
                           type "bgp:path-attr-treat-type";
                           description
                             "Mode in which specified path attributes are "+
                             "processed.";
                         }
                         leaf discard-id-map {
                           type "pub-type:id-range" {
                             pattern "((25[0-5]|2[0-4][0-9]|1[0-9][0-9]|[1-9][0-"+
                                     "9]|[0-9])?(-(25[0-5]|2[0-4][0-9]|1[0-9][0-"+
                                     "9]|[1-9][0-9]|[0-9]))?(,((25[0-5]|2[0-4][0"+
                                     "-9]|1[0-9][0-9]|[1-9][0-9]|[0-9])(-(25[0-5"+
                                     "]|2[0-4][0-9]|1[0-9][0-9]|[1-9][0-9]|[0-9]"+
                                     "))?))*)|((([\\+|\\-](25[0-5]|2[0-4][0-"+
                                     "9]|1[0-9][0-9]|[1-9][0-9]|[0-9]))|([\\+|"+
                                     "\\-]\\((25[0-5]|2[0-4][0-9]|1[0-9][0-9"+
                                     "]|[1-9][0-9]|[0-9])-(25[0-5]|2[0-4][0-9]|1"+
                                     "[0-9][0-9]|[1-9][0-9]|[0-9])\\)))?(,((["+
                                     "\\+|\\-](25[0-5]|2[0-4][0-9]|1[0-9][0-"+
                                     "9]|[1-9][0-9]|[0-9]))|([\\+|\\-]\\(("+
                                     "25[0-5]|2[0-4][0-9]|1[0-9][0-9]|[1-9][0-9]"+
                                     "|[0-9])-(25[0-5]|2[0-4][0-9]|1[0-9][0-9]|["+
                                     "1-9][0-9]|[0-9])\\))))*)";
                             ext:value-range "0..255";
                           }
                           description
                             "Specify a discard attribute ID list. The attribute"+
                             " IDs which are not supported as follows: 1 "+
                             "(ORIGIN), 2 (AS_PATH), 3 (NEXT_HOP), 4 (MED), 5 "+
                             "(LOCAL_PREF), 6 (ATOMICAGGREGATE), 7 (AGGREGATOR),"+
                             " 8 (COMMUNITY), 9 (ORIGINATOR_ID), 10 (CLUSTER_LIS"+
                             "T), 14 (MP_REACH_NLRI), 15 (MP_UNREACH_NLRI), 17 "+
                             "(AS4PATH), 18 (AS4AGGREGATOR).";
                         }
                         leaf withdraw-id-map {
                           type "pub-type:id-range" {
                             pattern "((25[0-5]|2[0-4][0-9]|1[0-9][0-9]|[1-9][0-"+
                                     "9]|[0-9])?(-(25[0-5]|2[0-4][0-9]|1[0-9][0-"+
                                     "9]|[1-9][0-9]|[0-9]))?(,((25[0-5]|2[0-4][0"+
                                     "-9]|1[0-9][0-9]|[1-9][0-9]|[0-9])(-(25[0-5"+
                                     "]|2[0-4][0-9]|1[0-9][0-9]|[1-9][0-9]|[0-9]"+
                                     "))?))*)|((([\\+|\\-](25[0-5]|2[0-4][0-"+
                                     "9]|1[0-9][0-9]|[1-9][0-9]|[0-9]))|([\\+|"+
                                     "\\-]\\((25[0-5]|2[0-4][0-9]|1[0-9][0-9"+
                                     "]|[1-9][0-9]|[0-9])-(25[0-5]|2[0-4][0-9]|1"+
                                     "[0-9][0-9]|[1-9][0-9]|[0-9])\\)))?(,((["+
                                     "\\+|\\-](25[0-5]|2[0-4][0-9]|1[0-9][0-"+
                                     "9]|[1-9][0-9]|[0-9]))|([\\+|\\-]\\(("+
                                     "25[0-5]|2[0-4][0-9]|1[0-9][0-9]|[1-9][0-9]"+
                                     "|[0-9])-(25[0-5]|2[0-4][0-9]|1[0-9][0-9]|["+
                                     "1-9][0-9]|[0-9])\\))))*)";
                             ext:value-range "0..255";
                           }
                           description
                             "Specify a withdraw attribute ID list. The "+
                             "attribute IDs which are not supported as follows: "+
                             "1 (ORIGIN), 2 (AS_PATH), 3 (NEXT_HOP), 4 (MED), 5 "+
                             "(LOCAL_PREF), 6 (ATOMICAGGREGATE), 7 (AGGREGATOR),"+
                             " 8 (COMMUNITY), 9 (ORIGINATOR_ID), 10 (CLUSTER_LIS"+
                             "T), 14 (MP_REACH_NLRI), 15 (MP_UNREACH_NLRI), 17 "+
                             "(AS4PATH), 18 (AS4AGGREGATOR).";
                         }
                         leaf unknown-id-map {
                           type "pub-type:id-range" {
                             pattern "((25[0-5]|2[0-4][0-9]|1[0-9][0-9]|[1-9][0-"+
                                     "9]|[0-9])?(-(25[0-5]|2[0-4][0-9]|1[0-9][0-"+
                                     "9]|[1-9][0-9]|[0-9]))?(,((25[0-5]|2[0-4][0"+
                                     "-9]|1[0-9][0-9]|[1-9][0-9]|[0-9])(-(25[0-5"+
                                     "]|2[0-4][0-9]|1[0-9][0-9]|[1-9][0-9]|[0-9]"+
                                     "))?))*)|((([\\+|\\-](25[0-5]|2[0-4][0-"+
                                     "9]|1[0-9][0-9]|[1-9][0-9]|[0-9]))|([\\+|"+
                                     "\\-]\\((25[0-5]|2[0-4][0-9]|1[0-9][0-9"+
                                     "]|[1-9][0-9]|[0-9])-(25[0-5]|2[0-4][0-9]|1"+
                                     "[0-9][0-9]|[1-9][0-9]|[0-9])\\)))?(,((["+
                                     "\\+|\\-](25[0-5]|2[0-4][0-9]|1[0-9][0-"+
                                     "9]|[1-9][0-9]|[0-9]))|([\\+|\\-]\\(("+
                                     "25[0-5]|2[0-4][0-9]|1[0-9][0-9]|[1-9][0-9]"+
                                     "|[0-9])-(25[0-5]|2[0-4][0-9]|1[0-9][0-9]|["+
                                     "1-9][0-9]|[0-9])\\))))*)";
                             ext:value-range "0..255";
                           }
                           description
                             "Specify an unknown attribute ID list. The "+
                             "attribute IDs which are not supported as follows: "+
                             "1 (ORIGIN), 2 (AS_PATH), 3 (NEXT_HOP), 4 (MED), 5 "+
                             "(LOCAL_PREF), 6 (ATOMICAGGREGATE), 7 (AGGREGATOR),"+
                             " 8 (COMMUNITY), 9 (ORIGINATOR_ID), 10 (CLUSTER_LIS"+
                             "T), 14 (MP_REACH_NLRI), 15 (MP_UNREACH_NLRI), 17 "+
                             "(AS4PATH), 18 (AS4AGGREGATOR).";
                         }
                       }
                     }
                   }
                   container ipv4-vpn {
                     when "../type = 'ipv4vpn' and ../../../../../../../../ni:na"+
                          "me='_public_'";
                     description
                       "Configure IPv4 VPNv4 options.";
                     leaf group-name {
                       type "leafref" {
                         path "../../../../../../peer-groups/peer-group/name";
                       }
                       must "../../../../../../peer-groups/peer-group[name = "+
                            "current()]/afs/af[type = 'ipv4vpn']";
                       description
                         "Configure a name for a peer group. After a peer is "+
                         "deleted from the peer group, the peer is disabled from"+
                         " the address family. The object cannot be modified.";
                       ext:operation-exclude "update" {
                         description
                           "The node cannot be modified, when the peer already "+
                           "belongs to a peer-group.";
                       }
                     }
                     leaf advertise-community {
                       type "boolean";
                       default "false";
                       description
                         "Enable/disable advertise the community attribute to a "+
                         "peer or a peer group.";
                     }
                     leaf reflect-client {
                       type "boolean";
                       default "false";
                       description
                         "Enable/disable the local device as a route reflector "+
                         "(RR) and a peer or peer group as its client. This "+
                         "configuration is applicable between IBGP peers only. "+
                         "The configurations of RRs and its clients in an "+
                         "address family are valid only in this address family. "+
                         "Therefore, it is recommended to configure RRs and its "+
                         "clients in the specified address family that is "+
                         "required.";
                     }
                     leaf nexthop-configure {
                       type "nexthop-configuration-type";
                       description
                         "Both the next-hop-local mode and next-hop-invariable "+
                         "mode are available when the peer address family is the"+
                         " VPNv4/VPNV6/L2VPN AD address family. Only the "+
                         "next-hop-local mode is available when the peer address"+
                         " family is not VPNv4/VPNV6/L2VPN AD address family. In"+
                         " next-hop-local mode, you can configure a BGP speaker "+
                         "to set its IP address of as the next hop of the routes"+
                         " to be advertised to IBGP peers or IBGP peer groups. "+
                         "In next-hop-invariable mode, you can configure PEs in "+
                         "different ASs not to change the next hop of routes "+
                         "when the PEs advertise the routes to their EBGP peers "+
                         "and use the next hop addresses of IGP routes to "+
                         "advertise imported IGP routes to IBGP peers. By "+
                         "default, when a BGP speaker advertises routes to EBGP "+
                         "peers and imported IGP routes to IBGP peers, the BGP "+
                         "speaker changes the next hop to its interface "+
                         "address.";
                     }
                     choice import-policy-type {
                       description
                         "Set route policy or filter.";
                       case rtp-ref {
                         description
                           "Route policy.";
                         leaf import-policy {
                           type "leafref" {
                             path "/rtp:routing-policy/rtp:policy-definitions/rt"+
                                  "p:policy-definition/rtp:name";
                           }
                           description
                             "Specify the filtering policy applied to the routes"+
                             " learned from a peer. By default, no such policy "+
                             "is specified.";
                         }
                       }
                       case xpl-ref {
                         description
                           "Route filter.";
                         container import-filter {
                           description
                             "Configure an import route-filter to filter the "+
                             "routes received from a peer group. By default, no "+
                             "route-filter is specified to filter the routes "+
                             "imported from a peer group.";
                           leaf name {
                             type "leafref" {
                               path "/xpl:xpl/xpl:route-filters/xpl:route-filter"+
                                    "/xpl:name";
                             }
                             description
                               "Specify an import route-filter name.";
                           }
                           leaf parameter {
                             when "../name";
                             type "xpl:filter-parameter-type";
                             description
                               "Specify an import route-filter parameter.";
                           }
                         }
                       }
                     }
                     choice export-policy-type {
                       description
                         "Set route policy or filter.";
                       case rtp-ref {
                         description
                           "Route policy.";
                         leaf export-policy {
                           type "leafref" {
                             path "/rtp:routing-policy/rtp:policy-definitions/rt"+
                                  "p:policy-definition/rtp:name";
                           }
                           description
                             "Specify the filtering policy applied to the routes"+
                             " to be advertised to a peer. By default, no such "+
                             "policy is specified.";
                         }
                       }
                       case xpl-ref {
                         description
                           "Route filter.";
                         container export-filter {
                           description
                             "Configure an export route-filter to filter the "+
                             "routes to be advertised to a peer group. By "+
                             "default, no route-filter is specified to filter "+
                             "the routes to be advertised to a peer group.";
                           leaf name {
                             type "leafref" {
                               path "/xpl:xpl/xpl:route-filters/xpl:route-filter"+
                                    "/xpl:name";
                             }
                             description
                               "Specify an export route-filter name.";
                           }
                           leaf parameter {
                             when "../name";
                             type "xpl:filter-parameter-type";
                             description
                               "Specify an export route-filter parameter.";
                           }
                         }
                       }
                     }
                     leaf allow-as-loop {
                       type "uint32" {
                         range "1..10";
                       }
                       description
                         "Allow repetitive local AS numbers. By default, "+
                         "repetitive local AS numbers are not allowed.";
                     }
                     leaf aigp {
                       type "boolean";
                       default "false";
                       description
                         "Enable/disable route with AIGP attribute advertisement"+
                         " to or from a peer.";
                     }
                     leaf add-path-mode {
                       type "add-path-cap-type";
                       default "null";
                       description
                         "Enable Add-Path route advertisement to a peer.";
                     }
                     leaf add-path-number {
                       type "uint8" {
                         range "2..64";
                       }
                       description
                         "Number of Add-Path routes that can be advertised to a "+
                         "peer.";
                     }
                     leaf import-ip-prefix {
                       type "leafref" {
                         path "/rtp:routing-policy/rtp:ipv4-prefix-filters/rtp:i"+
                              "pv4-prefix-filter/rtp:name";
                       }
                       description
                         "Specify the IPv4 filtering policy applied to the "+
                         "routes received from a specified peer. By default, no "+
                         "such policy is specified.";
                     }
                     leaf export-ip-prefix {
                       type "leafref" {
                         path "/rtp:routing-policy/rtp:ipv4-prefix-filters/rtp:i"+
                              "pv4-prefix-filter/rtp:name";
                       }
                       description
                         "Specify the IPv4 filtering policy applied to the "+
                         "routes to be advertised to a specified peer. By "+
                         "default, no such policy is specified.";
                     }
                     leaf import-as-path-filter {
                       type "leafref" {
                         path "/rtp:routing-policy/rtp:as-path-filters/rtp:as-pa"+
                              "th-filter/rtp:name";
                       }
                       description
                         "Apply an AS_Path-based filtering policy to the routes "+
                         "received from a specified peer. The policy can be "+
                         "identified with a name or number, and the number "+
                         "ranges from 1 to 256. By default, no such policy is "+
                         "specified. Therefore, all BGP routes can be accepted.";
                     }
                     leaf export-as-path-filter {
                       type "leafref" {
                         path "/rtp:routing-policy/rtp:as-path-filters/rtp:as-pa"+
                              "th-filter/rtp:name";
                       }
                       description
                         "Apply an AS_Path-based filtering policy to the routes "+
                         "to be advertised to a specified peer. The policy can "+
                         "be identified with a name or number, and the number "+
                         "ranges from 1 to 256. By default, no such policy is "+
                         "specified. Therefore, all BGP routes can be advertised"+
                         ".";
                     }
                     leaf import-acl-name-or-num {
                       type "leafref" {
                         path "/acl:acl/acl:groups/acl:group/acl:identity";
                       }
                       description
                         "Specifies the name of the import ACL policy.";
                     }
                     leaf export-acl-name-or-num {
                       type "leafref" {
                         path "/acl:acl/acl:groups/acl:group/acl:identity";
                       }
                       description
                         "Specifies the name of the export ACL policy.";
                     }
                     leaf route-update-interval {
                       type "uint16" {
                         range "0..600";
                       }
                       units "s";
                       description
                         "Specify the minimum interval at which Update packets "+
                         "are sent. By default, the interval at which Update "+
                         "packets are sent to IBGP peers is 15s, \nand the "+
                         "interval at which Update packets are sent to EBGP "+
                         "peers is 30s. When routes change, a router will send "+
                         "Update packets to notify its peers. \nIf a route "+
                         "changes frequently, you can set an interval at which "+
                         "Update packets are sent to prevent the router from "+
                         "sending Update packets each time the route changes. "+
                         "\nThis configuration is valid only to the routes "+
                         "learned from peers.";
                       ext:dynamic-default;
                     }
                     leaf preferred-value {
                       type "uint32" {
                         range "0..65535";
                       }
                       default "0";
                       description
                         "Assign a preferred value for the routes learned from a"+
                         " specified peer. After a preferred value is configured"+
                         " for the routes learned from a specified peer,\nall "+
                         "the routes that learnt from this peer will use this "+
                         "preferred value. When multiple routes reach the same "+
                         "address prefix, the route with the largest preferred "+
                         "value will be selected.";
                     }
                     leaf upe {
                       type "boolean";
                       default "false";
                       description
                         "Enable/disable the peer as an underlayer PE (UPE).";
                     }
                     leaf advertise-best-external {
                       type "boolean";
                       must "../reflect-client='false' or ../advertise-best-exte"+
                            "rnal='false'";
                       must "../add-path-mode='null' or not(../add-path-mode) or"+
                            " ../advertise-best-external='false'";
                       must "not(../add-path-number and ../advertise-best-extern"+
                            "al='true')";
                       default "false";
                       description
                         "Enable/disable the device to advertise Best External "+
                         "routes to peers.";
                     }
                     leaf keep-all-routes {
                       type "boolean";
                       default "false";
                       description
                         "Enable/disable saving all the updated information "+
                         "about BGP routes from a specified peer or peer group "+
                         "after a BGP connection is established, even though "+
                         "these BGP routes fail to match the routing policy on "+
                         "the ingress. By default, the updated information about"+
                         " BGP routes from a specified peer is saved only when "+
                         "the routes match the routing policy on the ingress. If"+
                         " a router supports route refreshing, this option is "+
                         "not required.";
                     }
                     leaf update-group-independent {
                       type "bgp:peer-comm-config-type";
                       default "default";
                       description
                         "Enable/disable the peer which can reside in an "+
                         "independent peer group.";
                     }
                     leaf update-group-independent-state {
                       type "boolean";
                       config "false";
                       description
                         "Whether the peer can reside in an independent peer "+
                         "group.";
                     }
                     leaf origin-as-validation {
                       type "boolean";
                       default "false";
                       description
                         "Enable/disable the BGP peer origin validation.";
                     }
                     container default-route-originates {
                       description
                         "Configure advertised default VPNv4 routes.";
                       list default-route-originate {
                         key "vpn-name";
                         description
                           "Configure advertised default VPNv4 route.";
                         leaf vpn-name {
                           type "leafref" {
                             path "/ni:network-instance/ni:instances/ni:instance"+
                                  "/ni:name";
                           }
                           must "../vpn-name!='_public_'";
                           description
                             "VPN instance name. It uniquely identifies a VPN "+
                             "instance. The name is a string of case-sensitive "+
                             "characters.";
                         }
                       }
                     }
                     container route-limit {
                       description
                         "Configure parameters of routes limited from this "+
                         "peer.";
                       leaf number {
                         type "uint32" {
                           range "1..4294967295";
                         }
                         description
                           "Configure the maximum number of routes that can be "+
                           "accepted from a peer.";
                       }
                       leaf percent {
                         when "../number";
                         type "uint8" {
                           range "1..100";
                         }
                         default "75";
                         description
                           "Specify the percentage of routes when a router "+
                           "starts to generate an alarm.";
                       }
                       leaf type {
                         when "../number";
                         type "bgp:route-limit-type";
                         must "(../type='idle-timeout' and ../idle-timeout) or "+
                              "(../type!='idle-timeout')";
                         default "noparameter";
                         description
                           "Set the processing method as alert-only, idle-foreve"+
                           "r, or idle-timeout when the number of routes exceeds"+
                           " the set threshold. When alert-only is used, only an"+
                           " alarm is generated when the number of routes "+
                           "exceeds the threshold. In this case, new routes are "+
                           "no longer accepted. When idle-forever is used, "+
                           "connections are not automatically reestablished "+
                           "after being cut off until BGP connections are reset "+
                           "if the number of routes exceeds the set threshold. "+
                           "When idle-timeout is used and the idle-timeout timer"+
                           " is specified, the connections are automatically "+
                           "reestablished after being cut off if the number of "+
                           "routes exceeds the set threshold. You can reset BGP "+
                           "connections to reestablish the connections before "+
                           "the idle-timeout times expires.";
                       }
                       leaf idle-timeout {
                         when "../type='idle-timeout'";
                         type "uint16" {
                           range "1..1200";
                         }
                         units "min";
                         description
                           "Specify the value of the idle-timeout timer to "+
                           "automatically reestablish the connections after they"+
                           " are cut off when the number of routes exceeds the "+
                           "set threshold.";
                       }
                     }
                     container public-as-only {
                       description
                         "Configure BGP Remove private AS number from outbound "+
                         "updates parameters.";
                       leaf enable {
                         type "boolean";
                         default "false";
                         description
                           "Enable/disable BGP to send Update packets carrying "+
                           "only public AS numbers.";
                       }
                       choice remove-private-as {
                         description
                           "Remove AS numbers except peer AS number from "+
                           "outbound updates.";
                         case all {
                           description
                             "Remove all private AS numbers.";
                           leaf force {
                             when "../enable='true'";
                             type "empty";
                             description
                               "Configures BGP to carry only the public AS "+
                               "number instead of the private AS number when BGP"+
                               " sends Update packets. By default, BGP can carry"+
                               " the private AS number when BGP sends Update "+
                               "packets.";
                           }
                         }
                         case left-most {
                           description
                             "Remove the left-most private AS numbers.";
                           leaf limited {
                             when "../enable='true'";
                             type "empty";
                             description
                               "When the BGP sends update packets, the left ends"+
                               " of both the local AS and public AS do not carry"+
                               " the private AS. By default, BGP can carry the "+
                               "private AS number when BGP sends Update "+
                               "packets.";
                           }
                         }
                       }
                       leaf replace {
                         when "../force or ../limited";
                         type "boolean";
                         default "false";
                         description
                           "Enable/disable the function to the private AS is "+
                           "replaced by the local AS when the BGP sends update "+
                           "packets.";
                       }
                       leaf no-skip-as {
                         when "../force or ../limited";
                         type "boolean";
                         default "false";
                         description
                           "Enable/disable the function to the neighbour AS is "+
                           "not processed when the BGP sends update packets.";
                       }
                     }
                     container public-as-only-import {
                       description
                         "Configure BGP remove private AS number in received BGP"+
                         " update messages parameters.";
                       leaf enable {
                         type "bgp:peer-comm-config-type";
                         default "default";
                         description
                           "Enable/disable BGP to receive update packets "+
                           "carrying only public AS numbers.";
                       }
                       choice remove-private-as {
                         description
                           "Remove private AS numbers in received BGP update "+
                           "messages.";
                         case all {
                           description
                             "Forcibly delete all the private AS numbers in the "+
                             "AS_Path list.";
                           leaf force {
                             when "../enable = 'enable'";
                             type "empty";
                             description
                               "Enable a device to forcibly remove all the "+
                               "private AS numbers in received BGP update "+
                               "messages in which the AS_Path list contains "+
                               "private AS numbers. By default, a device does "+
                               "not remove private AS numbers from the AS_Path "+
                               "list when receiving BGP update messages.";
                           }
                         }
                       }
                       leaf effect-enable {
                         type "boolean";
                         config "false";
                         description
                           "Flag indicating that the device is enabled to remove"+
                           " private AS numbers from the AS_Path list in "+
                           "received BGP update messages.";
                       }
                       leaf effect-force {
                         type "boolean";
                         config "false";
                         description
                           "Flag indicating that the device is enabled to "+
                           "forcibly remove all the private AS numbers from the "+
                           "AS_Path list in received BGP update messages.";
                       }
                     }
                     container path-attribute-treats {
                       description
                         "List of modes in which specified path attributes are "+
                         "processed.";
                       list path-attribute-treat {
                         must "discard-id-map or withdraw-id-map or unknown-id-m"+
                              "ap";
                         key "treat-type";
                         description
                           "Configure mode in which specified path attributes "+
                           "are processed.";
                         leaf treat-type {
                           type "bgp:path-attr-treat-type";
                           description
                             "Mode in which specified path attributes are "+
                             "processed.";
                         }
                         leaf discard-id-map {
                           type "pub-type:id-range" {
                             pattern "((25[0-5]|2[0-4][0-9]|1[0-9][0-9]|[1-9][0-"+
                                     "9]|[0-9])?(-(25[0-5]|2[0-4][0-9]|1[0-9][0-"+
                                     "9]|[1-9][0-9]|[0-9]))?(,((25[0-5]|2[0-4][0"+
                                     "-9]|1[0-9][0-9]|[1-9][0-9]|[0-9])(-(25[0-5"+
                                     "]|2[0-4][0-9]|1[0-9][0-9]|[1-9][0-9]|[0-9]"+
                                     "))?))*)|((([\\+|\\-](25[0-5]|2[0-4][0-"+
                                     "9]|1[0-9][0-9]|[1-9][0-9]|[0-9]))|([\\+|"+
                                     "\\-]\\((25[0-5]|2[0-4][0-9]|1[0-9][0-9"+
                                     "]|[1-9][0-9]|[0-9])-(25[0-5]|2[0-4][0-9]|1"+
                                     "[0-9][0-9]|[1-9][0-9]|[0-9])\\)))?(,((["+
                                     "\\+|\\-](25[0-5]|2[0-4][0-9]|1[0-9][0-"+
                                     "9]|[1-9][0-9]|[0-9]))|([\\+|\\-]\\(("+
                                     "25[0-5]|2[0-4][0-9]|1[0-9][0-9]|[1-9][0-9]"+
                                     "|[0-9])-(25[0-5]|2[0-4][0-9]|1[0-9][0-9]|["+
                                     "1-9][0-9]|[0-9])\\))))*)";
                             ext:value-range "0..255";
                           }
                           description
                             "Specify a discard attribute ID list. The attribute"+
                             " IDs which are not supported as follows: 1 "+
                             "(ORIGIN), 2 (AS_PATH), 3 (NEXT_HOP), 4 (MED), 5 "+
                             "(LOCAL_PREF), 6 (ATOMICAGGREGATE), 7 (AGGREGATOR),"+
                             " 8 (COMMUNITY), 9 (ORIGINATOR_ID), 10 (CLUSTER_LIS"+
                             "T), 14 (MP_REACH_NLRI), 15 (MP_UNREACH_NLRI), 17 "+
                             "(AS4PATH), 18 (AS4AGGREGATOR).";
                         }
                         leaf withdraw-id-map {
                           type "pub-type:id-range" {
                             pattern "((25[0-5]|2[0-4][0-9]|1[0-9][0-9]|[1-9][0-"+
                                     "9]|[0-9])?(-(25[0-5]|2[0-4][0-9]|1[0-9][0-"+
                                     "9]|[1-9][0-9]|[0-9]))?(,((25[0-5]|2[0-4][0"+
                                     "-9]|1[0-9][0-9]|[1-9][0-9]|[0-9])(-(25[0-5"+
                                     "]|2[0-4][0-9]|1[0-9][0-9]|[1-9][0-9]|[0-9]"+
                                     "))?))*)|((([\\+|\\-](25[0-5]|2[0-4][0-"+
                                     "9]|1[0-9][0-9]|[1-9][0-9]|[0-9]))|([\\+|"+
                                     "\\-]\\((25[0-5]|2[0-4][0-9]|1[0-9][0-9"+
                                     "]|[1-9][0-9]|[0-9])-(25[0-5]|2[0-4][0-9]|1"+
                                     "[0-9][0-9]|[1-9][0-9]|[0-9])\\)))?(,((["+
                                     "\\+|\\-](25[0-5]|2[0-4][0-9]|1[0-9][0-"+
                                     "9]|[1-9][0-9]|[0-9]))|([\\+|\\-]\\(("+
                                     "25[0-5]|2[0-4][0-9]|1[0-9][0-9]|[1-9][0-9]"+
                                     "|[0-9])-(25[0-5]|2[0-4][0-9]|1[0-9][0-9]|["+
                                     "1-9][0-9]|[0-9])\\))))*)";
                             ext:value-range "0..255";
                           }
                           description
                             "Specify a withdraw attribute ID list. The "+
                             "attribute IDs which are not supported as follows: "+
                             "1 (ORIGIN), 2 (AS_PATH), 3 (NEXT_HOP), 4 (MED), 5 "+
                             "(LOCAL_PREF), 6 (ATOMICAGGREGATE), 7 (AGGREGATOR),"+
                             " 8 (COMMUNITY), 9 (ORIGINATOR_ID), 10 (CLUSTER_LIS"+
                             "T), 14 (MP_REACH_NLRI), 15 (MP_UNREACH_NLRI), 17 "+
                             "(AS4PATH), 18 (AS4AGGREGATOR).";
                         }
                         leaf unknown-id-map {
                           type "pub-type:id-range" {
                             pattern "((25[0-5]|2[0-4][0-9]|1[0-9][0-9]|[1-9][0-"+
                                     "9]|[0-9])?(-(25[0-5]|2[0-4][0-9]|1[0-9][0-"+
                                     "9]|[1-9][0-9]|[0-9]))?(,((25[0-5]|2[0-4][0"+
                                     "-9]|1[0-9][0-9]|[1-9][0-9]|[0-9])(-(25[0-5"+
                                     "]|2[0-4][0-9]|1[0-9][0-9]|[1-9][0-9]|[0-9]"+
                                     "))?))*)|((([\\+|\\-](25[0-5]|2[0-4][0-"+
                                     "9]|1[0-9][0-9]|[1-9][0-9]|[0-9]))|([\\+|"+
                                     "\\-]\\((25[0-5]|2[0-4][0-9]|1[0-9][0-9"+
                                     "]|[1-9][0-9]|[0-9])-(25[0-5]|2[0-4][0-9]|1"+
                                     "[0-9][0-9]|[1-9][0-9]|[0-9])\\)))?(,((["+
                                     "\\+|\\-](25[0-5]|2[0-4][0-9]|1[0-9][0-"+
                                     "9]|[1-9][0-9]|[0-9]))|([\\+|\\-]\\(("+
                                     "25[0-5]|2[0-4][0-9]|1[0-9][0-9]|[1-9][0-9]"+
                                     "|[0-9])-(25[0-5]|2[0-4][0-9]|1[0-9][0-9]|["+
                                     "1-9][0-9]|[0-9])\\))))*)";
                             ext:value-range "0..255";
                           }
                           description
                             "Specify an unknown attribute ID list. The "+
                             "attribute IDs which are not supported as follows: "+
                             "1 (ORIGIN), 2 (AS_PATH), 3 (NEXT_HOP), 4 (MED), 5 "+
                             "(LOCAL_PREF), 6 (ATOMICAGGREGATE), 7 (AGGREGATOR),"+
                             " 8 (COMMUNITY), 9 (ORIGINATOR_ID), 10 (CLUSTER_LIS"+
                             "T), 14 (MP_REACH_NLRI), 15 (MP_UNREACH_NLRI), 17 "+
                             "(AS4PATH), 18 (AS4AGGREGATOR).";
                         }
                       }
                     }
                   }
                 }
               }
             }
           }
         }
       }
     }
   }
 }

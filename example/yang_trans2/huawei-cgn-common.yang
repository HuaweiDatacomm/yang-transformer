/******************************************************
* Copyright (C) 2021 Huawei Technologies Co., Ltd. All rights reserved.
*******************************************************/

 module huawei-cgn-common {
   namespace "urn:huawei:yang:huawei-cgn-common";
   prefix "cgn-common";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module contains a collection of YANG definitions for Configurations "+
     "of cgn commaon element.";
   revision "2021-07-31" {
     description
       "Initial revision.";
     reference
       "Huawei private.";
   }
   typedef alg-protocol-type {
     type "enumeration" {
       enum "ftp" {
         value "1";
         description
           "Indicate file transfer protocol.";
       }
       enum "rtsp" {
         value "2";
         description
           "Indicate real time streaming protocol.";
       }
       enum "pptp" {
         value "4";
         description
           "Indicate point-to-point tunnel protocol.";
       }
       enum "sip" {
         value "8";
         description
           "Indicate session initiation protocol.";
       }
       enum "dns" {
         value "16";
         description
           "Indicate domain name service.";
       }
     }
     description
       "ALG Protocol.";
   }
   ext:task-name "nat";
 }

/*
* Copyright (C) 2019-2021 Huawei Technologies Co., Ltd. All rights reserved.
*/

 module huawei-pub-type {
   namespace "urn:huawei:yang:huawei-pub-type";
   prefix "pub-type";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "This YANG module define public datatypes.";
   revision "2021-08-11" {
     description
       "Modify revision data.";
     reference
       "Huawei private.";
   }
   revision "2020-04-01" {
     description
       "Modify hex-binary type.";
     reference
       "Huawei private.";
   }
   revision "2020-02-05" {
     description
       "Add password type.";
     reference
       "Huawei private.";
   }
   revision "2019-09-26" {
     description
       "Modify description and status.";
     reference
       "Huawei private.";
   }
   revision "2019-07-18" {
     description
       "Modify regular expression to mac-address.";
     reference
       "Huawei private.";
   }
   revision "2019-07-08" {
     description
       "Add a regular expression to mac-address.";
     reference
       "Huawei private.";
   }
   revision "2019-04-27" {
     description
       "Initial revision.";
     reference
       "Huawei private.";
   }
   typedef time-hhmm {
     type "string" {
       length "3..5";
       pattern "(([0-1][0-9])|(2[0-3])|[0-9]):([0-5][0-9]|[0-9])";
     }
     description
       "Time in standard notation, is like string with format 'hh:mm', and hh is"+
       " hour, mm is minute, range is 00:00~23:59.";
   }
   typedef mac-address {
     type "string" {
       length "0..255";
       pattern "[0-9a-f]{4}(-[0-9a-f]{4}){2}";
       ext:case-sensitivity "lower-only";
     }
     description
       "A MAC address in standard notation.";
   }
   typedef if-name {
     type "string" {
       length "1..63";
     }
     description
       "Interface name is like ethernet1/1/1/1.";
   }
   typedef position {
     type "string" {
       length "1..32";
     }
     description
       "Board position in standard notation, serial-port position is like[1/1/1/"+
       "1:2:3].";
   }
   typedef password {
     type "string" {
       length "1..128";
     }
     description
       "The password is a string ranging from 1 to 16 characters for a "+
       "unencrypted password and 20 to 128 characters for a encrypted password.";
   }
   typedef password-extend {
     type "string" {
       length "1..432";
     }
     description
       "The password is a string ranging from 1 to 255 characters for a "+
       "unencrypted password and 20 to 432 characters for a encrypted password.";
   }
   typedef one-input-password-extend {
     type "string" {
       length "1..432";
     }
     description
       "The password is a string ranging from 1 to 255 characters for a plain "+
       "text password and 20 to 432 characters for a cipher text password.";
   }
   typedef vrf-name {
     type "string" {
       length "1..31";
     }
     description
       "VRF name in standard notation.";
   }
   typedef time-tick {
     type "uint32";
     description
       "Time tick in standard notation, represents the time in SECOND between "+
       "two epochs.";
   }
   typedef description-string {
     type "string" {
       pattern "([^?]*)";
     }
     description
       "Description string is used for description with little limitation.";
   }
   typedef row-status {
     type "enumeration" {
       enum "active" {
         value "0";
         description
           "Rule status is active at the current time.";
       }
       enum "not-in-service" {
         value "1";
         description
           "Rule status is not active at the current time.";
       }
       enum "not-ready" {
         value "2";
         description
           "The system is unavailable at the moment.";
       }
     }
     description
       "Row-status indicates current status.";
   }
   typedef percent {
     type "uint8" {
       range "0..100";
     }
     units "%";
     description
       "Percent is like uint8.";
   }
   typedef band-width {
     type "uint64";
     units "bit/s";
     description
       "The speed of interfaces.";
   }
   typedef host-name {
     type "string" {
       length "1..255";
     }
     description
       "Host-name is like string.";
   }
   typedef hex-binary {
     type "string" {
       length "1..10";
       pattern "0[xX](0|([1-9a-fA-F][0-9a-fA-F]*))";
     }
     ext:case-sensitivity "upper2lower";
     description
       "This is a hexadecimal variable.";
   }
   typedef date {
     type "string" {
       pattern "\\d{4}-\\d{2}-\\d{2}";
     }
     description
       "XSD date string type, such as '2010-10-08'.";
     reference
       "http://www.w3.org/TR/2004/REC-xmlschema-2-20041028/datatypes.html#date";
   }
   typedef time {
     type "string" {
       pattern "\\d{1,2}:\\d{1,2}:\\d{1,2}";
       pattern "(([0-1][0-9])|(2[0-3])|[0-9]):([0-5][0-9]|[0-9]):([0-5][0-9]|[0-"+
               "9])";
     }
     description
       "XSD time string type such as '20:15:30'. Range is 00:00:00~23:59:59.";
     reference
       "http://www.w3.org/TR/2004/REC-xmlschema-2-20041028/datatypes.html#date";
   }
   typedef id-range {
     type "string" {
       pattern "([0-9]|,|\\+|\\-|\\(|\\))+";
     }
     description
       "ID list, such as '1,3,5-7',or '+1,-3,+(20-30)'.";
   }
   typedef vlan-range {
     type "id-range" {
       pattern "((409[0-4]|40[0-8][0-9]|[1-3][0-9]{3}|[1-9][0-9]{1,2}|[1-9])?(-("+
               "409[0-4]|40[0-8][0-9]|[1-3][0-9]{3}|[1-9][0-9]{1,2}|[1-9]))?(,(("+
               "409[0-4]|40[0-8][0-9]|[1-3][0-9]{3}|[1-9][0-9]{1,2}|[1-9])(-(409"+
               "[0-4]|40[0-8][0-9]|[1-3][0-9]{3}|[1-9][0-9]{1,2}|[1-9]))?))*)|(("+
               "([\\+\\-](409[0-4]|40[0-8][0-9]|[1-3][0-9]{3}|[1-9][0-9]{1,2"+
               "}|[1-9]))|([\\+\\-]\\((409[0-4]|40[0-8][0-9]|[1-3][0-9]{3}"+
               "|[1-9][0-9]{1,2}|[1-9])-(409[0-4]|40[0-8][0-9]|[1-3][0-9]{3}|[1-"+
               "9][0-9]{1,2}|[1-9])\\)))?(,(([\\+\\-](409[0-4]|40[0-8][0-9"+
               "]|[1-3][0-9]{3}|[1-9][0-9]{1,2}|[1-9]))|([\\+\\-]\\((409[0"+
               "-4]|40[0-8][0-9]|[1-3][0-9]{3}|[1-9][0-9]{1,2}|[1-9])-(409[0-4]|"+
               "40[0-8][0-9]|[1-3][0-9]{3}|[1-9][0-9]{1,2}|[1-9])\\))))*)";
       ext:value-range "1..4094";
     }
     description
       "VLAN ID list.";
   }
 }

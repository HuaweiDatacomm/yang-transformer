/*
Copyright (C) 2020 Huawei Technologies Co., Ltd. All rights reserved.
*/

 submodule huawei-dhcp-server {
   yang-version "1";
   belongs-to huawei-dhcp {
     prefix "dhcp";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module contains a collection of YANG definitions for managing DHCP "+
     "server.";
   revision "2020-03-13" {
     description
       "Modify description.";
     reference
       "Huawei private.";
   }
   revision "2020-03-03" {
     description
       "Initial revision.";
     reference
       "Huawei private.";
   }
   typedef network-bios-type {
     type "enumeration" {
       enum "b-node" {
         value "1";
         description
           "B-node.";
       }
       enum "h-node" {
         value "2";
         description
           "H-node.";
       }
       enum "m-node" {
         value "3";
         description
           "M-node.";
       }
       enum "p-node" {
         value "4";
         description
           "P-node.";
       }
     }
     description
       "The type of network BIOS.";
   }
   typedef reply-type {
     type "enumeration" {
       enum "broadcast-always" {
         value "1";
         description
           "Always broadcast the reply.";
       }
       enum "unicast-always" {
         value "2";
         description
           "Always unicast the reply.";
       }
     }
     description
       "DHCP reply type.";
   }
   typedef sip-mode {
     type "enumeration" {
       enum "ip-mode" {
         value "1";
         description
           "SIP server IP mode.";
       }
       enum "list-mode" {
         value "2";
         description
           "SIP server string mode.";
       }
     }
     description
       "The type of SIP mode.";
   }
   typedef server-file-authentication-mode {
     type "enumeration" {
       enum "check" {
         value "0";
         description
           "Check.";
       }
       enum "no-check" {
         value "1";
         description
           "No-check.";
       }
       enum "force-check" {
         value "2";
         description
           "Force-check.";
       }
     }
     description
       "The type of file authentication mode.";
   }
 }

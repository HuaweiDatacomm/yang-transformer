/******************************************************
 * Copyright (C) 2019 Huawei Technologies Co., Ltd. All rights reserved.
 * Module description & tree structure:
 module: huawei-netconf-proxy
   +--ro proxy
      +--ro target-list* [target]
      |  +--ro target                  string
      |  +--ro target-id               string
      |  +--ro target-type             string
***************************************************/

 module huawei-netconf-proxy {
   namespace "urn:huawei:yang:huawei-netconf-proxy";
   prefix "ncp";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "NETCONF Proxy Protocol Data Types and Protocol Operations.\nThis YANG "+
     "module describe how to define a netconf proxy.";
   revision "2019-09-15" {
     description
       "Initial revision.";
     reference
       "Huawei private.";
   }
   container proxy {
     config "false";
     description
       "Container for NETCONF Proxy.";
     list target-list {
       key "target";
       description
         "Statistics of target list information.";
       leaf target {
         type "string" {
           length "1..127";
         }
         description
           "Target name.";
       }
       leaf target-id {
         ext:support-filter "true";
         type "string" {
           length "1..127";
         }
         description
           "Target Identifier.";
       }
       leaf target-type {
         ext:support-filter "true";
         type "string" {
           length "1..127";
         }
         description
           "The type of the target.";
       }
     }
   }
   ext:task-name "netconf";
 }

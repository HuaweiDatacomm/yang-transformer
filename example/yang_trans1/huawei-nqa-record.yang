/*
Copyright (C) 2019-2021 Huawei Technologies Co., Ltd. All rights reserved.
*/

 submodule huawei-nqa-record {
   yang-version "1";
   belongs-to huawei-nqa {
     prefix "nqa";
   }
   organization
     "Huawei Technologies Co., Ltd.";
   contact
     "Huawei Industrial Base\nBantian, Longgang\nShenzhen 518129\nPeople's "+
     "Republic of China\nWebsite: http://www.huawei.com\nEmail: support@huawei.c"+
     "om";
   description
     "Description of submodule nqa-record.";
   revision "2021-04-29" {
     description
       "Add ethernet-service-results.";
     reference
       "Huawei private.";
   }
   revision "2020-09-24" {
     description
       "Modify jitter-results.";
     reference
       "Huawei private.";
   }
   revision "2019-10-30" {
     description
       "Initial revision.";
     reference
       "Huawei private.";
   }
   typedef test-finsh-status-type {
     type "enumeration" {
       enum "finished" {
         value "1";
         description
           "Finished.";
       }
       enum "running" {
         value "0";
         description
           "Running.";
       }
     }
     description
       "Description of test-finsh-status-type.";
   }
   typedef test-step-type {
     type "enumeration" {
       enum "simple-cir" {
         value "0";
         description
           "Simple CIR.";
       }
       enum "percent-25-cir" {
         value "1";
         description
           "Step 25% CIR.";
       }
       enum "percent-50-cir" {
         value "2";
         description
           "Step 50% CIR.";
       }
       enum "percent-75-cir" {
         value "3";
         description
           "Step 75% CIR.";
       }
       enum "percent-100-cir" {
         value "4";
         description
           "Step 100% CIR.";
       }
       enum "eir" {
         value "5";
         description
           "EIR.";
       }
       enum "color-aware-eir" {
         value "6";
         description
           "Color-aware EIR.";
       }
       enum "traffic-policing" {
         value "7";
         description
           "Traffic policing.";
       }
       enum "color-aware-traffic-policing" {
         value "8";
         description
           "Color-aware traffic policing.";
       }
       enum "performance" {
         value "9";
         description
           "Performance.";
       }
       enum "green-eir" {
         value "10";
         description
           "EIR green packet test.";
       }
       enum "yellow-eir" {
         value "11";
         description
           "EIR yellow packet test.";
       }
       enum "total-eir" {
         value "12";
         description
           "Total EIR test.";
       }
       enum "green-traffic-policing" {
         value "13";
         description
           "Traffic policing green packet test.";
       }
       enum "yellow-traffic-policing" {
         value "14";
         description
           "Traffic policing yellow packet test.";
       }
       enum "total-traffic-policing" {
         value "15";
         description
           "Total traffic policing test.";
       }
       enum "init" {
         value "16";
         description
           "Init status.";
       }
     }
     description
       "Description of test-step-type.";
   }
   typedef result-status-type {
     type "enumeration" {
       enum "success" {
         value "0";
         description
           "Success.";
       }
       enum "failed" {
         value "1";
         description
           "Failed.";
       }
       enum "no-result" {
         value "2";
         description
           "Init status.";
       }
       enum "negotiate-failed" {
         value "3";
         description
           "Negotiate failed.";
       }
     }
     description
       "Description of result-status-type.";
   }
   typedef result-status-all-type {
     type "enumeration" {
       enum "no-result" {
         value "0";
         description
           "Init status.";
       }
       enum "success" {
         value "1";
         description
           "Success.";
       }
       enum "failed" {
         value "2";
         description
           "Failed.";
       }
       enum "negotiate-failed" {
         value "3";
         description
           "Negotiate failed.";
       }
     }
     description
       "Description of result-status-all-type.";
   }
   typedef test-result-type {
     type "enumeration" {
       enum "pass" {
         value "0";
         description
           "Pass.";
       }
       enum "failed" {
         value "1";
         description
           "Failed.";
       }
       enum "abort" {
         value "2";
         description
           "Abort.";
       }
       enum "abnormal" {
         value "3";
         description
           "Abnormal.";
       }
       enum "nil" {
         value "4";
         description
           "--";
       }
     }
     description
       "Description of test-result-type.";
   }
   typedef test-mode-type {
     type "enumeration" {
       enum "round-trip" {
         value "0";
         description
           "Round-trip.";
       }
     }
     description
       "Description of test-mode-type.";
   }
   typedef test-last-step-type {
     type "enumeration" {
       enum "simple-cir" {
         value "0";
         description
           "Simple CIR.";
       }
       enum "percent-25-cir" {
         value "1";
         description
           "Step 25% CIR.";
       }
       enum "percent-50-cir" {
         value "2";
         description
           "Step 50% CIR.";
       }
       enum "percent-75-cir" {
         value "3";
         description
           "Step 75% CIR.";
       }
       enum "percent-100-cir" {
         value "4";
         description
           "Step 100% CIR.";
       }
       enum "color-blind-eir" {
         value "5";
         description
           "Color-blind EIR.";
       }
       enum "color-aware-eir" {
         value "6";
         description
           "Color-aware EIR.";
       }
       enum "color-blind-traffic-policing" {
         value "7";
         description
           "Color-blind traffic policing.";
       }
       enum "color-aware-traffic-policing" {
         value "8";
         description
           "Color-aware traffic policing.";
       }
       enum "performance" {
         value "9";
         description
           "Performance.";
       }
       enum "green-eir" {
         value "10";
         description
           "CIR/EIR Test.";
       }
       enum "yellow-eir" {
         value "11";
         description
           "CIR/EIR Test.";
       }
       enum "total-eir" {
         value "12";
         description
           "CIR/EIR Test.";
       }
       enum "green-traffic-policing" {
         value "13";
         description
           "Traffic Policing Test.";
       }
       enum "yellow-traffic-policing" {
         value "14";
         description
           "Traffic Policing Test.";
       }
       enum "total-traffic-policing" {
         value "15";
         description
           "Traffic Policing Test.";
       }
       enum "init" {
         value "16";
         description
           "Init status.";
       }
     }
     description
       "Description of test-last-step-type.";
   }
   typedef test-stage-type {
     type "enumeration" {
       enum "configuration-test" {
         value "0";
         description
           "Configuration test.";
       }
       enum "performance-test" {
         value "1";
         description
           "Performance test.";
       }
     }
     description
       "Description of test-stage-type.";
   }
   typedef result-path-jitter-status-type {
     type "enumeration" {
       enum "initial" {
         value "0";
         description
           "PatchJitter test status initial.";
       }
       enum "trace-start" {
         value "1";
         description
           "PatchJitter test status trace start.";
       }
       enum "trace-end" {
         value "2";
         description
           "PatchJitter test status trace end.";
       }
       enum "jitter-start" {
         value "3";
         description
           "PatchJitter test status jitter start.";
       }
       enum "jitter-end" {
         value "4";
         description
           "PatchJitter test status jitter end.";
       }
       enum "close" {
         value "5";
         description
           "PatchJitter test status close.";
       }
     }
     description
       "Description of result-path-jitter-status-type.";
   }
   typedef lsp-sr-policy-path {
     type "enumeration" {
       enum "unknown" {
         value "0";
         description
           "UNKNOWN.";
       }
       enum "main-path" {
         value "1";
         description
           "MAIN-PATH.";
       }
       enum "backup-path" {
         value "2";
         description
           "BACK-PATH.";
       }
     }
     description
       "Description of lsp-sr-policy-path.";
   }
   typedef lsp-protocol-origin {
     type "enumeration" {
       enum "pecp" {
         value "10";
         description
           "PECP.";
       }
       enum "bgp" {
         value "20";
         description
           "BGP.";
       }
       enum "local" {
         value "30";
         description
           "LOCAL.";
       }
       enum "unknown" {
         value "255";
         description
           "UNKNOWN.";
       }
     }
     description
       "Description of lsp-protocol-origin.";
   }
   typedef timestamp-unit-type {
     type "enumeration" {
       enum "ms" {
         value "0";
         description
           "Millisecond.";
       }
       enum "us" {
         value "1";
         description
           "Microsecond.";
       }
     }
     description
       "Description of timestamp-unit-type.";
   }
 }

/*
Copyright (C) 2019-2020 Huawei Technologies Co., Ltd. All rights reserved.
*/

 module huawei-nd-notification {
   yang-version "1";
   namespace "urn:huawei:yang:huawei-nd-notification";
   prefix "nd-notification";
   import huawei-pub-type {
     prefix "pub-type";
   }
   import ietf-inet-types {
     prefix "inet";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of IPv6-nd-notification.";
   revision "2020-05-28" {
     description
       "The description of the source-ip leaf is modified.";
     reference
       "Huawei private.";
   }
   revision "2020-04-17" {
     description
       "Notification of anti-attack-rate-limit is added.";
     reference
       "Huawei private.";
   }
   revision "2019-12-01" {
     description
       "Initial revision.";
     reference
       "Huawei private.";
   }
   ext:task-name "nd";
   typedef nd-pkt-evt-disp-type {
     type "enumeration" {
       enum "RS" {
         value "1";
         description
           "Router solicitation packet.";
       }
       enum "RA" {
         value "2";
         description
           "Router advertisement packet.";
       }
       enum "NS" {
         value "3";
         description
           "Neighbor solicitation packet.";
       }
       enum "NA" {
         value "4";
         description
           "Neighbor advertisement packet.";
       }
       enum "NDMISS" {
         value "5";
         description
           "ND miss.";
       }
     }
     description
       "ND packet type or event value.";
   }
   typedef nd-suppress-type {
     type "enumeration" {
       enum "SRCIP" {
         value "1";
         description
           "Source IP address.";
       }
       enum "SRCMAC" {
         value "2";
         description
           "Source MAC address.";
       }
       enum "INTERFACE" {
         value "3";
         description
           "Interface.";
       }
       enum "INTERFACESRCIP" {
         value "4";
         description
           "Interface source IP address.";
       }
       enum "VSGLOBAL" {
         value "5";
         description
           "Virtual system.";
       }
       enum "LSGLOBAL" {
         value "6";
         description
           "Logic system.";
       }
       enum "DSTIP" {
         value "7";
         description
           "Destination IP address.";
       }
       enum "TGTIP" {
         value "8";
         description
           "Target IP address.";
       }
     }
     description
       "ND packet type or event value.";
   }
   notification dad-not-finished {
     description
       "DAD is not finished.";
     leaf if-name {
       type "pub-type:if-name";
       description
         "Interface name.";
     }
     leaf dad-addr {
       type "inet:ipv6-address-no-zone";
       description
         "DAD address.";
     }
     leaf dad-timeout {
       type "uint32";
       units "s";
       description
         "Dad timeout.";
     }
   }
   notification anti-attack-rate-limit {
     description
       "ND anti-attack rate limit.";
     leaf packet-type {
       type "nd-pkt-evt-disp-type";
       mandatory "true";
       description
         "Type of packets that are suppressed.";
     }
     leaf suppress-value {
       type "uint32";
       units "pps";
       mandatory "true";
       description
         "Rate limit of ND packets or ND miss messages.";
     }
     leaf current-value {
       type "uint32";
       units "pps";
       mandatory "true";
       description
         "Current rate of ND packets or ND miss messages.";
     }
     leaf suppress-type {
       type "nd-suppress-type";
       mandatory "true";
       description
         "Suppress type.";
     }
     leaf if-name {
       type "pub-type:if-name";
       mandatory "true";
       description
         "Interface name.";
     }
     leaf work-if-name {
       type "pub-type:if-name";
       description
         "Work interface name.";
     }
     leaf source-mac {
       type "pub-type:mac-address";
       description
         "Source MAC address.";
     }
     leaf destination-mac {
       type "pub-type:mac-address";
       description
         "Destination MAC address.";
     }
     leaf source-ip {
       type "inet:ipv6-address-no-zone";
       description
         "Source IP address, when the packet type is not NS or RS, the source "+
         "address is invalid if it is an unspecified address.";
     }
     leaf destination-ip {
       type "inet:ipv6-address-no-zone";
       description
         "Destination IP address.";
     }
     leaf target-ip {
       type "inet:ipv6-address-no-zone";
       description
         "Target IP address.";
     }
     leaf pe-vlan {
       type "uint32";
       description
         "Outer VLAN ID.";
     }
     leaf ce-vlan {
       type "uint32";
       description
         "Inner VLAN ID.";
     }
   }
 }

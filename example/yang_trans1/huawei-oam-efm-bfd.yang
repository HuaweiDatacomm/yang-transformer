/*
Copyright (C) 2020 Huawei Technologies Co., Ltd. All rights reserved.
*/

 module huawei-oam-efm-bfd {
   namespace "urn:huawei:yang:huawei-oam-efm-bfd";
   prefix "oam-efm-bfd";
   import huawei-extension {
     prefix "ext";
   }
   import huawei-oammgr {
     prefix "oammgr";
   }
   import huawei-bfd {
     prefix "bfd";
   }
   import huawei-ifm {
     prefix "ifm";
   }
   import huawei-efm {
     prefix "efm";
   }
   import huawei-bfd-static-mpls-te {
     prefix "bfd-static-mpls-te";
   }
   import huawei-bfd-static-vpws {
     prefix "bfd-static-vpws";
   }
   organization
     "Huawei Technologies Co., Ltd.";
   contact
     "Huawei Industrial Base\nBantian, Longgang\nShenzhen 518129\nPeople's "+
     "Republic of China\nWebsite: http://www.huawei.com\nEmail: support@huawei.c"+
     "om";
   description
     "Configure the operation, administration and maintenance (OAM) association "+
     "function.";
   revision "2020-09-18" {
     description
       "Initial revision.";
     reference
       "Huawei private.";
   }
   ext:task-name "oammgr";
   typedef efm-bind-bfd-type {
     type "enumeration" {
       enum "EFM-BFD" {
         value "1";
         description
           "Type that EFM transfers fault information to BFD.";
       }
       enum "BFD-EFM" {
         value "2";
         description
           "Type that BFD transfers fault information to EFM.";
       }
     }
     description
       "Binding type.";
   }
   augment "/oammgr:oammgr" {
     description
       "Configure the operation, administration and maintenance (OAM) associatio"+
       "n function.";
     container efm-bind-bfds {
       description
         "List of associations between EFM and BFD.";
       list efm-bind-bfd {
         key "if-name bfd-session-id bind-type";
         unique "if-name bind-type";
         unique "bfd-session-id bind-type";
         description
           "Configure an instance of an association between EFM and BFD.";
         leaf if-name {
           type "leafref" {
             path "/ifm:ifm/ifm:interfaces/ifm:interface/ifm:name";
           }
           must "/ifm:ifm/ifm:interfaces/ifm:interface[ifm:name=current()]/efm:e"+
                "fm/efm:session/efm:state='enable'";
           description
             "Configure the name of interface which the EFM instance bound.";
         }
         leaf bfd-session-id {
           type "uint32" {
             range "1..16384";
           }
           must "/bfd:bfd/bfd:sessions/bfd:session[bfd:local-discriminator-multi"+
                "cast-ipv4=current()] or /bfd:bfd/bfd:sessions/bfd:session[bfd:l"+
                "ocal-discriminator=current()] or /bfd:bfd/bfd:sessions/bfd:sess"+
                "ion[bfd:local-discriminator-static-ldp-lsp=current()] or "+
                "/bfd:bfd/bfd:sessions/bfd:session[bfd-static-mpls-te:local-disc"+
                "riminator-static-te-lsp=current()] or /bfd:bfd/bfd:sessions/bfd"+
                ":session[bfd-static-mpls-te:local-discriminator-static-te-tunne"+
                "l=current()] or /bfd:bfd/bfd:sessions/bfd:session[bfd-static-vp"+
                "ws:local-discriminator-static-vll-pw=current()]";
           description
             "Configure the local discriminator of a BFD session.";
         }
         leaf bind-type {
           type "efm-bind-bfd-type";
           description
             "Configure a binding type.";
         }
       }
     }
   }
 }

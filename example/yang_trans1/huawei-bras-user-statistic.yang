/*
Copyright (C) 2019-2020 Huawei Technologies Co., Ltd. All rights reserved.
*/

 module huawei-bras-user-statistic {
   yang-version "1";
   namespace "urn:huawei:yang:huawei-bras-user-statistic";
   prefix "bras-user-statistic";
   import huawei-ifm {
     prefix "ifm";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "BRAS user statistics.";
   reference
     "Huawei private.";
   revision "2020-03-03" {
     description
       "Modify description.";
     reference
       "Huawei private.";
   }
   revision "2019-04-03" {
     description
       "Init revision.";
     reference
       "Huawei private.";
   }
   ext:task-name "aaa-access";
   typedef bras-user-statistic-user-type {
     type "enumeration" {
       enum "pppoe" {
         value "1";
         description
           "Pppoe user.";
       }
       enum "dhcp" {
         value "3";
         description
           "Dhcp user.";
       }
       enum "lns" {
         value "4";
         description
           "Lns user.";
       }
       enum "lac" {
         value "5";
         description
           "Lac user.";
       }
       enum "ipv4" {
         value "6";
         description
           "IPv4 user.";
       }
       enum "ipv6" {
         value "7";
         description
           "IPv6 user.";
       }
       enum "dual-stack" {
         value "8";
         description
           "Dual-stack user.";
       }
       enum "layer2-leased-line" {
         value "12";
         description
           "Layer 2 leased line user.";
       }
       enum "l2vpn-leased-line" {
         value "13";
         description
           "Layer 2 vpn leased line user.";
       }
       enum "layer3-leased-line" {
         value "14";
         description
           "Layer 3 leased line user.";
       }
       enum "layer2-static" {
         value "15";
         description
           "Layer 2 static user.";
       }
       enum "layer3-static" {
         value "16";
         description
           "Layer 3 static user.";
       }
       enum "lts" {
         value "17";
         description
           "L2TP Tunnel Switch user.";
       }
       enum "lac-tunnel" {
         value "18";
         description
           "L2TP LAC tunnel user.";
       }
       enum "lns-tunnel" {
         value "19";
         description
           "L2TP LNS tunnel user.";
       }
       enum "eap-relay" {
         value "20";
         description
           "EAP relay user.";
       }
       enum "eap-end" {
         value "21";
         description
           "EAP end user.";
       }
     }
     description
       "User type of access user.";
   }
   rpc filter-access-user-summary-info {
     description
       "Display summary statistics about access users.";
     input {
       leaf interface-name {
         type "leafref" {
           path "/ifm:ifm/ifm:interfaces/ifm:interface/ifm:name";
         }
         description
           "Interface name.";
       }
       leaf include-sub-interface {
         when "../interface-name";
         type "boolean";
         description
           "Whether user access sources include sub-interfaces.";
       }
       leaf pe-vlan-start-id {
         type "uint16" {
           range "0..4094";
         }
         description
           "Start outer VLAN ID for user access.";
       }
       leaf user-type {
         type "bras-user-statistic-user-type";
         description
           "User type of access user.";
       }
     }
     output {
       leaf normal-users-number {
         type "uint32";
         description
           "Number of common users.";
       }
       leaf rui-local-users-number {
         type "uint32";
         description
           "Number of local RUI users.";
       }
       leaf rui-remote-users-number {
         type "uint32";
         description
           "Number of remote RUI users.";
       }
       leaf radius-auth-number {
         type "uint32";
         description
           "Number of users authenticated through a RADIUS server.";
       }
       leaf radius-proxy-auth-number {
         type "uint32";
         description
           "Number of users authenticated through a RADIUS proxy server.";
       }
       leaf no-auth-number {
         type "uint32";
         description
           "Number of users granted access without authentication.";
       }
       leaf local-auth-number {
         type "uint32";
         description
           "Number of users authenticated locally.";
       }
       leaf tacacs-auth-number {
         type "uint32";
         description
           "Number of users authenticated through a TACACS server.";
       }
       leaf total-users-number {
         type "uint32";
         description
           "Total number of users.";
       }
     }
   }
 }

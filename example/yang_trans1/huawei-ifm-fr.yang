/*
Copyright (C) 2019 Huawei Technologies Co., Ltd. All rights reserved.
*/

 module huawei-ifm-fr {
   yang-version "1";
   namespace "urn:huawei:yang:huawei-ifm-fr";
   prefix "ifm-fr";
   import huawei-ifm {
     prefix "ifm";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Frame relay protocol.";
   revision "2019-12-25" {
     description
       "Initial revision.";
     reference
       "Huawei private.";
   }
   ext:task-name "fr";
   typedef encapsulation-format {
     type "enumeration" {
       enum "ietf" {
         value "19";
         description
           "IETF.";
       }
       enum "nonstandard" {
         value "20";
         description
           "Nonstandard.";
       }
     }
     description
       "FR interface encapsulation format.";
   }
   augment "/ifm:ifm/ifm:interfaces/ifm:interface" {
     description
       "Configure extend attributes on the interface.";
     container fr-encapsulation {
       when "../ifm:class='main-interface' and ../ifm:type='Pos' and ../ifm:link"+
            "-protocol='fr'";
       description
         "Configure frame relay interface encapsulation format.";
       leaf encapsulation {
         type "encapsulation-format";
         default "ietf";
         description
           "FR interface encapsulation format.";
       }
     }
   }
 }

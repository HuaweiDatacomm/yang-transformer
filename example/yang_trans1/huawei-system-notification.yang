/*
Copyright (C) 2021 Huawei Technologies Co., Ltd. All rights reserved.
*/

 module huawei-system-notification {
   yang-version "1";
   namespace "urn:huawei:yang:huawei-system-notification";
   prefix "system-notification";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "The SYSTEM notification nodes are defined in this file.";
   revision "2021-09-17" {
     description
       "Initial revision.";
     reference
       "Huawei private.";
   }
   ext:task-name "system";
   notification security-risk {
     description
       "With the development of cryptographic technologies and\nthe improvement "+
       "of computing capabilities, some cryptographic\nalgorithm and protocols "+
       "are deprecated. Please use more secure\nalgorithms and protocols.";
     leaf risk-type {
       type "string" {
         length "1..31";
       }
       description
         "Risk type.";
     }
   }
   notification security-risk-clear {
     description
       "The security risk has been recoverd.";
     leaf risk-type {
       type "string" {
         length "1..31";
       }
       description
         "Risk type.";
     }
   }
 }

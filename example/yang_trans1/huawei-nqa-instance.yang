/*
Copyright (C) 2019-2021 Huawei Technologies Co., Ltd. All rights reserved.
*/

 submodule huawei-nqa-instance {
   yang-version "1";
   belongs-to huawei-nqa {
     prefix "nqa";
   }
   include huawei-nqa-type;
   include huawei-nqa-test-flow;
   organization
     "Huawei Technologies Co., Ltd.";
   contact
     "Huawei Industrial Base\nBantian, Longgang\nShenzhen 518129\nPeople's "+
     "Republic of China\nWebsite: http://www.huawei.com\nEmail: support@huawei.c"+
     "om";
   description
     "Description of submodule nqa-instance.";
   revision "2021-04-29" {
     description
       "Add ethernet-service test instance.";
     reference
       "Huawei private.";
   }
   revision "2021-03-19" {
     description
       "Modify default-value of probe-count, jitter-packet-num, and data-size in"+
       " a jitter test instance.";
     reference
       "Huawei private.";
   }
   revision "2020-09-24" {
     description
       "Add MAC ping test instance.";
     reference
       "Huawei private.";
   }
   revision "2020-03-09" {
     description
       "Modify send-trap-bits.";
     reference
       "Huawei private.";
   }
   revision "2020-02-19" {
     description
       "Modify ni-name.";
     reference
       "Huawei private.";
   }
   revision "2020-02-14" {
     description
       "Modify execution-policy.";
     reference
       "Huawei private.";
   }
   revision "2020-02-13" {
     description
       "Modify TCP and ICMP Jitter.";
     reference
       "Huawei private.";
   }
   revision "2020-02-06" {
     description
       "Modify execution-policy.";
     reference
       "Huawei private.";
   }
   revision "2020-01-15" {
     description
       "Delete next-hop of icmp-input.";
     reference
       "Huawei private.";
   }
   revision "2020-01-11" {
     description
       "Modify execution-policy to rpc.";
     reference
       "Huawei private.";
   }
   revision "2019-12-12" {
     description
       "ICMP modification.";
     reference
       "Huawei private.";
   }
   revision "2019-10-30" {
     description
       "Init revision.";
     reference
       "Huawei private.";
   }
   typedef path-type {
     type "enumeration" {
       enum "bypass" {
         value "1";
         description
           "Bypath.";
       }
     }
     description
       "Path type.";
   }
   typedef jitter-code-type {
     type "enumeration" {
       enum "none" {
         value "1";
         description
           "None.";
       }
       enum "g711a" {
         value "2";
         description
           "G711a.";
       }
       enum "g711u" {
         value "3";
         description
           "G711u.";
       }
       enum "g729a" {
         value "4";
         description
           "G729a.";
       }
     }
     description
       "Description of jitter-code-type.";
   }
   typedef jitter-mode-type {
     type "enumeration" {
       enum "icmp-echo" {
         value "2";
         description
           "Icmp echo.";
       }
       enum "icmp-timestamp" {
         value "1";
         description
           "Icmp timestamp.";
       }
     }
     description
       "Description of jitter-mode-type.";
   }
   typedef time-unit-type {
     type "enumeration" {
       enum "microsecond" {
         value "1";
         description
           "Microsecond timestamp.";
       }
       enum "millisecond" {
         value "0";
         description
           "Millisecond timestamp.";
       }
     }
     description
       "Description of time-unit-type.";
   }
   typedef recv-time-unit-type {
     type "enumeration" {
       enum "unknown" {
         value "0";
         description
           "Unknown timestamp.";
       }
       enum "microsecond" {
         value "2";
         description
           "Microsecond timestamp.";
       }
       enum "millisecond" {
         value "1";
         description
           "Millisecond timestamp.";
       }
     }
     description
       "Description of recv-time-unit-type.";
   }
   typedef lsp-reply-mode-type {
     type "enumeration" {
       enum "no-reply" {
         value "1";
         description
           "NQA test packets are not to be responded.";
       }
       enum "udp" {
         value "2";
         description
           "UDP packets are used to respond NQA test packets.";
       }
       enum "level-control-channel" {
         value "4";
         description
           "Control-channel packets are used to respond to NQA test packets.";
       }
     }
     description
       "Description of lsp-reply-mode-type.";
   }
   typedef ip-lsp-reply-mode-type {
     type "enumeration" {
       enum "no-reply" {
         value "1";
         description
           "NQA test packets are not to be responded.";
       }
       enum "udp" {
         value "2";
         description
           "UDP packets are used to respond NQA test packets.";
       }
     }
     description
       "Description of ip-lsp-reply-mode-type.";
   }
   typedef bgp-lsp-reply-mode-type {
     type "enumeration" {
       enum "no-reply" {
         value "1";
         description
           "NQA test packets are not to be responded.";
       }
       enum "udp" {
         value "2";
         description
           "UDP packets are used to respond NQA test packets.";
       }
     }
     description
       "Description of ip-lsp-reply-mode-type.";
   }
   typedef te-lsp-reply-mode-type {
     type "enumeration" {
       enum "no-reply" {
         value "1";
         description
           "NQA test packets are not to be responded.";
       }
       enum "udp" {
         value "2";
         description
           "UDP packets are used to respond NQA test packets.";
       }
       enum "level-control-channel" {
         value "4";
         description
           "Control-channel packets are used to respond to NQA test packets.";
       }
     }
     description
       "Description of lsp-reply-mode-type.";
   }
   typedef lsp-path {
     type "enumeration" {
       enum "working" {
         value "0";
         description
           "Use working tunnel.";
       }
       enum "hot-standby" {
         value "1";
         description
           "Use hot standby tunnel.";
       }
       enum "primary" {
         value "2";
         description
           "Use primary tunnel.";
       }
     }
     description
       "Description of lsp-path.";
   }
   typedef lsp-ping-trace-lsp-path {
     type "enumeration" {
       enum "hot-standby" {
         value "1";
         description
           "Use hot standby tunnel.";
       }
       enum "primary" {
         value "2";
         description
           "Use primary tunnel.";
       }
     }
     description
       "Description of lsp-path.";
   }
   typedef ttl-mode {
     type "enumeration" {
       enum "uniform" {
         value "1";
         description
           "Uniform.";
       }
       enum "pipe" {
         value "2";
         description
           "Pipe.";
       }
     }
     description
       "Description of ttl-mode.";
   }
   typedef vc-type {
     type "enumeration" {
       enum "ldp" {
         value "1";
         description
           "LDP.";
       }
     }
     description
       "Description of vc-type.";
   }
   typedef lsp-version {
     type "enumeration" {
       enum "rfc4379" {
         value "2";
         description
           "Rfc4379.";
       }
       enum "ptn-mode" {
         value "3";
         description
           "Ptn-mode.";
       }
     }
     description
       "Description of lsp-version.";
   }
   typedef pwe3-reply-mode-type {
     type "enumeration" {
       enum "no-reply" {
         value "1";
         description
           "NQA test packets are not to be responded.";
       }
       enum "udp" {
         value "2";
         description
           "UDP packets are used to respond NQA test packets.";
       }
       enum "level-control-channel" {
         value "4";
         description
           "Control-channel packets are used to respond to NQA test packets.";
       }
     }
     description
       "Description of pwe3-reply-mode-type.";
   }
   typedef vpls-reply-mode-type {
     type "enumeration" {
       enum "no-reply" {
         value "1";
         description
           "No-reply.";
       }
       enum "udp" {
         value "2";
         description
           "UDP.";
       }
       enum "udp-via-vpls" {
         value "5";
         description
           "UDP-via-vpls.";
       }
     }
     description
       "Description of vpls-reply-mode-type.";
   }
   typedef pwe3-label-type {
     type "enumeration" {
       enum "label-alert" {
         value "1";
         description
           "Label alert.";
       }
       enum "control-word" {
         value "2";
         description
           "Control word.";
       }
       enum "normal" {
         value "3";
         description
           "Normal.";
       }
     }
     description
       "Description of pwe3-label-type.";
   }
   typedef start-now-type {
     type "enumeration" {
       enum "start-now" {
         value "1";
         description
           "Start now.";
       }
     }
     description
       "Start now.";
   }
   typedef stop-type {
     type "enumeration" {
       enum "stop" {
         value "1";
         description
           "Stop.";
       }
     }
     description
       "Stop.";
   }
 }

/*
Copyright (C) 2019 Huawei Technologies Co., Ltd. All rights reserved.
*/

 module huawei-vcchassis {
   yang-version "1";
   namespace "urn:huawei:yang:huawei-vcchassis";
   prefix "vcchassis";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Virtual cluter chassis.";
   revision "2019-04-01" {
     description
       "Init revision.";
     reference
       "Huawei private.";
   }
   ext:task-name "device-mgr";
   typedef vcluster-role-type {
     type "enumeration" {
       enum "master" {
         value "0";
         description
           "Master chassis.";
       }
       enum "slave" {
         value "1";
         description
           "Slave chassis.";
       }
     }
     description
       "Information of enum type vcluster-role-type.";
   }
   typedef vcluster-topo-type {
     type "enumeration" {
       enum "line" {
         value "0";
         description
           "Line topo.";
       }
       enum "ring" {
         value "1";
         description
           "Ring topo.";
       }
     }
     description
       "Information of enum type vcluster-topo-type.";
   }
   container vcchassis {
     description
       "Statistics of virtual cluter chassis.";
     container global-attribute {
       config "false";
       description
         "Statistics of global attribute.";
       leaf cluster-id {
         type "uint32" {
           range "1..255";
         }
         description
           "Cluster ID.";
       }
       leaf cluster-topo {
         type "vcluster-topo-type";
         description
           "Cluster topo.";
       }
       leaf cluster-member-number {
         type "uint32" {
           range "1..2";
         }
         description
           "Frame number of cluster.";
       }
       leaf cluster-manage-sysoid {
         type "string" {
           length "1..50";
         }
         description
           "Virtual cluster manage systerm ID.";
       }
     }
     container vcchassis-members {
       config "false";
       description
         "List of virtual cluter members.";
       list vcchassis-member {
         key "chassis-id";
         max-elements "2";
         description
           "Statistics of virtual cluter member.";
         leaf chassis-id {
           type "uint32" {
             range "1..2";
           }
           description
             "Chassis ID.";
         }
         leaf chassis-role {
           type "vcluster-role-type";
           description
             "Member chassis role.";
         }
         leaf chassis-sysoid {
           type "string" {
             length "1..50";
           }
           description
             "Member system ID.";
         }
       }
     }
   }
 }

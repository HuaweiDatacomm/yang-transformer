/*
Copyright (C) 2021 Huawei Technologies Co., Ltd. All rights reserved.
*/

 submodule huawei-te-flow-group-type {
   belongs-to huawei-te-flow-group {
     prefix "teflowgroup";
   }
   organization
     "Huawei Technologies Co., Ltd.";
   contact
     "Huawei Industrial Base\nBantian, Longgang\nShenzhen 518129\nPeople's "+
     "Republic of China\nWebsite: http://www.huawei.com\nEmail: support@huawei.c"+
     "om";
   description
     "Te flow group type defined file.";
   revision "2021-05-20" {
     description
       "Initial revision.";
     reference
       "Huawei private.";
   }
   typedef match-type {
     type "bits" {
       bit dscp {
         position "0";
         description
           "DSCP.";
       }
       bit service-class {
         position "3";
         description
           "Service class.";
       }
     }
     description
       "Match type.";
   }
   typedef flow-match-type {
     type "enumeration" {
       enum "dscp" {
         value "0";
         description
           "DSCP.";
       }
       enum "service-class" {
         value "3";
         description
           "Service class.";
       }
     }
     description
       "Flow match type.";
   }
   typedef dscp-type {
     type "string" {
       length "1..384";
       pattern "((6[0-3]|[1-5][0-9]|[0-9])(-(6[0-3]|[1-5][0-9]|[0-9]))?(,((6[0-3"+
               "]|[1-5][0-9]|[0-9])(-(6[0-3]|[1-5][0-9]|[0-9]))?))*)";
     }
     description
       "Type definition for DSCP value.";
   }
   typedef address-family-set-type {
     type "enumeration" {
       enum "ipv4" {
         value "4";
         description
           "IPv4.";
       }
       enum "ipv6" {
         value "6";
         description
           "IPv6.";
       }
     }
     description
       "Address family type.";
   }
   typedef address-family-type {
     type "enumeration" {
       enum "ipv4-ipv6" {
         value "1";
         description
           "IPv4 and IPv6.";
       }
       enum "ipv4" {
         value "4";
         description
           "IPv4.";
       }
       enum "ipv6" {
         value "6";
         description
           "IPv6.";
       }
     }
     description
       "Address family type.";
   }
   typedef tunnel-type {
     type "enumeration" {
       enum "srv6-te-flow-group" {
         value "55";
         description
           "SRv6 TE flow group.";
       }
     }
     description
       "Flow group tunnel types.";
   }
   typedef group-state-type {
     type "enumeration" {
       enum "down" {
         value "0";
         description
           "Down.";
       }
       enum "up" {
         value "1";
         description
           "Up.";
       }
       enum "delay-delete" {
         value "2";
         description
           "Delay delete.";
       }
       enum "overrun" {
         value "3";
         description
           "Overrun.";
       }
     }
     description
       "Flow group state.";
   }
   typedef tunnel-state-type {
     type "enumeration" {
       enum "down" {
         value "0";
         description
           "Down.";
       }
       enum "up" {
         value "1";
         description
           "Up.";
       }
     }
     description
       "Match tunnel state.";
   }
   typedef group-down-reason-type {
     type "enumeration" {
       enum "no-active-tunnel" {
         value "1";
         description
           "No active tunnel exists.";
       }
       enum "subscribe-delete" {
         value "2";
         description
           "Flow group subscription is deleted.";
       }
       enum "configuration-delete" {
         value "3";
         description
           "Configuration is deleted.";
       }
       enum "unknown-reason" {
         value "4";
         description
           "Unknown reason.";
       }
     }
     description
       "Flow group down reason types.";
   }
   typedef map-down-reason-type {
     type "enumeration" {
       enum "sr-policy-down" {
         value "1";
         description
           "SR Policy down.";
       }
       enum "configuration-delete" {
         value "2";
         description
           "Configuration is deleted.";
       }
       enum "flow-group-delete" {
         value "3";
         description
           "The flow group is deleted.";
       }
       enum "no-route" {
         value "4";
         description
           "No route exist.";
       }
       enum "unknown-reason" {
         value "5";
         description
           "Unknown reason.";
       }
     }
     description
       "Mappings down reason types.";
   }
   typedef group-create-type {
     type "enumeration" {
       enum "dynamic" {
         value "0";
         description
           "The create type is dynamic.";
       }
       enum "static" {
         value "1";
         description
           "The create type is static.";
       }
     }
     description
       "Create type of flow group.";
   }
   typedef service-class-type {
     type "bits" {
       bit be {
         position "0";
         description
           "Service name is BE.";
       }
       bit af1 {
         position "1";
         description
           "Service name is AF1.";
       }
       bit af2 {
         position "2";
         description
           "Service name is AF2.";
       }
       bit af3 {
         position "3";
         description
           "Service name is AF3.";
       }
       bit af4 {
         position "4";
         description
           "Service name is AF4.";
       }
       bit ef {
         position "5";
         description
           "Service name is EF.";
       }
       bit cs6 {
         position "6";
         description
           "Service name is CS6.";
       }
       bit cs7 {
         position "7";
         description
           "Service name is CS7.";
       }
     }
     description
       "Service-class type.";
   }
 }

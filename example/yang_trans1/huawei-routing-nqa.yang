/*
Copyright (C) 2020 Huawei Technologies Co., Ltd. All rights reserved.
*/

 module huawei-routing-nqa {
   yang-version "1";
   namespace "urn:huawei:yang:huawei-routing-nqa";
   prefix "rt-nqa";
   import huawei-extension {
     prefix "ext";
   }
   import huawei-network-instance {
     prefix "ni";
   }
   import huawei-l3vpn {
     prefix "l3vpn";
   }
   import huawei-routing {
     prefix "rt";
   }
   import huawei-nqa {
     prefix "nqa";
   }
   organization
     "Huawei Technologies Co., Ltd.";
   contact
     "Huawei Industrial Base\nBantian, Longgang\nShenzhen 518129\nPeople's "+
     "Republic of China\nWebsite: http://www.huawei.com\nEmail: support@huawei.c"+
     "om";
   description
     "The file defines the static route track NQA.";
   revision "2020-04-20" {
     description
       "Add NQA query node.";
     reference
       "Huawei private.";
   }
   revision "2020-02-25" {
     description
       "Initial revision.";
     reference
       "Huawei private.";
   }
   ext:task-name "route-base";
   augment "/ni:network-instance/ni:instances/ni:instance/l3vpn:afs/l3vpn:af/rt:"+
           "routing/rt:static-routing/rt:unicast-routes/rt:unicast-route/rt:trac"+
           "k-setting" {
     description
       "Static route track NQA.";
     case nqa {
       description
         "Track NQA.";
       leaf admin-name {
         type "leafref" {
           path "/nqa:nqa/nqa:instances/nqa:instance/nqa:admin-name";
         }
         must "../rt:bfd-enable='false' and ../rt:inherit-cost='false' and "+
              "../rt:permanent='false' and ../rt:topology-name='base' and "+
              "../test-name";
         description
           "Name of an NQA administer instance.";
       }
       leaf test-name {
         type "leafref" {
           path "/nqa:nqa/nqa:instances/nqa:instance/nqa:test-name";
         }
         must "../rt:bfd-enable='false' and ../rt:inherit-cost='false' and "+
              "../rt:permanent='false' and ../rt:topology-name='base' and "+
              "../admin-name";
         description
           "Name of an NQA test instance.";
       }
     }
   }
   augment "/ni:network-instance/ni:instances/ni:instance/l3vpn:afs/l3vpn:af/rt:"+
           "routing/rt:static-routing/rt:unicast-route2s/rt:unicast-route2/rt:ne"+
           "xthop-interfaces/rt:nexthop-interface/rt:track-setting" {
     description
       "Static route track NQA.";
     case nqa {
       description
         "Track NQA.";
       leaf nqa-admin-name {
         type "leafref" {
           path "/nqa:nqa/nqa:instances/nqa:instance/nqa:admin-name";
         }
         must "../rt:permanent='false' and ../../../rt:topology-name='base' and "+
              "../nqa-test-name";
         description
           "Name of an NQA administer instance.";
       }
       leaf nqa-test-name {
         type "leafref" {
           path "/nqa:nqa/nqa:instances/nqa:instance/nqa:test-name";
         }
         must "../rt:permanent='false' and ../../../rt:topology-name='base' and "+
              "../nqa-admin-name";
         description
           "Name of an NQA test instance.";
       }
     }
   }
   augment "/ni:network-instance/ni:instances/ni:instance/l3vpn:afs/l3vpn:af/rt:"+
           "routing/rt:static-routing/rt:unicast-route2s/rt:unicast-route2/rt:ne"+
           "xthop-interface-addresses/rt:nexthop-interface-address/rt:track-sett"+
           "ing" {
     description
       "Static route track NQA.";
     case nqa {
       description
         "Track NQA.";
       leaf nqa-admin-name {
         type "leafref" {
           path "/nqa:nqa/nqa:instances/nqa:instance/nqa:admin-name";
         }
         must "../rt:permanent='false' and ../../../rt:topology-name='base' and "+
              "../nqa-test-name";
         description
           "Name of an NQA administer instance.";
       }
       leaf nqa-test-name {
         type "leafref" {
           path "/nqa:nqa/nqa:instances/nqa:instance/nqa:test-name";
         }
         must "../rt:permanent='false' and ../../../rt:topology-name='base' and "+
              "../nqa-admin-name";
         description
           "Name of an NQA test instance.";
       }
     }
   }
   augment "/ni:network-instance/ni:instances/ni:instance/l3vpn:afs/l3vpn:af/rt:"+
           "routing/rt:static-routing/rt:unicast-route2s/rt:unicast-route2/rt:ne"+
           "xthop-addresses/rt:nexthop-address/rt:track-setting" {
     description
       "Static route track NQA.";
     case nqa {
       description
         "Track NQA.";
       leaf nqa-admin-name {
         type "leafref" {
           path "/nqa:nqa/nqa:instances/nqa:instance/nqa:admin-name";
         }
         must "../rt:inherit-cost='false' and ../rt:permanent='false' and "+
              "../../../rt:topology-name='base' and ../nqa-test-name";
         description
           "Name of an NQA administer instance.";
       }
       leaf nqa-test-name {
         type "leafref" {
           path "/nqa:nqa/nqa:instances/nqa:instance/nqa:test-name";
         }
         must "../rt:inherit-cost='false' and ../rt:permanent='false' and "+
              "../../../rt:topology-name='base' and ../nqa-admin-name";
         description
           "Name of an NQA test instance.";
       }
     }
   }
   augment "/ni:network-instance/ni:instances/ni:instance/l3vpn:afs/l3vpn:af/rt:"+
           "routing/rt:static-routing/rt:unicast-route2s/rt:unicast-route2/rt:ne"+
           "xthop-vrf-addresses/rt:nexthop-vrf-address/rt:track-setting" {
     description
       "Static route track NQA.";
     case nqa {
       description
         "Track NQA.";
       leaf nqa-admin-name {
         type "leafref" {
           path "/nqa:nqa/nqa:instances/nqa:instance/nqa:admin-name";
         }
         must "../rt:inherit-cost='false' and ../rt:permanent='false' and "+
              "../../../rt:topology-name='base' and ../nqa-test-name";
         description
           "Name of an NQA administer instance.";
       }
       leaf nqa-test-name {
         type "leafref" {
           path "/nqa:nqa/nqa:instances/nqa:instance/nqa:test-name";
         }
         must "../rt:inherit-cost='false' and ../rt:permanent='false' and "+
              "../../../rt:topology-name='base' and ../nqa-admin-name";
         description
           "Name of an NQA test instance.";
       }
     }
   }
   augment "/ni:network-instance/ni:instances/ni:instance/l3vpn:afs/l3vpn:af/rt:"+
           "routing/rt:static-routing/rt:ipv4-routes/rt:ipv4-route" {
     description
       "Static route track NQA.";
     leaf nqa-admin-name {
       type "leafref" {
         path "/nqa:nqa/nqa:instances/nqa:instance/nqa:admin-name";
       }
       must "../nqa-test-name";
       description
         "Name of an NQA administer instance.";
     }
     leaf nqa-test-name {
       type "leafref" {
         path "/nqa:nqa/nqa:instances/nqa:instance/nqa:test-name";
       }
       must "../nqa-admin-name";
       description
         "Name of an NQA test instance.";
     }
   }
   augment "/ni:network-instance/ni:instances/ni:instance/l3vpn:afs/l3vpn:af/rt:"+
           "routing/rt:static-routing/rt:ipv6-routes/rt:ipv6-route" {
     description
       "Static route track NQA.";
     leaf nqa-admin-name {
       type "leafref" {
         path "/nqa:nqa/nqa:instances/nqa:instance/nqa:admin-name";
       }
       must "../nqa-test-name";
       description
         "Name of an NQA administer instance.";
     }
     leaf nqa-test-name {
       type "leafref" {
         path "/nqa:nqa/nqa:instances/nqa:instance/nqa:test-name";
       }
       must "../nqa-admin-name";
       description
         "Name of an NQA test instance.";
     }
   }
 }

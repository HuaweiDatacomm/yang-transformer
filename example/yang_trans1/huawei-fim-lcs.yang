/*
Copyright (C) 2020 Huawei Technologies Co., Ltd. All rights reserved.
*/

 module huawei-fim-lcs {
   yang-version "1";
   namespace "urn:huawei:yang:huawei-fim-lcs";
   prefix "fim-lcs";
   import huawei-extension {
     prefix "ext";
   }
   import huawei-license {
     prefix "lcs";
   }
   organization
     "Huawei Technologies Co., Ltd.";
   contact
     "Huawei Industrial Base\nBantian, Longgang\nShenzhen 518129\nPeople's "+
     "Republic of China\nWebsite: http://www.huawei.com\nEmail: support@huawei.c"+
     "om";
   description
     "Global Configuration.";
   revision "2020-03-11" {
     description
       "Initial revision.";
     reference
       "Huawei private.";
   }
   augment "/lcs:license/lcs:license-items/lcs:license-item" {
     description
       "Channelized sub-interface license information list.";
     container port-mode-channels {
       when "(../lcs:name ='LCR5S0FCHAN91' or ../lcs:name ='LCR5S0FCHAN92' or "+
            "../lcs:name ='LCR5S0FCHAN93' or ../lcs:name ='LCR5S0FCHAN94' or "+
            "../lcs:name ='LCR5S03SUBC93' or ../lcs:name ='LCR5S03SUBC94' or "+
            "../lcs:name ='LCR5S03SUBC95' or ../lcs:name ='LCR5S03SUBC92' or "+
            "../lcs:name ='LCR5S42CHAN70' or ../lcs:name ='LCR5S42CHAN71' or "+
            "../lcs:name ='LCR5S42CHAN72' or ../lcs:name ='LCR5S42CHAN73' or "+
            "../lcs:name ='LCR5S42CHAN90' or ../lcs:name ='LCR5S42CHAN91' or "+
            "../lcs:name ='LCR5S42CHAN92' or ../lcs:name ='LCR5S42CHAN93' or "+
            "../lcs:name ='LCR5S40CHIN00' or ../lcs:name ='LCR5S40CHIN01' or "+
            "../lcs:name ='LCR5S40CHIN02' or ../lcs:name ='LCX6S40CHIN00' or "+
            "../lcs:name ='LCX6S40CHIN01' or ../lcs:name ='LCX6S40CHIN02' or "+
            "../lcs:name ='LTNRS69CHIN00' or ../lcs:name ='LTNRS69CHIN01' or "+
            "../lcs:name ='LTNRS69CHIN02' or ../lcs:name ='LCR9S9KXCSF80' or "+
            "../lcs:name ='LCR9S9KNCSF81' or ../lcs:name ='LCR9S9KNCSF80' or "+
            "../lcs:name ='LCR9S9KKCSF80' or ../lcs:name ='LCX6S00NCSFAP' or "+
            "../lcs:name ='LCX6S00XCSFAP')";
       description
         "List of channelized sub-interface license information.";
       list port-mode-channel {
         key "position";
         description
           "Configure channelized sub-interface license information.";
         leaf position {
           type "string" {
             length "1..32";
           }
           description
             "Port position.";
         }
       }
     }
   }
   ext:task-name "forwarding";
 }

/*
Copyright (C) 2019-2020 Huawei Technologies Co., Ltd. All rights reserved.
*/

 module huawei-igp {
   namespace "urn:huawei:yang:huawei-igp";
   prefix "igp";
   import huawei-mpls-te {
     prefix "mpls-te";
   }
   import huawei-tunnel-management {
     prefix "tnlm";
   }
   import huawei-ifm {
     prefix "ifm";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "IGP management.";
   revision "2020-03-13" {
     description
       "Modify the format specification.";
     reference
       "Huawei private.";
   }
   revision "2020-02-03" {
     description
       "Reconstructing Yang file by yin mechanism.";
     reference
       "Huawei private.";
   }
   revision "2019-04-04" {
     description
       "Initial revision.";
     reference
       "Huawei private.";
   }
   ext:task-name "mpls-te";
   typedef shortcut-mode {
     type "enumeration" {
       enum "disable" {
         value "0";
         description
           "The IGP shortcut function is disabled.";
       }
       enum "isis" {
         value "1";
         description
           "To enable the IGP shortcut mode as ISIS.";
       }
       enum "ospf" {
         value "2";
         description
           "To enable the IGP shortcut mode as OSPF.";
       }
       enum "both" {
         value "3";
         description
           "To enable the IGP shortcut mode as both.";
       }
     }
     description
       "Interface IGP short cut mode.";
   }
   augment "/ifm:ifm/ifm:interfaces/ifm:interface/tnlm:tunnel-protocol/tnlm:type"+
           "/mpls-te:mpls-te/mpls-te:te-tunnel" {
     description
       "IGP augment to MPLS TE.";
     container igp-attr {
       when "../mpls-te:common-attributes/mpls-te:signal-protocol!='cr-static'";
       description
         "Configure IGP attribute of tunnel interface.";
       leaf adv-enable {
         type "boolean";
         must "../adv-enable='false' or (../../mpls-te:common-attributes/mpls-te"+
              ":signal-protocol!='segment-routing' and ../shortcut-type!='ospf' "+
              "and ../shortcut-type!='isis')";
         default "false";
         description
           "Enable/disable tunnel interface forwarding adjacency based on tunnel"+
           " interfaces. An MPLE TE tunnel can be advertised as a virtual link "+
           "over an IGP network. The virtual link can participate in route "+
           "calculation.";
       }
       leaf adv-ipv6-enable {
         type "boolean";
         must "../adv-ipv6-enable='false' or ../adv-enable='true'";
         default "false";
         description
           "Enable/disable tunnel interface forwarding adjacency IPv6 based on "+
           "tunnel interfaces. An MPLE TE tunnel can be advertised as a virtual "+
           "link over an IGP network. The virtual link can participate in route "+
           "calculation.";
       }
       leaf hold-time {
         type "uint32" {
           range "0..4294967295";
         }
         units "ms";
         must "../hold-time=0 or ../adv-enable='true' or ../shortcut-type='isis'"+
              "";
         default "0";
         description
           "When tunnel get down, the time of notifying tunnel as virtual link "+
           "to other routers.";
       }
       leaf shortcut-type {
         type "shortcut-mode";
         must "../shortcut-type='disable' or ../adv-enable!='true'";
         default "disable";
         description
           "Tunnel interface shortcut types.";
       }
       choice metric-type {
         description
           "IGP metric types of tunnel interfaces. Relative metric type and "+
           "absolute metric type.";
         case relative {
           description
             "IGP relative metric value of a tunnel interface.";
           leaf relative {
             type "int32" {
               range "-10..10";
             }
             description
               "IGP relative metric value of a tunnel interface.";
           }
         }
         case absolute {
           description
             "IGP absolute metric value of a tunnel interface.";
           leaf absolute {
             type "int32" {
               range "1..65535";
             }
             description
               "IGP absolute metric value of a tunnel interface.";
           }
         }
       }
     }
   }
 }

/*
Copyright (C) 2019-2020 Huawei Technologies Co., Ltd. All rights reserved.
*/

 submodule huawei-te-type {
   belongs-to huawei-te {
     prefix "te";
   }
   organization
     "Huawei Technologies Co., Ltd.";
   contact
     "Huawei Industrial Base\nBantian, Longgang\nShenzhen 518129\nPeople's "+
     "Republic of China\nWebsite: http://www.huawei.com\nEmail: support@huawei.c"+
     "om";
   description
     "Te Description of Type.";
   revision "2020-03-10" {
     description
       "Fixed some descriptions.";
     reference
       "Huawei private.";
   }
   revision "2019-06-14" {
     description
       "Init revision.";
     reference
       "Huawei private.";
   }
   typedef er-hop-type {
     type "enumeration" {
       enum "include-strict" {
         value "1";
         description
           "Strictly included.";
       }
       enum "include-loose" {
         value "2";
         description
           "Loosely included.";
       }
       enum "exclude" {
         value "3";
         description
           "Exclude.";
       }
     }
     description
       "ErHop Type.";
   }
   typedef er-hop-interface-type {
     type "enumeration" {
       enum "default" {
         value "0";
         description
           "Not configured.";
       }
       enum "incoming" {
         value "1";
         description
           "Incoming interface.";
       }
       enum "outgoing" {
         value "2";
         description
           "Outgoing interface.";
       }
     }
     description
       "ErHop Int Type.";
   }
   typedef te-hop-address-type {
     type "enumeration" {
       enum "ipv4" {
         value "1";
         description
           "IPv4 type.";
       }
     }
     description
       "Te Hop Address Type.";
   }
   typedef er-sid-label-type {
     type "enumeration" {
       enum "adjacency" {
         value "1";
         description
           "Adjacency label.";
       }
       enum "prefix" {
         value "2";
         description
           "Prefix label.";
       }
       enum "binding" {
         value "3";
         description
           "Binding label.";
       }
     }
     description
       "ERHop SID Label Type.";
   }
 }

/*
Copyright (C) 2019-2020 Huawei Technologies Co., Ltd. All rights reserved.
*/

 module huawei-bgp-vpnv4mcast {
   yang-version "1";
   namespace "urn:huawei:yang:huawei-bgp-vpnv4mcast";
   prefix "bgp-vpnv4mcast";
   import huawei-extension {
     prefix "ext";
   }
   import huawei-network-instance {
     prefix "ni";
   }
   import huawei-bgp {
     prefix "bgp";
   }
   import huawei-xpl {
     prefix "xpl";
   }
   import huawei-routing-policy {
     prefix "rtp";
   }
   import huawei-bgp-routing-table {
     prefix "bgp-rt";
   }
   import ietf-inet-types {
     prefix "inet";
   }
   import huawei-pub-type {
     prefix "pub-type";
   }
   organization
     "Huawei Technologies Co., Ltd.";
   contact
     "Huawei Industrial Base\nBantian, Longgang\nShenzhen 518129\nPeople's "+
     "Republic of China\nWebsite: http://www.huawei.com\nEmail: support@huawei.c"+
     "om";
   description
     "Inter-AS routing protocol that exchanges Network Layer Reachability "+
     "Information (NLRI) with other BGP systems.";
   revision "2020-08-30" {
     description
       "The YANG descriptions are modified according to new standards.";
     reference
       "Huawei private.";
   }
   revision "2019-03-22" {
     description
       "Initial revision.";
     reference
       "Huawei private.";
   }
   ext:task-name "bgp";
   augment "/ni:network-instance/ni:instances/ni:instance/bgp:bgp/bgp:base-proce"+
           "ss/bgp:afs/bgp:af" {
     description
       "BGP IPv4 vpnv4-multicast address family configuration.";
     container ipv4-vpn-multicast {
       when "../bgp:type='ipv4vpnmcast'";
       description
         "Configure IPv4 vpnv4-multicast address family.";
       container common {
         description
           "Configure BGP IPv4 vpnv4-multicast common options.";
         leaf policy-vpntarget {
           type "boolean";
           default "true";
           description
             "Enable/disable VPN target-based filtering for the received VPN "+
             "routes. Only the VPN route whose Export RT attribute matches the "+
             "local Import RT attribute can be added to the routing table. This "+
             "option can be used in the inter-AS VPN Option B solution and the "+
             "ASBR MP-EBGP inter-AS L2VPN solution in Kompella mode.";
         }
         choice reflector-type {
           description
             "Set IPv4 address or id.";
           case address {
             description
               "IPv4 address.";
             leaf reflector-cluster-ipv4 {
               type "inet:ipv4-address-no-zone";
               description
                 "Set a cluster ID. The value is expressed in the format of an "+
                 "IPv4 address. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
           case id {
             description
               "Set value.";
             leaf reflector-cluster-id {
               type "uint32" {
                 range "1..4294967295";
               }
               description
                 "Set a cluster ID. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
         }
         leaf reflect-between-client {
           type "boolean";
           default "true";
           description
             "Enable/disable route reflection between clients.";
         }
         leaf reflect-change-path {
           type "boolean";
           default "false";
           description
             "Enable/disable an RR to use an export policy to change route "+
             "AS_Path. By default, this function is not enabled.";
         }
       }
       container slow-peer {
         description
           "Configure peer advertising routes slowly.";
         leaf detection {
           type "boolean";
           default "true";
           description
             "Enable/disable detect slow peers.";
         }
         leaf detection-threshold {
           type "uint16" {
             range "120..3600";
           }
           units "s";
           default "300";
           description
             "Specify the time in seconds lagging behind average when a peer is "+
             "determined to be a slow peer.";
         }
         leaf absolute-detection {
           type "boolean";
           default "true";
           description
             "Enable/disable absolute-detect slow peers.";
         }
         leaf absolute-detection-threshold {
           type "uint16" {
             range "3..3600";
           }
           units "s";
           default "9";
           description
             "Specify the packet send delay time in second when a peer is "+
             "determined to be a slow peer.";
         }
       }
     }
   }
   augment "/ni:network-instance/ni:instances/ni:instance/bgp:bgp/bgp:base-proce"+
           "ss/bgp:peer-groups/bgp:peer-group/bgp:afs/bgp:af" {
     description
       "BGP IPv4 vpnv4-multicast address family configuration.";
     container ipv4-vpn-multicast {
       when "../bgp:type='ipv4vpnmcast'";
       description
         "Configure BGP IPv4 vpnv4-multicast options.";
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       leaf advertise-large-community {
         type "boolean";
         default "false";
         description
           "Enable/disable large-community attribute advertisement. The "+
           "Link-state address family and the RPD address family do not support "+
           "this element.";
       }
       leaf advertise-community {
         type "boolean";
         default "false";
         description
           "Enable/disable advertise the community attribute to a peer or a peer"+
           " group.";
       }
       leaf update-group-independent {
         type "boolean";
         default "false";
         description
           "Enable/disable the peer which can reside in an independent peer "+
           "group.";
       }
       leaf reflect-client {
         when "../../../../bgp:type='ibgp'";
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf update-packet-standard-compatible {
         type "boolean";
         default "false";
         description
           "Enable/disable compatible standard update packet.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
     }
   }
   augment "/ni:network-instance/ni:instances/ni:instance/bgp:bgp/bgp:base-proce"+
           "ss/bgp:peers/bgp:peer/bgp:afs/bgp:af" {
     description
       "BGP IPv4 vpnv4-multicast address family configuration.";
     container ipv4-vpn-multicast {
       when "../bgp:type = 'ipv4vpnmcast'";
       description
         "Configure IPv4 vpnv4-multicast options.";
       leaf group-name {
         type "leafref" {
           path "../../../../../../bgp:peer-groups/bgp:peer-group/bgp:name";
         }
         must "../../../../../../bgp:peer-groups/bgp:peer-group[bgp:name = "+
              "current()]/bgp:afs/bgp:af[bgp:type='ipv4vpnmcast']";
         must "../../../../../../bgp:peer-groups/bgp:peer-group[bgp:name = "+
              "current()]/bgp:peer-establish-mode = 'static'";
         description
           "Configure a name for a peer group. After a peer is deleted from the "+
           "peer group, the peer is disabled from the address family. The object"+
           " cannot be modified.";
         ext:operation-exclude "update" {
           description
             "The node cannot be modified, when the peer already belongs to a "+
             "peer-group.";
         }
       }
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       leaf advertise-large-community {
         type "bgp:peer-comm-config-type";
         default "default";
         description
           "Enable large-community attribute advertisement. The Link-state "+
           "address family and the RPD address family do not support this "+
           "element.";
       }
       leaf advertise-large-community-state {
         type "boolean";
         default "false";
         config "false";
         description
           "Whether large-community attribute advertisement is enabled on a "+
           "peer. The Link-state address family and the RPD address family do "+
           "not support this element.";
       }
       leaf advertise-community {
         type "boolean";
         default "false";
         description
           "Enable/disable advertise the community attribute to a peer or a peer"+
           " group.";
       }
       leaf update-group-independent {
         type "bgp:peer-comm-config-type";
         default "default";
         description
           "Enable/disable the peer which can reside in an independent peer "+
           "group.";
       }
       leaf update-group-independent-state {
         type "boolean";
         config "false";
         description
           "Whether the peer can reside in an independent peer group.";
       }
       leaf reflect-client {
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf update-packet-standard-compatible {
         type "boolean";
         default "false";
         description
           "Enable/disable compatible standard update packet.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
   }
   augment "/bgp:bgp/bgp:base-process/bgp-rt:bgp-route" {
     description
       "BGP IPv4 vpnv4-multicast address family routes information.";
     container ipv4-vpn-multicast {
       config "false";
       description
         "Statistics of IPv4 vpnv4-multicast routes.";
       container statistic {
         description
           "Statistics of BGP routes information of IPv4 vpnv4-multicast address"+
           " family.";
         leaf total-number {
           type "uint32";
           description
             "Total number of routes.";
         }
       }
     }
   }
 }

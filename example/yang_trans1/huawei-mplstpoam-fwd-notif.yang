/*
Copyright (C) 2020 Huawei Technologies Co., Ltd. All rights reserved.
*/

 module huawei-mplstpoam-fwd-notif {
   yang-version "1";
   namespace "urn:huawei:yang:huawei-mplstpoam-fwd-notif";
   prefix "mplstpoam-fwd-notif";
   import ietf-inet-types {
     prefix "inet";
   }
   import huawei-l2vpn {
     prefix "l2vpn";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of MPLS-TP OAM.";
   revision "2020-04-10" {
     description
       "Initial revision.";
     reference
       "Huawei private.";
   }
   ext:task-name "tpoam";
   notification tpoam-tunnel-not-support {
     description
       "MPLS-TP OAM for PW does not support the current public tunnel.";
     leaf vc-id {
       type "uint32";
       description
         "Identifier of the layer 2 virtual circuit.";
     }
     leaf vc-type {
       type "l2vpn:encapsulation-type";
       description
         "Encapsulation type of a L2VPN instance.";
     }
     leaf peer-addr {
       type "inet:ipv4-address-no-zone";
       description
         "Peer IP address.";
     }
   }
   notification tpoam-tunnel-not-support-resume {
     description
       "The alarm that MPLS-TP OAM for PW does not support the current public "+
       "tunnel is resumed.";
     leaf vc-id {
       type "uint32";
       description
         "Identifier of the layer 2 virtual circuit.";
     }
     leaf vc-type {
       type "l2vpn:encapsulation-type";
       description
         "Encapsulation type of a L2VPN instance.";
     }
     leaf peer-addr {
       type "inet:ipv4-address-no-zone";
       description
         "Peer IP address.";
     }
   }
 }

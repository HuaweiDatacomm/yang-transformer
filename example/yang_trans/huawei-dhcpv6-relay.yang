/*
Copyright (C) 2019-2020 Huawei Technologies Co., Ltd. All rights reserved.
*/

 submodule huawei-dhcpv6-relay {
   yang-version "1";
   belongs-to huawei-dhcpv6 {
     prefix "dhcpv6";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module contains a collection of YANG definitions for managing DHCPv6 "+
     "relay.";
   revision "2020-03-09" {
     description
       "Modify description.";
     reference
       "Huawei private.";
   }
   revision "2019-12-16" {
     description
       "Initial revision.";
     reference
       "Huawei private.";
   }
   typedef rapid-commit-flag-type {
     type "enumeration" {
       enum "off" {
         value "0";
         description
           "Disable rapid commit.";
       }
       enum "on" {
         value "1";
         description
           "Enable rapid commit.";
       }
     }
     description
       "The type of rapid commit flag.";
   }
   typedef relay-table-status {
     type "enumeration" {
       enum "init" {
         value "0";
         description
           "Init status.";
       }
       enum "solicit" {
         value "1";
         description
           "Send solicit packet to server.";
       }
       enum "advertise" {
         value "2";
         description
           "Send Advertise packet to client.";
       }
       enum "request" {
         value "3";
         description
           "Send request packet to server.";
       }
       enum "renewrebind" {
         value "4";
         description
           "Send renew or rebind packet to server.";
       }
       enum "confirm" {
         value "5";
         description
           "Send confirm packet to server.";
       }
       enum "decline" {
         value "6";
         description
           "Send decline packet to server.";
       }
       enum "release" {
         value "7";
         description
           "Send release packet to server.";
       }
       enum "up" {
         value "8";
         description
           "Stable status.";
       }
       enum "error" {
         value "9";
         description
           "Error status.";
       }
     }
     description
       "The type of relay table status.";
   }
   typedef ia-type {
     type "enumeration" {
       enum "iainvalid" {
         value "0";
         description
           "Invalid identity association.";
       }
       enum "iana" {
         value "1";
         description
           "Identity association for non-temporary addresses.";
       }
       enum "iata" {
         value "2";
         description
           "Identity association for temporary addresses.";
       }
       enum "iapd" {
         value "3";
         description
           "Identity association for prefix delegation.";
       }
     }
     description
       "The type of identity association.";
   }
   typedef relay-file-authentication-mode {
     type "enumeration" {
       enum "check" {
         value "0";
         description
           "Check.";
       }
       enum "no-check" {
         value "1";
         description
           "No-check.";
       }
       enum "force-check" {
         value "2";
         description
           "Force-check.";
       }
     }
     description
       "The type of file authentication mode.";
   }
 }

module ietf-netconf {
   // the namespace for NETCONF XML definitions is unchanged

   // from RFC 4741, which this document replaces

   namespace "urn:ietf:params:xml:ns:netconf:base:1.0";
   prefix "nc";
   import ietf-inet-types {
     prefix "inet";
   }
   organization
     "IETF NETCONF (Network Configuration) Working Group";
   contact
     "WG Web:   <http://tools.ietf.org/wg/netconf/>\nWG List:  <netconf@ietf.org"+
     ">\nWG Chair: Bert Wijnen\n          <bertietf@bwijnen.net>\nWG Chair: "+
     "Mehmet Ersue\n          <mehmet.ersue@nsn.com>\nEditor:   Martin "+
     "Bjorklund\n          <mbj@tail-f.com>\nEditor:   Juergen Schoenwaelder\n  "+
     "        <j.schoenwaelder@jacobs-university.de>\nEditor:   Andy Bierman\n  "+
     "        <andy.bierman@brocade.com>";
   description
     "NETCONF Protocol Data Types and Protocol Operations.\nCopyright (c) 2011 "+
     "IETF Trust and the persons identified as\nthe document authors.  All "+
     "rights reserved.\nRedistribution and use in source and binary forms, with "+
     "or\nwithout modification, is permitted pursuant to, and subject\nto the "+
     "license terms contained in, the Simplified BSD License\nset forth in "+
     "Section 4.c of the IETF Trust's Legal Provisions\nRelating to IETF "+
     "Documents\n(http://trustee.ietf.org/license-info).\nThis version of this "+
     "YANG module is part of RFC 6241; see\nthe RFC itself for full legal "+
     "notices.";
   revision "2011-06-01" {
     description
       "Initial revision";
     reference
       "RFC 6241: Network Configuration Protocol";
   }
   extension get-filter-element-attributes {
     description
       "If this extension is present within an 'anyxml'\nstatement named "+
       "'filter', which must be conceptually\ndefined within the RPC input "+
       "section for the <get>\nand <get-config> protocol operations, then "+
       "the\nfollowing unqualified XML attribute is supported\nwithin the "+
       "<filter> element, within a <get> or\n<get-config> protocol operation:\n "+
       " type : optional attribute with allowed\n         value strings "+
       "'subtree' and 'xpath'.\n         If missing, the default value is "+
       "'subtree'.\nIf the 'xpath' feature is supported, then the\nfollowing "+
       "unqualified XML attribute is\nalso supported:\n  select: optional "+
       "attribute containing a\n          string representing an XPath "+
       "expression.\n          The 'type' attribute must be equal to 'xpath'\n  "+
       "        if this attribute is present.";
   }
   // NETCONF capabilities defined as features

   feature writable-running {
     description
       "NETCONF :writable-running capability;\nIf the server advertises the "+
       ":writable-running\ncapability for a session, then this feature "+
       "must\nalso be enabled for that session.  Otherwise,\nthis feature must "+
       "not be enabled.";
     reference
       "RFC 6241, Section 8.2";
   }
   feature candidate {
     description
       "NETCONF :candidate capability;\nIf the server advertises the :candidate"+
       "\ncapability for a session, then this feature must\nalso be enabled for "+
       "that session.  Otherwise,\nthis feature must not be enabled.";
     reference
       "RFC 6241, Section 8.3";
   }
   feature confirmed-commit {
     if-feature "candidate";
     description
       "NETCONF :confirmed-commit:1.1 capability;\nIf the server advertises the "+
       ":confirmed-commit:1.1\ncapability for a session, then this feature "+
       "must\nalso be enabled for that session.  Otherwise,\nthis feature must "+
       "not be enabled.";
     reference
       "RFC 6241, Section 8.4";
   }
   feature rollback-on-error {
     description
       "NETCONF :rollback-on-error capability;\nIf the server advertises the "+
       ":rollback-on-error\ncapability for a session, then this feature "+
       "must\nalso be enabled for that session.  Otherwise,\nthis feature must "+
       "not be enabled.";
     reference
       "RFC 6241, Section 8.5";
   }
   feature validate {
     description
       "NETCONF :validate:1.1 capability;\nIf the server advertises the "+
       ":validate:1.1\ncapability for a session, then this feature must\nalso be"+
       " enabled for that session.  Otherwise,\nthis feature must not be "+
       "enabled.";
     reference
       "RFC 6241, Section 8.6";
   }
   feature startup {
     description
       "NETCONF :startup capability;\nIf the server advertises the :startup\ncap"+
       "ability for a session, then this feature must\nalso be enabled for that "+
       "session.  Otherwise,\nthis feature must not be enabled.";
     reference
       "RFC 6241, Section 8.7";
   }
   feature url {
     description
       "NETCONF :url capability;\nIf the server advertises the :url\ncapability "+
       "for a session, then this feature must\nalso be enabled for that session."+
       "  Otherwise,\nthis feature must not be enabled.";
     reference
       "RFC 6241, Section 8.8";
   }
   feature xpath {
     description
       "NETCONF :xpath capability;\nIf the server advertises the :xpath\ncapabil"+
       "ity for a session, then this feature must\nalso be enabled for that "+
       "session.  Otherwise,\nthis feature must not be enabled.";
     reference
       "RFC 6241, Section 8.9";
   }
   // NETCONF Simple Types

   typedef session-id-type {
     type "uint32" {
       range "1..max";
     }
     description
       "NETCONF Session Id";
   }
   typedef session-id-or-zero-type {
     type "uint32";
     description
       "NETCONF Session Id or Zero to indicate none";
   }
   // NETCONF Standard Protocol Operations

   rpc get-config {
     description
       "Retrieve all or part of a specified configuration.";
     reference
       "RFC 6241, Section 7.1";
     input {
       container source {
         description
           "Particular configuration to retrieve.";
         choice config-source {
           mandatory "true";
           description
             "The configuration to retrieve.";
           leaf candidate {
             if-feature "candidate";
             type "empty";
             description
               "The candidate configuration is the config source.";
           }
           leaf running {
             type "empty";
             description
               "The running configuration is the config source.";
           }
           leaf startup {
             if-feature "startup";
             type "empty";
             description
               "The startup configuration is the config source.\nThis is "+
               "optional-to-implement on the server because\nnot all servers "+
               "will support filtering for this\ndatastore.";
           }
         }
       }
       anyxml filter {
         description
           "Subtree or XPath filter to use.";
         nc:get-filter-element-attributes;
       }
     }
     output {
       anyxml data {
         description
           "Copy of the source datastore subset that matched\nthe filter "+
           "criteria (if any).  An empty data container\nindicates that the "+
           "request did not produce any results.";
       }
     }
   }
   rpc edit-config {
     description
       "The <edit-config> operation loads all or part of a specified\nconfigurat"+
       "ion to the specified target configuration.";
     reference
       "RFC 6241, Section 7.2";
     input {
       container target {
         description
           "Particular configuration to edit.";
         choice config-target {
           mandatory "true";
           description
             "The configuration target.";
           leaf candidate {
             if-feature "candidate";
             type "empty";
             description
               "The candidate configuration is the config target.";
           }
           leaf running {
             if-feature "writable-running";
             type "empty";
             description
               "The running configuration is the config source.";
           }
         }
       }
       leaf default-operation {
         type "enumeration" {
           enum "merge" {
             description
               "The default operation is merge.";
           }
           enum "replace" {
             description
               "The default operation is replace.";
           }
           enum "none" {
             description
               "There is no default operation.";
           }
         }
         default "merge";
         description
           "The default operation to use.";
       }
       leaf test-option {
         if-feature "validate";
         type "enumeration" {
           enum "test-then-set" {
             description
               "The server will test and then set if no errors.";
           }
           enum "set" {
             description
               "The server will set without a test first.";
           }
           enum "test-only" {
             description
               "The server will only test and not set, even\nif there are no "+
               "errors.";
           }
         }
         default "test-then-set";
         description
           "The test option to use.";
       }
       leaf error-option {
         type "enumeration" {
           enum "stop-on-error" {
             description
               "The server will stop on errors.";
           }
           enum "continue-on-error" {
             description
               "The server may continue on errors.";
           }
           enum "rollback-on-error" {
             description
               "The server will roll back on errors.\nThis value can only be "+
               "used if the 'rollback-on-error'\nfeature is supported.";
           }
         }
         default "stop-on-error";
         description
           "The error option to use.";
       }
       choice edit-content {
         mandatory "true";
         description
           "The content for the edit operation.";
         anyxml config {
           description
             "Inline Config content.";
         }
         leaf url {
           if-feature "url";
           type "inet:uri";
           description
             "URL-based config content.";
         }
       }
     }
   }
   rpc copy-config {
     description
       "Create or replace an entire configuration datastore with the\ncontents "+
       "of another complete configuration datastore.";
     reference
       "RFC 6241, Section 7.3";
     input {
       container target {
         description
           "Particular configuration to copy to.";
         choice config-target {
           mandatory "true";
           description
             "The configuration target of the copy operation.";
           leaf candidate {
             if-feature "candidate";
             type "empty";
             description
               "The candidate configuration is the config target.";
           }
           leaf running {
             if-feature "writable-running";
             type "empty";
             description
               "The running configuration is the config target.\nThis is "+
               "optional-to-implement on the server.";
           }
           leaf startup {
             if-feature "startup";
             type "empty";
             description
               "The startup configuration is the config target.";
           }
           leaf url {
             if-feature "url";
             type "inet:uri";
             description
               "The URL-based configuration is the config target.";
           }
         }
       }
       container source {
         description
           "Particular configuration to copy from.";
         choice config-source {
           mandatory "true";
           description
             "The configuration source for the copy operation.";
           leaf candidate {
             if-feature "candidate";
             type "empty";
             description
               "The candidate configuration is the config source.";
           }
           leaf running {
             type "empty";
             description
               "The running configuration is the config source.";
           }
           leaf startup {
             if-feature "startup";
             type "empty";
             description
               "The startup configuration is the config source.";
           }
           leaf url {
             if-feature "url";
             type "inet:uri";
             description
               "The URL-based configuration is the config source.";
           }
           anyxml config {
             description
               "Inline Config content: <config> element.  Represents\nan entire "+
               "configuration datastore, not\na subset of the running datastore."+
               "";
           }
         }
       }
     }
   }
   rpc delete-config {
     description
       "Delete a configuration datastore.";
     reference
       "RFC 6241, Section 7.4";
     input {
       container target {
         description
           "Particular configuration to delete.";
         choice config-target {
           mandatory "true";
           description
             "The configuration target to delete.";
           leaf startup {
             if-feature "startup";
             type "empty";
             description
               "The startup configuration is the config target.";
           }
           leaf url {
             if-feature "url";
             type "inet:uri";
             description
               "The URL-based configuration is the config target.";
           }
         }
       }
     }
   }
   rpc lock {
     description
       "The lock operation allows the client to lock the configuration\nsystem "+
       "of a device.";
     reference
       "RFC 6241, Section 7.5";
     input {
       container target {
         description
           "Particular configuration to lock.";
         choice config-target {
           mandatory "true";
           description
             "The configuration target to lock.";
           leaf candidate {
             if-feature "candidate";
             type "empty";
             description
               "The candidate configuration is the config target.";
           }
           leaf running {
             type "empty";
             description
               "The running configuration is the config target.";
           }
           leaf startup {
             if-feature "startup";
             type "empty";
             description
               "The startup configuration is the config target.";
           }
         }
       }
     }
   }
   rpc unlock {
     description
       "The unlock operation is used to release a configuration lock,\npreviousl"+
       "y obtained with the 'lock' operation.";
     reference
       "RFC 6241, Section 7.6";
     input {
       container target {
         description
           "Particular configuration to unlock.";
         choice config-target {
           mandatory "true";
           description
             "The configuration target to unlock.";
           leaf candidate {
             if-feature "candidate";
             type "empty";
             description
               "The candidate configuration is the config target.";
           }
           leaf running {
             type "empty";
             description
               "The running configuration is the config target.";
           }
           leaf startup {
             if-feature "startup";
             type "empty";
             description
               "The startup configuration is the config target.";
           }
         }
       }
     }
   }
   rpc get {
     description
       "Retrieve running configuration and device state information.";
     reference
       "RFC 6241, Section 7.7";
     input {
       anyxml filter {
         description
           "This parameter specifies the portion of the system\nconfiguration "+
           "and state data to retrieve.";
         nc:get-filter-element-attributes;
       }
     }
     output {
       anyxml data {
         description
           "Copy of the running datastore subset and/or state\ndata that matched"+
           " the filter criteria (if any).\nAn empty data container indicates "+
           "that the request did not\nproduce any results.";
       }
     }
   }
   rpc close-session {
     description
       "Request graceful termination of a NETCONF session.";
     reference
       "RFC 6241, Section 7.8";
   }
   rpc kill-session {
     description
       "Force the termination of a NETCONF session.";
     reference
       "RFC 6241, Section 7.9";
     input {
       leaf session-id {
         type "session-id-type";
         mandatory "true";
         description
           "Particular session to kill.";
       }
     }
   }
   rpc commit {
     if-feature "candidate";
     description
       "Commit the candidate configuration as the device's new\ncurrent "+
       "configuration.";
     reference
       "RFC 6241, Section 8.3.4.1";
     input {
       leaf confirmed {
         if-feature "confirmed-commit";
         type "empty";
         description
           "Requests a confirmed commit.";
         reference
           "RFC 6241, Section 8.3.4.1";
       }
       leaf confirm-timeout {
         if-feature "confirmed-commit";
         type "uint32" {
           range "1..max";
         }
         units "seconds";
         default "600";
         // 10 minutes

         description
           "The timeout interval for a confirmed commit.";
         reference
           "RFC 6241, Section 8.3.4.1";
       }
       leaf persist {
         if-feature "confirmed-commit";
         type "string";
         description
           "This parameter is used to make a confirmed commit\npersistent.  A "+
           "persistent confirmed commit is not aborted\nif the NETCONF session "+
           "terminates.  The only way to abort\na persistent confirmed commit is"+
           " to let the timer expire,\nor to use the <cancel-commit> operation."+
           "\nThe value of this parameter is a token that must be given\nin the "+
           "'persist-id' parameter of <commit> or\n<cancel-commit> operations in"+
           " order to confirm or cancel\nthe persistent confirmed commit.\nThe "+
           "token should be a random string.";
         reference
           "RFC 6241, Section 8.3.4.1";
       }
       leaf persist-id {
         if-feature "confirmed-commit";
         type "string";
         description
           "This parameter is given in order to commit a persistent\nconfirmed "+
           "commit.  The value must be equal to the value\ngiven in the "+
           "'persist' parameter to the <commit> operation.\nIf it does not "+
           "match, the operation fails with an\n'invalid-value' error.";
         reference
           "RFC 6241, Section 8.3.4.1";
       }
     }
   }
   rpc discard-changes {
     if-feature "candidate";
     description
       "Revert the candidate configuration to the current\nrunning configuration"+
       ".";
     reference
       "RFC 6241, Section 8.3.4.2";
   }
   rpc cancel-commit {
     if-feature "confirmed-commit";
     description
       "This operation is used to cancel an ongoing confirmed commit.\nIf the "+
       "confirmed commit is persistent, the parameter\n'persist-id' must be "+
       "given, and it must match the value of the\n'persist' parameter.";
     reference
       "RFC 6241, Section 8.4.4.1";
     input {
       leaf persist-id {
         type "string";
         description
           "This parameter is given in order to cancel a persistent\nconfirmed "+
           "commit.  The value must be equal to the value\ngiven in the "+
           "'persist' parameter to the <commit> operation.\nIf it does not "+
           "match, the operation fails with an\n'invalid-value' error.";
       }
     }
   }
   rpc validate {
     if-feature "validate";
     description
       "Validates the contents of the specified configuration.";
     reference
       "RFC 6241, Section 8.6.4.1";
     input {
       container source {
         description
           "Particular configuration to validate.";
         choice config-source {
           mandatory "true";
           description
             "The configuration source to validate.";
           leaf candidate {
             if-feature "candidate";
             type "empty";
             description
               "The candidate configuration is the config source.";
           }
           leaf running {
             type "empty";
             description
               "The running configuration is the config source.";
           }
           leaf startup {
             if-feature "startup";
             type "empty";
             description
               "The startup configuration is the config source.";
           }
           leaf url {
             if-feature "url";
             type "inet:uri";
             description
               "The URL-based configuration is the config source.";
           }
           anyxml config {
             description
               "Inline Config content: <config> element.  Represents\nan entire "+
               "configuration datastore, not\na subset of the running datastore."+
               "";
           }
         }
       }
     }
   }
 }

/*
Copyright (C) 2021 Huawei Technologies Co., Ltd. All rights reserved.
*/

 module huawei-mpls-forward-devm-deviations-OC-NE-X8X16 {
   namespace "urn:huawei:yang:huawei-mpls-forward-devm-deviations-OC-NE-X8X16";
   prefix "mpls-forward-devm-devs-OC-NE-X8X16";
   import huawei-mpls-forward-devm {
     prefix "mpls-forward-devm";
   }
   import huawei-devm {
     prefix "devm";
   }
   import huawei-loadbalance {
     prefix "loadbalance";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-mpls-forward-devm "+
     "module.";
   revision "2021-05-07" {
     description
       "Initial revision.";
     reference
       "Huawei private.";
   }
   deviation "/loadbalance:loadbalance/mpls-forward-devm:mpls-hashpacket/mpls-fo"+
             "rward-devm:hashpacket/mpls-forward-devm:slotid" {
     deviate "replace" {
       type "leafref" {
         path "/devm:devm/devm:lpu-boards/devm:lpu-board/devm:position";
       }
     }
   }
   deviation "/loadbalance:loadbalance/mpls-forward-devm:mpls-intfmtu/mpls-forwa"+
             "rd-devm:intfmtu/mpls-forward-devm:slotid" {
     deviate "replace" {
       type "leafref" {
         path "/devm:devm/devm:lpu-boards/devm:lpu-board/devm:position";
       }
     }
   }
 }

/*
Copyright (C) 2020 Huawei Technologies Co., Ltd. All rights reserved.
*/

 module huawei-openconfig-bgp-deviations-OC-NE-X8X16 {
   yang-version "1";
   namespace "urn:huawei:yang:huawei-openconfig-bgp-deviations-OC-NE-X8X16";
   prefix "of-bgp-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "This module describes a YANG model for BGP protocol\nconfiguration.It is a"+
     " limited subset of all of the configuration\nparameters available in the "+
     "variety of vendor implementations,\nhence it is expected that it would be "+
     "augmented with vendor-\nspecific configuration data as needed. Additional "+
     "modules or\nsubmodules to handle other aspects of BGP configuration,\nincl"+
     "uding policy, VRFs, VPNs, and additional address families\nare also "+
     "expected.";
   revision "2020-10-23" {
     description
       "Initial revision.";
     reference
       "Huawei private.";
   }
 }

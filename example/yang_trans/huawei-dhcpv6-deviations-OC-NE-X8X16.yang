/*
Copyright (C) 2019 Huawei Technologies Co., Ltd. All rights reserved.
*/

 module huawei-dhcpv6-deviations-OC-NE-X8X16 {
   namespace "urn:huawei:yang:huawei-dhcpv6-deviations-OC-NE-X8X16";
   prefix "dhcpv6-devs-OC-NE-X8X16";
   import huawei-dhcpv6 {
     prefix "dhcpv6";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "Dynamic Host Configuration Protocol for IPv6.";
   revision "2019-04-29" {
     description
       "Initial revision.";
     reference
       "Huawei private.";
   }
   typedef dhcpv6-duid-deviations {
     type "enumeration" {
       enum "invalid" {
         value "0";
         description
           "-";
       }
       enum "llt" {
         value "1";
         description
           "Link-layer address plus time.";
       }
       enum "user-defined" {
         value "3";
         description
           "User-defined.";
       }
     }
     description
       "Description of dhcp6_dhcpv6Duid_type.";
   }
   deviation "/dhcpv6:dhcpv6/dhcpv6:common/dhcpv6:global/dhcpv6:duid-format" {
     deviate "replace" {
       type "dhcpv6-devs-OC-NE-X8X16:dhcpv6-duid-deviations";
     }
   }
   deviation "/ifm:ifm/ifm:interfaces/ifm:interface/dhcpv6:dhcpv6-relay-attribut"+
             "e" {
     deviate "add" {
       must "(count(destination-addresses/destination-address) + count(destinati"+
            "on-ifs/destination-if)) <= 8";
     }
   }
 }

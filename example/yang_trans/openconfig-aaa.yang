module openconfig-aaa {
   yang-version "1";
   namespace "http://openconfig.net/yang/aaa";
   prefix "oc-aaa";
   import openconfig-extensions {
     prefix "oc-ext";
   }
   include openconfig-aaa-tacacs;
   include openconfig-aaa-radius;
   organization
     "OpenConfig working group";
   contact
     "OpenConfig working group\nwww.openconfig.net";
   description
     "This module defines configuration and operational state data\nrelated to "+
     "authorization, authentication, and accounting (AAA)\nmanagement.\n\nPortio"+
     "ns of this model reuse data definitions or structure from\nRFC 7317 - A "+
     "YANG Data Model for System Management";
   oc-ext:openconfig-version "0.3.0";
   revision "2017-09-18" {
     description
       "Updated to use OpenConfig types modules";
     reference
       "0.3.0";
   }
   revision "2017-07-06" {
     description
       "Move to oc-inet types, add IETF attribution, add RADIUS\ncounters, "+
       "changed password leaf names to indicate hashed";
     reference
       "0.2.0";
   }
   revision "2017-01-29" {
     description
       "Initial public release";
     reference
       "0.1.0";
   }
 }

/*
Copyright (C) 2019-2021 Huawei Technologies Co., Ltd. All rights reserved.
*/

 module huawei-syslog {
   namespace "urn:huawei:yang:huawei-syslog";
   prefix "syslog";
   import ietf-inet-types {
     prefix "inet";
   }
   import ietf-yang-types {
     prefix "yang";
   }
   import huawei-extension {
     prefix "ext";
   }
   import huawei-network-instance {
     prefix "ni";
   }
   import huawei-ssl {
     prefix "ssl";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "System log.";
   revision "2021-05-26" {
     description
       "Add ssl-policy-name node.";
     reference
       "Huawei private.";
   }
   revision "2021-03-17" {
     description
       "Add collect-log-process and collect-log.";
     reference
       "Huawei private.";
   }
   revision "2020-07-21" {
     description
       "Add character-set node.";
     reference
       "Huawei private.";
   }
   revision "2020-07-10" {
     description
       "Add container and rpc.";
     reference
       "Huawei private.";
   }
   revision "2020-06-02" {
     description
       "Modify information of leafs.";
     reference
       "Huawei private.";
   }
   revision "2020-05-22" {
     description
       "Add the brief format of syslog host.";
     reference
       "Huawei private.";
   }
   revision "2020-02-24" {
     description
       "Add the syslog node.";
     reference
       "Huawei private.";
   }
   revision "2020-02-19" {
     description
       "Add the name and activated of syslog host.";
     reference
       "Huawei private.";
   }
   revision "2020-02-11" {
     description
       "Add the severity mask and facility mask of syslog host.";
     reference
       "Huawei private.";
   }
   revision "2020-01-20" {
     description
       "Add syslogserver.";
     reference
       "Huawei private.";
   }
   revision "2019-09-24" {
     description
       "Initial revision.";
     reference
       "Huawei private.";
   }
   typedef loghost-facility {
     type "enumeration" {
       enum "local0" {
         value "16";
         description
           "Log server local 0.";
       }
       enum "local1" {
         value "17";
         description
           "Log server local 1.";
       }
       enum "local2" {
         value "18";
         description
           "Log server local 2.";
       }
       enum "local3" {
         value "19";
         description
           "Log server local 3.";
       }
       enum "local4" {
         value "20";
         description
           "Log server local 4.";
       }
       enum "local5" {
         value "21";
         description
           "Log server local 5.";
       }
       enum "local6" {
         value "22";
         description
           "Log server local 6.";
       }
       enum "local7" {
         value "23";
         description
           "Log server local 7.";
       }
     }
     description
       "The type of log host facility.";
   }
   typedef log-level {
     type "enumeration" {
       enum "emergencies" {
         value "0";
         description
           "The log host level is emergencies.";
       }
       enum "alert" {
         value "1";
         description
           "The log host level is alert.";
       }
       enum "critical" {
         value "2";
         description
           "The log host level is critical.";
       }
       enum "error" {
         value "3";
         description
           "The log host level is error.";
       }
       enum "warning" {
         value "4";
         description
           "The log host level is warning.";
       }
       enum "notification" {
         value "5";
         description
           "The log host level is notification.";
       }
       enum "informational" {
         value "6";
         description
           "The log host level is informational.";
       }
       enum "debugging" {
         value "7";
         description
           "The log host level is debugging.";
       }
     }
     description
       "The type of log level.";
   }
   typedef log-type {
     type "enumeration" {
       enum "eventlog" {
         value "2";
         description
           "The event log.";
       }
       enum "operlog" {
         value "1";
         description
           "The operation log.";
       }
       enum "alarmlog" {
         value "5";
         description
           "The alarm log.";
       }
       enum "diaglog" {
         value "4";
         description
           "The diagnose log.";
       }
       enum "notificationlog" {
         value "10";
         description
           "The notification Log.";
       }
       enum "maintainlog" {
         value "11";
         description
           "The maintain Log.";
       }
       enum "servicelog" {
         value "18";
         description
           "The service log.";
       }
     }
     description
       "The log type.";
   }
   typedef address-family-type {
     type "enumeration" {
       enum "ipv4" {
         value "1";
         description
           "The address type is IPv4.";
       }
       enum "ipv6" {
         value "2";
         description
           "The address type is IPv6.";
       }
     }
     description
       "The type of IP address.";
   }
   typedef timestamp {
     type "enumeration" {
       enum "date-boot" {
         value "11";
         description
           "Time elapsed since the system started. It is a relative time "+
           "period.";
       }
       enum "date-second" {
         value "12";
         description
           "Date format with second precision.";
       }
       enum "date-tenthsecond" {
         value "13";
         description
           "Date format with tenth-second precision.";
       }
       enum "date-millisecond" {
         value "14";
         description
           "Date format with millisecond precision.";
       }
       enum "shortdate-second" {
         value "15";
         description
           "Short date format second precision.";
       }
       enum "shortdate-tenthsecond" {
         value "16";
         description
           "Short date format with tenth-second precision.";
       }
       enum "shortdate-millisecond" {
         value "17";
         description
           "Short date format with millisecond precision.";
       }
       enum "formatdate-second" {
         value "18";
         description
           "Format date format with second precision.";
       }
       enum "formatdate-tenthsecond" {
         value "19";
         description
           "Format date format with tenth-second precision.";
       }
       enum "formatdate-millisecond" {
         value "20";
         description
           "Format date format with millisecond precision.";
       }
     }
     description
       "The type of time stamp.";
   }
   typedef timestamp-format {
     type "enumeration" {
       enum "UTC" {
         value "0";
         description
           "UTC format.";
       }
       enum "localtime" {
         value "1";
         description
           "Local time format.";
       }
     }
     description
       "The time stamp format.";
   }
   typedef logfile-type {
     type "enumeration" {
       enum "log" {
         value "1";
         description
           "Log logfile.";
       }
       enum "security" {
         value "3";
         description
           "Security logfile.";
       }
       enum "operation" {
         value "4";
         description
           "Operation logfile.";
       }
       enum "debug" {
         value "6";
         description
           "Debug logfile.";
       }
     }
     description
       "The type of log.";
   }
   typedef transport-mode-type {
     type "enumeration" {
       enum "udp" {
         value "2";
         description
           "UDP transport mode.";
       }
       enum "tcp" {
         value "1";
         description
           "TCP transport mode.";
       }
     }
     description
       "The type of transport mode.";
   }
   typedef save-log-type {
     type "enumeration" {
       enum "log" {
         value "0";
         description
           "Common logs.";
       }
       enum "diaglog" {
         value "1";
         description
           "Diagnoseic logs.";
       }
     }
     description
       "The saved log type.";
   }
   typedef prefix-file-type {
     type "enumeration" {
       enum "debug" {
         value "6";
         description
           "Debug logfile.";
       }
     }
     description
       "The type of log.";
   }
   ext:task-name "log";
   container syslog {
     description
       "System log.";
     container servers {
       description
         "List of syslog servers.";
       list server {
         key "ip-type ipaddress is-default-vpn vrf-name";
         max-elements "8";
         description
           "Configure attributes of log server.";
         leaf ip-type {
           type "address-family-type";
           description
             "Log server address type, IPv4 or IPv6.";
         }
         leaf ipaddress {
           type "inet:ip-address-no-zone";
           description
             "Log server address, IPv4 or IPv6 type.";
         }
         leaf is-default-vpn {
           type "boolean";
           description
             "Enable/disable the default VPN.";
         }
         leaf vrf-name {
           type "leafref" {
             path "/ni:network-instance/ni:instances/ni:instance/ni:name";
           }
           must "not(../is-default-vpn='true') or (../is-default-vpn='true' and "+
                "../vrf-name='_public_')";
           description
             "VPN name on a log server.";
         }
         leaf level {
           type "log-level";
           default "debugging";
           description
             "Level of logs saved on a log server.";
           ext:support-filter "true";
         }
         leaf port {
           type "uint32" {
             range "1..65535";
           }
           ext:dynamic-default;
           description
             "Number of a port recving logs.";
           ext:support-filter "true";
         }
         leaf facility {
           type "loghost-facility";
           default "local7";
           description
             "Log record tool.";
           ext:support-filter "true";
         }
         leaf channel-id {
           type "leafref" {
             path "/syslog:syslog/syslog:info-center-channels/syslog:info-center"+
                  "-channel/syslog:channel-id";
           }
           default "2";
           description
             "Channel number.";
           ext:support-filter "true";
         }
         leaf channel-name {
           type "string" {
             length "1..30";
           }
           default "loghost";
           config "false";
           description
             "Channel name.";
         }
         leaf timestamp {
           type "timestamp-format";
           default "UTC";
           description
             "Log server timestamp.";
           ext:support-filter "true";
         }
         leaf transport-mode {
           type "transport-mode-type";
           default "udp";
           description
             "Transport mode.";
           ext:support-filter "true";
         }
         leaf ssl-policy-name {
           type "leafref" {
             path "/ssl:ssl/ssl:ssl-policys/ssl:ssl-policy/ssl:policy-name";
           }
           must "../transport-mode='tcp'";
           description
             "SSL policy name.";
         }
         leaf source-ip {
           ext:support-filter "true";
           type "inet:ip-address-no-zone";
           description
             "Syslog source IP address.";
         }
         leaf dns-identifier-name {
           type "string" {
             length "1..255";
           }
           must "../transport-mode='tcp' and ../ssl-policy-name";
           description
             "DNS Identifier Name.";
         }
         leaf is-security-only {
           type "boolean";
           must "../is-security-only='false' or (../is-security-only='true' and "+
                "../ssl-policy-name)";
           default "false";
           description
             "Enable/disable security log server.";
         }
       }
     }
     container global-parameter {
       description
         "Configure global parameter.";
       leaf info-center-enable {
         type "boolean";
         default "true";
         description
           "Enable/disable the info-center function.";
       }
       leaf buffer-size {
         type "int32" {
           range "0..102400";
         }
         default "512";
         description
           "Size of a log buffer, the maximum value is configured by the PAF.";
       }
       leaf suppress-enable {
         type "boolean";
         default "true";
         description
           "Enable/disable suppression function of duplicate logs.";
       }
       leaf log-timestamp {
         type "timestamp";
         default "date-second";
         description
           "Timestamp format of log information.";
       }
       leaf trap-timestamp {
         type "timestamp";
         default "date-second";
         description
           "Timestamp format of alarm information.";
       }
       leaf debug-timestamp {
         type "timestamp";
         default "date-millisecond";
         description
           "Timestamp type of debugging information.";
       }
       leaf interface-name {
         type "leafref" {
           path "/ifm:ifm/ifm:interfaces/ifm:interface/ifm:name";
         }
         description
           "Name of a log host interface sending logs.";
       }
       leaf logbuffer-enable {
         type "boolean";
         default "true";
         description
           "Enable/disable log buffer to output information.";
       }
       leaf trapbuffer-enable {
         type "boolean";
         default "true";
         description
           "Enable/disable trap buffer to output information.";
       }
       leaf trapbuffer-size {
         type "int32" {
           range "0..1024";
         }
         default "256";
         description
           "Size of a trap buffer.";
       }
       leaf packet-priority {
         type "int32" {
           range "0..7";
         }
         default "0";
         description
           "Set the priority of the syslog packet.";
       }
       leaf source-port {
         type "uint32" {
           range "1025..65535";
         }
         default "38514";
         description
           "Port of the loghost.";
       }
       leaf log-none-timezone {
         type "boolean";
         default "false";
         description
           "Enable/disable log Timestamp Without Timezone.";
       }
       leaf trap-none-timezone {
         type "boolean";
         default "false";
         description
           "Enable/disable trap Timestamp Without Timezone.";
       }
       leaf debug-none-timezone {
         type "boolean";
         default "false";
         description
           "Enable/disable debug Timestamp Without Timezone.";
       }
       leaf delay-suppress-enable {
         type "boolean";
         default "true";
         description
           "Enable/disable event delay suppress is enabled.";
       }
       leaf event-logging-all {
         type "boolean";
         default "false";
         description
           "Enable/disable logging flag of global event.";
       }
     }
     container info-center-channels {
       description
         "List of Channel.";
       list info-center-channel {
         key "channel-id";
         max-elements "10";
         description
           "Configure info center channel.";
         ext:generated-by "system";
         ext:operation-exclude "create";
         leaf channel-id {
           type "uint32" {
             range "0..9";
           }
           description
             "Number for channel.";
         }
         leaf channel-default-name {
           type "string" {
             length "1..30";
           }
           config "false";
           description
             "Info-center channel default name.";
         }
         leaf channel-name {
           type "string" {
             length "1..30";
             pattern "[a-zA-Z][a-zA-Z0-9]*";
           }
           ext:dynamic-default;
           description
             "Channel name.";
         }
       }
     }
     container info-center-sources {
       description
         "List of rules in channel for outputting information.";
       list info-center-source {
         key "module-name channel-id";
         description
           "Configure rule in channel for outputting information.";
         ext:generated-by "system" {
           ext:can-be-deleted;
         }
         leaf module-name {
           type "string" {
             length "1..31";
             pattern "[^A-Z]*";
           }
           ext:case-sensitivity "lower-only";
           description
             "Module name of the rule.";
         }
         leaf channel-id {
           type "leafref" {
             path "/syslog:syslog/syslog:info-center-channels/syslog:info-center"+
                  "-channel/syslog:channel-id";
           }
           description
             "Number of a channel.";
         }
         leaf channel-name {
           type "string" {
             length "1..30";
           }
           config "false";
           description
             "Name of a channel.";
         }
         leaf enable-log {
           type "boolean";
           ext:dynamic-default;
           description
             "Enable/disable the log output function.";
         }
         leaf enable-log-level {
           type "log-level";
           ext:dynamic-default;
           description
             "Log level permitted to output.";
         }
         leaf enable-trap {
           type "boolean";
           ext:dynamic-default;
           description
             "Enable/disable the alarm output function.";
         }
         leaf enable-trap-level {
           type "log-level";
           default "debugging";
           description
             "Trap level permitted to output.";
         }
         leaf enable-debug {
           type "boolean";
           ext:dynamic-default;
           description
             "Enable/disable the debug output function.";
         }
         leaf enable-debug-level {
           type "log-level";
           default "debugging";
           description
             "Debug level permitted to output.";
         }
       }
     }
     container log-switch-list {
       description
         "Configure the log switch.";
       list log-switch {
         key "feature-name log-name";
         max-elements "65535";
         description
           "Configure log switch.";
         ext:generated-by "system";
         ext:operation-exclude "create";
         leaf feature-name {
           type "string" {
             length "1..31";
           }
           description
             "Feature name of a log.";
         }
         leaf log-name {
           type "string" {
             length "1..63";
           }
           description
             "Log name.";
         }
         leaf log-level {
           type "log-level";
           ext:dynamic-default;
           description
             "Log level.";
         }
         leaf security-log-flag {
           type "boolean";
           config "false";
           description
             "Enable/disable flag of security log.";
         }
         leaf log-type {
           type "log-type";
           config "false";
           description
             "Log Type.";
         }
       }
     }
     container info-center-filters {
       description
         "List of info-center filter.";
       list info-center-filter {
         key "feature-name filter-log-name";
         max-elements "65535";
         description
           "Configure filter item.";
         leaf feature-name {
           type "leafref" {
             path "/syslog:syslog/syslog:log-switch-list/syslog:log-switch/syslo"+
                  "g:feature-name";
           }
           description
             "Feature name of the filtered log.";
         }
         leaf filter-log-name {
           type "leafref" {
             path "/syslog:syslog/syslog:log-switch-list/syslog:log-switch/syslo"+
                  "g:log-name";
           }
           description
             "Name of the filtered log.";
         }
       }
     }
     container domain-servers {
       description
         "List of domain syslog servers.";
       list domain-server {
         key "server-domain is-default-vpn vrf-name";
         max-elements "8";
         description
           "Configure the domain log server that receives logs.";
         leaf server-domain {
           type "string" {
             length "1..255";
           }
           description
             "Log server domain address.";
         }
         leaf is-default-vpn {
           type "boolean";
           description
             "Enable/disable the default VPN.";
         }
         leaf vrf-name {
           type "leafref" {
             path "/ni:network-instance/ni:instances/ni:instance/ni:name";
           }
           must "not(../is-default-vpn='true') or (../is-default-vpn='true' and "+
                "../vrf-name='_public_')";
           description
             "VPN name on a log server.";
         }
         leaf level {
           type "log-level";
           default "debugging";
           description
             "Level of logs saved on a log server.";
         }
         leaf server-port {
           type "uint32" {
             range "1..65535";
           }
           default "514";
           description
             "Number of a port recving logs.";
         }
         leaf facility {
           type "loghost-facility";
           default "local7";
           description
             "Log record tool.";
         }
         leaf channel-id {
           type "leafref" {
             path "/syslog:syslog/syslog:info-center-channels/syslog:info-center"+
                  "-channel/syslog:channel-id";
           }
           default "2";
           description
             "Channel number.";
         }
         leaf channel-name {
           type "string" {
             length "1..30";
           }
           default "loghost";
           config "false";
           description
             "Channel name.";
         }
         leaf timestamp {
           type "timestamp-format";
           default "UTC";
           description
             "Log server timestamp.";
         }
         leaf transport-mode {
           type "transport-mode-type";
           default "udp";
           description
             "Transport mode.";
         }
         leaf ssl-policy-name {
           type "leafref" {
             path "/ssl:ssl/ssl:ssl-policys/ssl:ssl-policy/ssl:policy-name";
           }
           must "../transport-mode='tcp'";
           description
             "SSL policy name.";
         }
         leaf source-ip {
           ext:support-filter "true";
           type "inet:ipv4-address-no-zone";
           description
             "Syslog source IP address.";
         }
         leaf is-security-only {
           type "boolean";
           must "../is-security-only='false' or (../is-security-only='true' and "+
                "../ssl-policy-name)";
           default "false";
           description
             "Enable/disable Syslog support security log.";
         }
         leaf dns-identifier-name {
           type "string" {
             length "1..255";
           }
           must "../transport-mode='tcp' and ../ssl-policy-name";
           description
             "DNS Identifier Name.";
         }
       }
     }
     container logfiles {
       description
         "List of log file info.";
       list logfile {
         key "logfile-type";
         max-elements "4";
         description
           "Specify Log file info.";
         ext:generated-by "system";
         ext:operation-exclude "create|delete";
         leaf logfile-type {
           type "logfile-type";
           description
             "Log file type.";
         }
         leaf max-file-num {
           type "uint32" {
             range "1..500";
           }
           ext:dynamic-default;
           must "(../logfile-type='debug' and (../max-file-num>=1 and ../max-fil"+
                "e-num<=50)) or (../logfile-type!='debug' and (../max-file-num>="+
                "3 and ../max-file-num<=500))";
           description
             "Maximum number of log files of the same type.";
         }
         leaf max-file-size {
           type "uint32" {
             range "1..32";
           }
           units "MB";
           ext:dynamic-default;
           must "(../logfile-type='debug' and ../max-file-size='8') or "+
                "((../logfile-type='security' or ../logfile-type='operation') "+
                "and (../max-file-size>=1 and ../max-file-size<=4))or (../logfil"+
                "e-type='log' and (../max-file-size='4' or ../max-file-size='8' "+
                "or ../max-file-size='16' or ../max-file-size='32'))";
           description
             "Maximum size (in MB) of a log file. The value range for log files "+
             "is [4, 8, 16, 32], for security files is [1~4], and for operation "+
             "files is [1~4].";
         }
       }
     }
     container direction-channels {
       description
         "List of mappings of output directions and channels of the information "+
         "center.";
       list direction-channel {
         key "output-direction";
         max-elements "7";
         description
           "Specify the relation of direction and channel.";
         ext:generated-by "system";
         ext:operation-exclude "create";
         leaf output-direction {
           type "string" {
             length "1..30";
           }
           description
             "Direction of information output.";
         }
         leaf default-channel-id {
           type "uint32" {
             range "0..9";
           }
           config "false";
           description
             "Number of the default channel.";
         }
         leaf channel-id {
           type "leafref" {
             path "/syslog:syslog/syslog:info-center-channels/syslog:info-center"+
                  "-channel/syslog:channel-id";
           }
           ext:dynamic-default;
           description
             "Number of a configured channel.";
         }
         leaf channel-name {
           type "string" {
             length "1..30";
           }
           config "false";
           description
             "Name of a configured channel.";
         }
       }
     }
     container info-center-statistics {
       config "false";
       description
         "List of info-center statistics.";
       list info-center-statistic {
         key "module-name";
         description
           "Statistics of info-center item.";
         leaf module-name {
           type "string" {
             length "1..31";
           }
           description
             "Module name of the log.";
         }
         leaf receive-log {
           type "uint32";
           description
             "Number of received logs.";
         }
         leaf drop-log {
           type "uint32";
           description
             "Number of dropped logs.";
         }
         leaf receive-diaglog {
           type "uint32";
           description
             "Number of received diagnostic logs.";
         }
         leaf drop-diaglog {
           type "uint32";
           description
             "Number of dropped diagnostic logs.";
         }
         leaf receive-eventtrap {
           type "uint32";
           description
             "Number of received event traps.";
         }
         leaf drop-eventtrap {
           type "uint32";
           description
             "Number of dropped event traps.";
         }
         leaf receive-debug {
           type "uint32";
           description
             "Number of received debugging logs.";
         }
         leaf drop-debug {
           type "uint32";
           description
             "Number of dropped debugging logs.";
         }
       }
     }
     container info-center-buffers {
       config "false";
       description
         "List of the buffer statistics.";
       list info-center-buffer {
         key "buffer-name";
         max-elements "2";
         description
           "Display buffer statistics.";
         leaf buffer-name {
           type "string" {
             length "1..31";
           }
           description
             "Buffer name.";
         }
         leaf enable-flag {
           type "boolean";
           default "true";
           description
             "Enable/disable Buffer enable state.";
         }
         leaf max-buffer-size {
           type "uint32" {
             range "1..10240";
           }
           units "Byte";
           description
             "Maximum buffer size.";
         }
         leaf cur-buffer-size {
           type "uint32" {
             range "1..10240";
           }
           units "Byte";
           description
             "Configured buffer size.";
         }
         leaf current-message {
           type "uint32";
           description
             "Number of existing messages in the buffer.";
         }
         leaf dropped-message {
           type "uint32";
           description
             "Number of dropped messages in the buffer.";
         }
         leaf overwrite-message {
           type "uint32";
           description
             "Number of overwritten messages in the buffer.";
         }
         leaf channel-id {
           type "uint32" {
             range "0..9";
           }
           default "0";
           description
             "ID of channel bind to the buffer.";
         }
         leaf channel-name {
           type "string" {
             length "1..30";
           }
           description
             "Name of channel bind to the buffer.";
         }
       }
     }
     container modules {
       config "false";
       description
         "List of module name information.";
       list module {
         key "module-name";
         description
           "Operational data of module name information item.";
         leaf module-name {
           type "string" {
             length "1..31";
           }
           description
             "Module name.";
         }
       }
     }
     container logbuffers {
       config "false";
       description
         "List of of log buffer.";
       list logbuffer {
         key "sequence";
         description
           "Statistics of log buffer item.";
         leaf sequence {
           type "int32" {
             range "1..102400";
           }
           description
             "Sequence number of a queried log.";
         }
         leaf starttime {
           type "yang:date-and-time";
           description
             "Query start time. The valid value range is after 1970-01-01.";
           ext:support-filter "true";
         }
         leaf endtime {
           type "yang:date-and-time";
           description
             "Query end time. The valid value range is after 1970-01-01.";
           ext:support-filter "true";
         }
         leaf level {
           type "log-level";
           description
             "Level of queried logs.";
           ext:support-filter "true";
         }
         leaf log-content {
           type "string" {
             length "0..1200";
           }
           description
             "Content of queried logs.";
         }
       }
     }
     container trapbuffers {
       config "false";
       description
         "List of trap buffer table.";
       list trapbuffer {
         key "sequence";
         description
           "Statistics of trap buffer item.";
         leaf sequence {
           type "int32" {
             range "1..1024";
           }
           description
             "Sequence number of a queried trap.";
         }
         leaf trap-content {
           type "string" {
             length "0..1200";
           }
           description
             "Content of query trap.";
         }
       }
     }
     container securitybuffers {
       config "false";
       description
         "List of security of a log buffer.";
       list securitybuffer {
         key "sequence";
         description
           "Operational data of the security of a log buffer item.";
         leaf sequence {
           type "int32" {
             range "1..102400";
           }
           description
             "Sequence number of a queried log.";
         }
         leaf starttime {
           type "yang:date-and-time";
           description
             "Query start time. The valid value range is after 1970-01-01.";
           ext:support-filter "true";
         }
         leaf endtime {
           type "yang:date-and-time";
           description
             "Query end time. The valid value range is after 1970-01-01.";
           ext:support-filter "true";
         }
         leaf level {
           type "log-level";
           description
             "Level of queried logs.";
           ext:support-filter "true";
         }
         leaf log-content {
           type "string" {
             length "0..1200";
           }
           description
             "Content of queried logs.";
         }
       }
     }
     container logfile-prefixs {
       description
         "List of log file prefix.";
       list logfile-prefix {
         key "type name";
         max-elements "1";
         description
           "Specify Log file prefixs.";
         leaf type {
           type "prefix-file-type";
           description
             "Log file type.";
         }
         leaf name {
           type "string" {
             length "1..16";
             pattern "[a-zA-Z0-9]*";
           }
           description
             "File name.";
         }
       }
     }
   }
   rpc save-logfile {
     description
       "Save logs to file.";
     input {
       leaf log-type {
         type "save-log-type";
         mandatory "true";
         description
           "Log type.";
       }
     }
   }
 }

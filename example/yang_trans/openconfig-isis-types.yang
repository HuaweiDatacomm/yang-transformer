module openconfig-isis-types {
   yang-version "1";
   namespace "http://openconfig.net/yang/isis-types";
   prefix "oc-isis-types";
   import openconfig-extensions {
     prefix "oc-ext";
   }
   organization
     "OpenConfig working group";
   contact
     "OpenConfig working group\nwww.openconfig.net";
   description
     "This module contains general data definitions for use in ISIS YANG\nmodel."+
     "";
   oc-ext:openconfig-version "0.4.2";
   revision "2018-11-21" {
     description
       "Add OpenConfig module metadata extensions.";
     reference
       "0.4.2";
   }
   revision "2018-11-21" {
     description
       "Add OpenConfig module metadata extensions.";
     reference
       "0.4.1";
   }
   revision "2018-05-14" {
     description
       "Update LSDB model to correct Extended IS reach TLV\nbug. This change is "+
       "backwards incompatible due to\nadding an additional level of hierarchy "+
       "to support\nmultiple instances of the TLV.";
     reference
       "0.4.0";
   }
   revision "2017-07-26" {
     description
       "Update LSDB and fix bugs.";
     reference
       "0.3.2";
   }
   revision "2017-05-15" {
     description
       "Refactor LSDB.";
     reference
       "0.3.0";
   }
   revision "2017-01-13" {
     description
       "Remove top-level /isis container";
     reference
       "0.2.1";
   }
   revision "2016-12-15" {
     description
       "Add segment routing to IS-IS module";
     reference
       "0.2.0";
   }
   revision "2016-10-18" {
     description
       "Initial revision of IS-IS models.";
     reference
       "0.1.0";
   }
   oc-ext:regexp-posix;
   oc-ext:catalog-organization "openconfig";
   oc-ext:origin "openconfig";
   identity OVERLOAD_RESET_TRIGGER_TYPE {
     description
       "Base identify type for triggers that reset Overload Bit";
   }
   identity WAIT_FOR_BGP {
     base "OVERLOAD_RESET_TRIGGER_TYPE";
     description
       "Base identity type for resetting Overload Bit when BGP has converged. ";
   }
   identity WAIT_FOR_SYSTEM {
     base "OVERLOAD_RESET_TRIGGER_TYPE";
     description
       "Base identity type for resetting Overload Bit when system resources "+
       "have\nbeen restored. ";
   }
   identity MT_TYPE {
     description
       "Base identify type for multi-topology";
   }
   identity SAFI_TYPE {
     description
       "Base identify type for SAFI";
   }
   identity AFI_TYPE {
     description
       "Base identify type for AFI";
   }
   identity AFI_SAFI_TYPE {
     description
       "Base identify type for AFI/SAFI";
   }
   identity IPV4_UNICAST {
     base "AFI_SAFI_TYPE";
     description
       "Base identify type for IPv4 Unicast address family";
   }
   identity IPV6_MULTICAST {
     base "AFI_SAFI_TYPE";
     description
       "Base identify type for IPv6 multicast address family";
   }
   identity IPV4_MULTICAST {
     base "AFI_SAFI_TYPE";
     description
       "Base identify type for IPv4 multicast address family";
   }
   identity IPV6_UNICAST {
     base "AFI_SAFI_TYPE";
     description
       "Base identify type for IPv6 unicast address family";
   }
   identity UNICAST {
     base "SAFI_TYPE";
     description
       "Base identify type for IPv4 Unicast address family";
   }
   identity MULTICAST {
     base "SAFI_TYPE";
     description
       "Base identify type for IPv6 multicast address family";
   }
   identity IPV4 {
     base "AFI_TYPE";
     description
       "Base identify type for IPv4 address family";
   }
   identity IPV6 {
     base "AFI_TYPE";
     description
       "Base identify type for IPv6 address family";
   }
 }

/*
Copyright (C) 2019 Huawei Technologies Co., Ltd. All rights reserved.
*/

 module huawei-rsvp-interface-deviations-OC-NE-X8X16 {
   namespace "urn:huawei:yang:huawei-rsvp-interface-deviations-OC-NE-X8X16";
   prefix "rsvp-interface-devs-OC-NE-X8X16";
   import huawei-network-instance {
     prefix "ni";
   }
   import huawei-mpls {
     prefix "mpls";
   }
   import huawei-mpls-te {
     prefix "mpls-te";
   }
   import huawei-rsvp-interface {
     prefix "rsvp-interface";
   }
   import huawei-ifm {
     prefix "ifm";
   }
   import huawei-tunnel-management {
     prefix "tnlm";
   }
   import huawei-gre {
     prefix "gre";
   }
   import huawei-ip {
     prefix "ip";
   }
   import huawei-if-ip {
     prefix "if-ip";
   }
   organization
     "Huawei Technologies Co., Ltd.";
   contact
     "Huawei Industrial Base\nBantian, Longgang\nShenzhen 518129\nPeople's "+
     "Republic of China\nWebsite: http://www.huawei.com\nEmail: support@huawei.c"+
     "om";
   description
     "Specifies the multi-protocol label switching protocol.";
   revision "2019-03-27" {
     description
       "Init revision.";
     reference
       "Huawei private.";
   }
   deviation "/ni:network-instance/ni:instances/ni:instance/mpls:mpls/mpls-te:te"+
             "/rsvp-interface:rsvp-interfaces/rsvp-interface:rsvp-interface" {
     deviate "add" {
       must "not(/ifm:ifm/ifm:interfaces/ifm:interface[ifm:name = current()/name"+
            "]/tnlm:tunnel-protocol/gre:gre-tunnel) or not(/ifm:ifm/ifm:interfac"+
            "es/ifm:interface[ifm:name = current()/name]/ip:ipv4/ip:unnumbered-a"+
            "ddress/ip:unnumbered-if-name) or not(/ni:network-instance/ni:instan"+
            "ces/ni:instance/if-ip:ipv4-ifs/if-ip:ipv4-if[if-ip:name = "+
            "current()/name])";
     }
   }
 }

module ietf-hardware {
   yang-version "1.1";
   namespace "urn:ietf:params:xml:ns:yang:ietf-hardware";
   prefix "hw";
   import ietf-inet-types {
     prefix "inet";
   }
   import ietf-yang-types {
     prefix "yang";
   }
   import iana-hardware {
     prefix "ianahw";
   }
   organization
     "IETF NETMOD (Network Modeling) Working Group";
   contact
     "WG Web:   <https://datatracker.ietf.org/wg/netmod/>\nWG List:  <mailto:net"+
     "mod@ietf.org>\n\nEditor:   Andy Bierman\n          <mailto:andy@yumaworks."+
     "com>\n\nEditor:   Martin Bjorklund\n          <mailto:mbj@tail-f.com>\n\nE"+
     "ditor:   Jie Dong\n          <mailto:jie.dong@huawei.com>\n\nEditor:   Dan"+
     " Romascanu\n          <mailto:dromasca@gmail.com>";
   description
     "This module contains a collection of YANG definitions for\nmanaging "+
     "hardware.\n\nThis data model is designed for the Network Management "+
     "Datastore\nArchitecture (NMDA) defined in RFC 8342.\nCopyright (c) 2018 "+
     "IETF Trust and the persons identified as\nauthors of the code.  All rights"+
     " reserved.\n\nRedistribution and use in source and binary forms, with "+
     "or\nwithout modification, is permitted pursuant to, and subject\nto the "+
     "license terms contained in, the Simplified BSD License\nset forth in "+
     "Section 4.c of the IETF Trust's Legal Provisions\nRelating to IETF "+
     "Documents\n(https://trustee.ietf.org/license-info).\n\nThis version of "+
     "this YANG module is part of RFC 8348; see\nthe RFC itself for full legal "+
     "notices.";
   revision "2018-03-13" {
     description
       "Initial revision.";
     reference
       "RFC 8348: A YANG Data Model for Hardware Management";
   }
   feature entity-mib {
     description
       "This feature indicates that the device implements\nthe ENTITY-MIB.";
     reference
       "RFC 6933: Entity MIB (Version 4)";
   }
   feature hardware-state {
     description
       "Indicates that ENTITY-STATE-MIB objects are supported";
     reference
       "RFC 4268: Entity State MIB";
   }
   feature hardware-sensor {
     description
       "Indicates that ENTITY-SENSOR-MIB objects are supported";
     reference
       "RFC 3433: Entity Sensor Management Information Base";
   }
   typedef admin-state {
     type "enumeration" {
       enum "unknown" {
         value "1";
         description
           "The resource is unable to report administrative state.";
       }
       enum "locked" {
         value "2";
         description
           "The resource is administratively prohibited from use.";
       }
       enum "shutting-down" {
         value "3";
         description
           "The resource usage is administratively limited to current\ninstances"+
           " of use.";
       }
       enum "unlocked" {
         value "4";
         description
           "The resource is not administratively prohibited from\nuse.";
       }
     }
     description
       "Represents the various possible administrative states.";
     reference
       "RFC 4268: Entity State MIB - EntityAdminState";
   }
   typedef oper-state {
     type "enumeration" {
       enum "unknown" {
         value "1";
         description
           "The resource is unable to report its operational state.";
       }
       enum "disabled" {
         value "2";
         description
           "The resource is totally inoperable.";
       }
       enum "enabled" {
         value "3";
         description
           "The resource is partially or fully operable.";
       }
       enum "testing" {
         value "4";
         description
           "The resource is currently being tested and cannot\ntherefore report "+
           "whether or not it is operational.";
       }
     }
     description
       "Represents the possible values of operational states.";
     reference
       "RFC 4268: Entity State MIB - EntityOperState";
   }
   typedef alarm-state {
     type "bits" {
       bit unknown {
         position "0";
         description
           "The resource is unable to report alarm state.";
       }
       bit under-repair {
         position "1";
         description
           "The resource is currently being repaired, which, depending\non the "+
           "implementation, may make the other values in this\nbit string not "+
           "meaningful.";
       }
       bit critical {
         position "2";
         description
           "One or more critical alarms are active against the\nresource.";
       }
       bit major {
         position "3";
         description
           "One or more major alarms are active against the\nresource.";
       }
       bit minor {
         position "4";
         description
           "One or more minor alarms are active against the\nresource.";
       }
       bit warning {
         position "5";
         description
           "One or more warning alarms are active against the\nresource.";
       }
       bit indeterminate {
         position "6";
         description
           "One or more alarms of whose perceived severity cannot be\ndetermined"+
           " are active against this resource.";
       }
     }
     description
       "Represents the possible values of alarm states.  An alarm is a\npersiste"+
       "nt indication of an error or warning condition.\n\nWhen no bits of this "+
       "attribute are set, then no active alarms\nare known against this "+
       "component and it is not under repair.";
     reference
       "RFC 4268: Entity State MIB - EntityAlarmStatus";
   }
   typedef standby-state {
     type "enumeration" {
       enum "unknown" {
         value "1";
         description
           "The resource is unable to report standby state.";
       }
       enum "hot-standby" {
         value "2";
         description
           "The resource is not providing service, but it will be\nimmediately "+
           "able to take over the role of the resource to\nbe backed up, without"+
           " the need for initialization\nactivity, and will contain the same "+
           "information as the\nresource to be backed up.";
       }
       enum "cold-standby" {
         value "3";
         description
           "The resource is to back up another resource, but it will\nnot be "+
           "immediately able to take over the role of a\nresource to be backed "+
           "up and will require some\ninitialization activity.";
       }
       enum "providing-service" {
         value "4";
         description
           "The resource is providing service.";
       }
     }
     description
       "Represents the possible values of standby states.";
     reference
       "RFC 4268: Entity State MIB - EntityStandbyStatus";
   }
   container hardware {
     description
       "Data nodes representing components.\n\nIf the server supports configurat"+
       "ion of hardware components,\nthen this data model is instantiated in the"+
       " configuration\ndatastores supported by the server.  The leaf-list "+
       "'datastore'\nfor the module 'ietf-hardware' in the YANG library "+
       "provides\nthis information.";
     leaf last-change {
       type "yang:date-and-time";
       config "false";
       description
         "The time the '/hardware/component' list changed in the\noperational "+
         "state.";
     }
     list component {
       key "name";
       description
         "List of components.\n\nWhen the server detects a new hardware "+
         "component, it\ninitializes a list entry in the operational state.\n\nI"+
         "f the server does not support configuration of hardware\ncomponents, "+
         "list entries in the operational state are\ninitialized with values for"+
         " all nodes as detected by the\nimplementation.\n\nOtherwise, this "+
         "procedure is followed:\n\n  1. If there is an entry in the '/hardware/"+
         "component' list\n     in the intended configuration with values for "+
         "the nodes\n     'class', 'parent', and 'parent-rel-pos' that are "+
         "equal\n     to the detected values, then the list entry in the\n     "+
         "operational state is initialized with the configured\n     values, "+
         "including the 'name'.\n\n  2. Otherwise (i.e., there is no matching "+
         "configuration\n     entry), the list entry in the operational state "+
         "is\n     initialized with values for all nodes as detected by\n     "+
         "the implementation.\n\nIf the '/hardware/component' list in the "+
         "intended\nconfiguration is modified, then the system MUST behave as "+
         "if\nit re-initializes itself and follow the procedure in (1).";
       reference
         "RFC 6933: Entity MIB (Version 4) - entPhysicalEntry";
       leaf name {
         type "string";
         description
           "The name assigned to this component.\n\nThis name is not required to"+
           " be the same as\nentPhysicalName.";
         config "false";
       }
       leaf class {
         type "identityref" {
           base "ianahw:hardware-class";
         }
         mandatory "true";
         description
           "An indication of the general hardware type of the\ncomponent.";
         reference
           "RFC 6933: Entity MIB (Version 4) - entPhysicalClass";
       }
       leaf physical-index {
         if-feature "entity-mib";
         type "int32" {
           range "1..2147483647";
         }
         config "false";
         description
           "The entPhysicalIndex for the entPhysicalEntry represented\nby this "+
           "list entry.";
         reference
           "RFC 6933: Entity MIB (Version 4) - entPhysicalIndex";
       }
       leaf description {
         type "string";
         config "false";
         description
           "A textual description of the component.  This node should\ncontain a"+
           " string that identifies the manufacturer's name\nfor the component "+
           "and should be set to a distinct value\nfor each version or model of "+
           "the component.";
         reference
           "RFC 6933: Entity MIB (Version 4) - entPhysicalDescr";
       }
       leaf parent {
         type "leafref" {
           path "../../component/name";
           require-instance "false";
         }
         description
           "The name of the component that physically contains this\ncomponent."+
           "\n\nIf this leaf is not instantiated, it indicates that this\ncompon"+
           "ent is not contained in any other component.\n\nIn the event that a "+
           "physical component is contained by\nmore than one physical component"+
           " (e.g., double-wide\nmodules), this node contains the name of one of"+
           " these\ncomponents.  An implementation MUST use the same name\nevery"+
           " time this node is instantiated.";
         reference
           "RFC 6933: Entity MIB (Version 4) - entPhysicalContainedIn";
       }
       leaf parent-rel-pos {
         type "int32" {
           range "0 .. 2147483647";
         }
         description
           "An indication of the relative position of this child\ncomponent "+
           "among all its sibling components.  Sibling\ncomponents are defined "+
           "as components that:\n\n  o share the same value of the 'parent' node"+
           " and\n\n  o share a common base identity for the 'class' node.\n\nNo"+
           "te that the last rule gives implementations flexibility\nin how "+
           "components are numbered.  For example, some\nimplementations might "+
           "have a single number series for all\ncomponents derived from "+
           "'ianahw:port', while some others\nmight have different number series"+
           " for different\ncomponents with identities derived from 'ianahw:port"+
           "' (for\nexample, one for registered jack 45 (RJ45) and one "+
           "for\nsmall form-factor pluggable (SFP)).";
         reference
           "RFC 6933: Entity MIB (Version 4) -\n        entPhysicalParentRelPos";
       }
       leaf-list contains-child {
         type "leafref" {
           path "../../component/name";
         }
         config "false";
         description
           "The name of the contained component.";
         reference
           "RFC 6933: Entity MIB (Version 4) - entPhysicalChildIndex";
       }
       leaf hardware-rev {
         type "string";
         config "false";
         description
           "The vendor-specific hardware revision string for the\ncomponent.  "+
           "The preferred value is the hardware revision\nidentifier actually "+
           "printed on the component itself (if\npresent).";
         reference
           "RFC 6933: Entity MIB (Version 4) -\n        entPhysicalHardwareRev";
       }
       leaf firmware-rev {
         type "string";
         config "false";
         description
           "The vendor-specific firmware revision string for the\ncomponent.";
         reference
           "RFC 6933: Entity MIB (Version 4) -\n        entPhysicalFirmwareRev";
       }
       leaf software-rev {
         type "string";
         config "false";
         description
           "The vendor-specific software revision string for the\ncomponent.";
         reference
           "RFC 6933: Entity MIB (Version 4) -\n        entPhysicalSoftwareRev";
       }
       leaf serial-num {
         type "string";
         config "false";
         description
           "The vendor-specific serial number string for the\ncomponent.  The "+
           "preferred value is the serial number\nstring actually printed on the"+
           " component itself (if\npresent).";
         reference
           "RFC 6933: Entity MIB (Version 4) - entPhysicalSerialNum";
       }
       leaf mfg-name {
         type "string";
         config "false";
         description
           "The name of the manufacturer of this physical component.\nThe "+
           "preferred value is the manufacturer name string\nactually printed on"+
           " the component itself (if present).\n\nNote that comparisons between"+
           " instances of the\n'model-name', 'firmware-rev', 'software-rev', "+
           "and\n'serial-num' nodes are only meaningful amongst components\nwith"+
           " the same value of 'mfg-name'.\n\nIf the manufacturer name string "+
           "associated with the\nphysical component is unknown to the server, "+
           "then this\nnode is not instantiated.";
         reference
           "RFC 6933: Entity MIB (Version 4) - entPhysicalMfgName";
       }
       leaf model-name {
         type "string";
         config "false";
         description
           "The vendor-specific model name identifier string\nassociated with "+
           "this physical component.  The preferred\nvalue is the customer-visib"+
           "le part number, which may be\nprinted on the component itself.\nIf "+
           "the model name string associated with the physical\ncomponent is "+
           "unknown to the server, then this node is not\ninstantiated.";
         reference
           "RFC 6933: Entity MIB (Version 4) - entPhysicalModelName";
       }
       leaf alias {
         type "string";
         description
           "An 'alias' name for the component, as specified by a\nnetwork "+
           "manager, that provides a non-volatile 'handle' for\nthe component.\n"+
           "\nIf no configured value exists, the server MAY set the\nvalue of "+
           "this node to a locally unique value in the\noperational state.\n\nA "+
           "server implementation MAY map this leaf to the\nentPhysicalAlias MIB"+
           " object.  Such an implementation needs\nto use some mechanism to "+
           "handle the differences in size\nand characters allowed between this "+
           "leaf and\nentPhysicalAlias.  The definition of such a mechanism "+
           "is\noutside the scope of this document.";
         reference
           "RFC 6933: Entity MIB (Version 4) - entPhysicalAlias";
       }
       leaf asset-id {
         type "string";
         description
           "This node is a user-assigned asset tracking identifier for\nthe "+
           "component.\n\nA server implementation MAY map this leaf to "+
           "the\nentPhysicalAssetID MIB object.  Such an implementation\nneeds "+
           "to use some mechanism to handle the differences in\nsize and "+
           "characters allowed between this leaf and\nentPhysicalAssetID.  The "+
           "definition of such a mechanism is\noutside the scope of this "+
           "document.";
         reference
           "RFC 6933: Entity MIB (Version 4) - entPhysicalAssetID";
       }
       leaf is-fru {
         type "boolean";
         config "false";
         description
           "This node indicates whether or not this component is\nconsidered a "+
           "'field-replaceable unit' by the vendor.  If\nthis node contains the "+
           "value 'true', then this component\nidentifies a field-replaceable "+
           "unit.  For all components\nthat are permanently contained within a "+
           "field-replaceable\nunit, the value 'false' should be returned for "+
           "this\nnode.";
         reference
           "RFC 6933: Entity MIB (Version 4) - entPhysicalIsFRU";
       }
       leaf mfg-date {
         type "yang:date-and-time";
         config "false";
         description
           "The date of manufacturing of the managed component.";
         reference
           "RFC 6933: Entity MIB (Version 4) - entPhysicalMfgDate";
       }
       leaf-list uri {
         type "inet:uri";
         description
           "This node contains identification information about the\ncomponent.";
         reference
           "RFC 6933: Entity MIB (Version 4) - entPhysicalUris";
       }
       leaf uuid {
         type "yang:uuid";
         config "false";
         description
           "A Universally Unique Identifier of the component.";
         reference
           "RFC 6933: Entity MIB (Version 4) - entPhysicalUUID";
       }
       container state {
         if-feature "hardware-state";
         description
           "State-related nodes";
         reference
           "RFC 4268: Entity State MIB";
         leaf admin-state {
           type "admin-state";
           description
             "The administrative state for this component.\n\nThis node refers "+
             "to a component's administrative\npermission to service both other "+
             "components within its\ncontainment hierarchy as well other users "+
             "of its\nservices defined by means outside the scope of this\nmodul"+
             "e.\n\nSome components exhibit only a subset of the remaining\nadmi"+
             "nistrative state values.  Some components cannot be\nlocked; "+
             "hence, this node exhibits only the 'unlocked'\nstate.  Other "+
             "components cannot be shut down gracefully;\nhence, this node does "+
             "not exhibit the 'shutting-down'\nstate.";
           reference
             "RFC 4268: Entity State MIB - entStateAdmin";
         }
         leaf oper-state {
           type "oper-state";
           config "false";
           description
             "The operational state for this component.\n\nNote that this node "+
             "does not follow the administrative\nstate.  An administrative "+
             "state of 'down' does not\npredict an operational state of "+
             "'disabled'.\n\nNote that some implementations may not be able "+
             "to\naccurately report oper-state while the admin-state node\nhas a"+
             " value other than 'unlocked'.  In these cases, this\nnode MUST "+
             "have a value of 'unknown'.";
           reference
             "RFC 4268: Entity State MIB - entStateOper";
         }
         leaf alarm-state {
           type "alarm-state";
           config "false";
           description
             "The alarm state for this component.  It does not\ninclude the "+
             "alarms raised on child components within its\ncontainment "+
             "hierarchy.";
           reference
             "RFC 4268: Entity State MIB - entStateAlarm";
         }
         leaf standby-state {
           type "standby-state";
           config "false";
           description
             "The standby state for this component.\n\nSome components will "+
             "exhibit only a subset of the\nremaining standby state values.  If "+
             "this component\ncannot operate in a standby role, the value of "+
             "this node\nwill always be 'providing-service'.";
           reference
             "RFC 4268: Entity State MIB - entStateStandby";
         }
         config "false";
       }
       config "false";
     }
   }
 }

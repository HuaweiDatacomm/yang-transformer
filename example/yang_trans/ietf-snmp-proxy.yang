submodule ietf-snmp-proxy {
   belongs-to ietf-snmp {
     prefix "snmp";
   }
   include ietf-snmp-common;
   include ietf-snmp-target;
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Martin Bjorklund\n          <mailto:mbj@tail-"+
     "f.com>\nEditor:   Juergen Schoenwaelder\n          <mailto:j.schoenwaelder"+
     "@jacobs-university.de>";
   description
     "This submodule contains a collection of YANG definitions\nfor configuring "+
     "SNMP proxies.\nCopyright (c) 2014 IETF Trust and the persons identified "+
     "as\nauthors of the code.  All rights reserved.\nRedistribution and use in "+
     "source and binary forms, with or\nwithout modification, is permitted "+
     "pursuant to, and subject\nto the license terms contained in, the "+
     "Simplified BSD License\nset forth in Section 4.c of the IETF Trust's Legal"+
     " Provisions\nRelating to IETF Documents\n(http://trustee.ietf.org/license-"+
     "info).\nThis version of this YANG module is part of RFC 7407; see\nthe RFC"+
     " itself for full legal notices.";
   reference
     "RFC 3413: Simple Network Management Protocol (SNMP)\nApplications";
   revision "2014-12-10" {
     description
       "Initial revision.";
     reference
       "RFC 7407: A YANG Data Model for SNMP Configuration";
   }
   feature proxy {
     description
       "A server implements this feature if it can act as an\nSNMP proxy.";
     reference
       "RFC 3413: Simple Network Management Protocol (SNMP)\nApplications";
   }
   augment "/snmp:snmp" {
     if-feature "snmp:proxy";
     list proxy {
       key "name";
       description
         "List of proxy parameters.";
       reference
         "RFC 3413: Simple Network Management Protocol (SNMP).\nApplications.\nS"+
         "NMP-PROXY-MIB.snmpProxyTable";
       leaf name {
         type "snmp:identifier";
         description
           "Identifies the proxy parameter entry.";
         reference
           "RFC 3413: Simple Network Management Protocol (SNMP).\nApplications."+
           "\nSNMP-PROXY-MIB.snmpProxyName";
       }
       leaf type {
         type "enumeration" {
           enum "read" {
             value "1";
           }
           enum "write" {
             value "2";
           }
           enum "trap" {
             value "3";
           }
           enum "inform" {
             value "4";
           }
         }
         mandatory "true";
         reference
           "RFC 3413: Simple Network Management Protocol (SNMP).\nApplications."+
           "\nSNMP-PROXY-MIB.snmpProxyType";
       }
       leaf context-engine-id {
         type "snmp:engine-id";
         mandatory "true";
         reference
           "RFC 3413: Simple Network Management Protocol (SNMP).\nApplications."+
           "\nSNMP-PROXY-MIB.snmpProxyContextEngineID";
       }
       leaf target-params-in {
         type "snmp:identifier";
         description
           "The name of a target parameters list entry.\nImplementations MAY "+
           "restrict the values of this\nleaf to be one of the available values "+
           "of\n/snmp/target-params/name in a valid configuration.";
         reference
           "RFC 3413: Simple Network Management Protocol (SNMP).\nApplications."+
           "\nSNMP-PROXY-MIB.snmpProxyTargetParamsIn";
       }
       leaf single-target-out {
         when "../type = 'read' or ../type = 'write'";
         type "snmp:identifier";
         description
           "Implementations MAY restrict the values of this leaf\nto be one of "+
           "the available values of /snmp/target/name in\na valid configuration."+
           "";
         reference
           "RFC 3413: Simple Network Management Protocol (SNMP).\nApplications."+
           "\nSNMP-PROXY-MIB.snmpProxySingleTargetOut";
       }
       leaf multiple-target-out {
         when "../type = 'trap' or ../type = 'inform'";
         type "snmp:tag-value";
         description
           "Implementations MAY restrict the values of this leaf\nto be one of "+
           "the available values of /snmp/target/tag in\na valid configuration.";
         reference
           "RFC 3413: Simple Network Management Protocol (SNMP).\nApplications."+
           "\nSNMP-PROXY-MIB.snmpProxyMultipleTargetOut";
         config "false";
       }
     }
   }
 }

/*
Copyright (C) 2019 Huawei Technologies Co., Ltd. All rights reserved.
*/

 module huawei-mstp-deviations-OC-NE-X8X16 {
   namespace "urn:huawei:yang:huawei-mstp-deviations-OC-NE-X8X16";
   prefix "mstp-devs-OC-NE-X8X16";
   import huawei-mstp {
     prefix "mstp";
   }
   import huawei-ifm {
     prefix "ifm";
   }
   import huawei-ethernet {
     prefix "ethernet";
   }
   import huawei-erps {
     prefix "erps";
   }
   organization
     "Huawei Technologies Co., Ltd.";
   contact
     "Huawei Industrial Base\nBantian, Longgang\nShenzhen 518129\nPeople's "+
     "Republic of China\nWebsite: http://www.huawei.com\nEmail: support@huawei.c"+
     "om";
   description
     "Multiple spanning tree protocol.";
   revision "2019-04-23" {
     description
       "Initial revision.";
     reference
       "Huawei private.";
   }
   typedef stp-mode-deviations {
     type "enumeration" {
       enum "stp" {
         value "0";
         description
           "Spanning tree protocol mode.";
       }
       enum "rstp" {
         value "2";
         description
           "Rapid spanning tree protocol mode.";
       }
       enum "mstp" {
         value "3";
         description
           "Multiple ppanning tree protocol mode.";
       }
     }
     description
       "STP mode.";
   }
   deviation "/mstp:mstp/mstp:processs/mstp:process/mstp:mode" {
     deviate "replace" {
       type "mstp-devs-OC-NE-X8X16:stp-mode-deviations";
     }
   }
   deviation "/mstp:mstp/mstp:default-process/mstp:mode" {
     deviate "replace" {
       type "mstp-devs-OC-NE-X8X16:stp-mode-deviations";
     }
   }
   deviation "/ifm:ifm/ifm:interfaces/ifm:interface/ethernet:ethernet/ethernet:m"+
             "ain-interface/ethernet:l2-attribute/mstp:mstp-attribute/mstp:enabl"+
             "e" {
     deviate "add" {
       must "current() = 'false' or not(../../erps:erps-attribute/erps:rings/erp"+
            "s:ring)";
     }
   }
   deviation "/ifm:ifm/ifm:interfaces/ifm:interface/ethernet:ethernet/ethernet:m"+
             "ain-interface/ethernet:l2-attribute/mstp:mstp-attribute/mstp:vpls-"+
             "sub-interface" {
     deviate "add" {
       must "current() = 'false' or not(../../erps:erps-attribute/erps:rings/erp"+
            "s:ring)";
     }
   }
   deviation "/ifm:ifm/ifm:interfaces/ifm:interface/ethernet:ethernet/ethernet:m"+
             "ain-interface/ethernet:l2-attribute/mstp:mstp-attribute/mstp:tc-sn"+
             "ooping/mstp:enable" {
     deviate "add" {
       must "current() = 'false' or (../../enable = 'false' and not(../../../erp"+
            "s:erps-attribute/erps:rings/erps:ring))";
     }
   }
 }

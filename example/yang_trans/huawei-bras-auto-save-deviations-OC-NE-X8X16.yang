/*
Copyright (C) 2021 Huawei Technologies Co., Ltd. All rights reserved.
*/

 module huawei-bras-auto-save-deviations-OC-NE-X8X16 {
   namespace "urn:huawei:yang:huawei-bras-auto-save-deviations-OC-NE-X8X16";
   prefix "bras-auto-save-devs-OC-NE-X8X16";
   import huawei-bras-auto-save {
     prefix "bras-auto-save";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-bras-auto-save "+
     "module.";
   revision "2021-05-07" {
     description
       "Initial revision.";
     reference
       "Huawei private.";
   }
   deviation "/bras-auto-save:bras-auto-save/bras-auto-save:auto-save-max-user/b"+
             "ras-auto-save:number" {
     deviate "replace" {
       type "uint32" {
         range "8000..1024000";
       }
     }
   }
 }

module openconfig-rib-bgp {
   yang-version "1";
   namespace "http://openconfig.net/yang/rib/bgp";
   prefix "oc-rib-bgp";
   import openconfig-extensions {
     prefix "oc-ext";
   }
   include openconfig-rib-bgp-tables;
   include openconfig-rib-bgp-shared-attributes;
   include openconfig-rib-bgp-attributes;
   include openconfig-rib-bgp-table-attributes;
   organization
     "OpenConfig working group";
   contact
     "OpenConfig working group\nwww.openconfig.net";
   description
     "Defines a data model for representing BGP routing table (RIB)\ncontents.  "+
     "The model supports 5 logical RIBs per address family:\n\nloc-rib: This is "+
     "the main BGP routing table for the local routing\ninstance, containing "+
     "best-path selections for each prefix. The\nloc-rib table may contain "+
     "multiple routes for a given prefix,\nwith an attribute to indicate which "+
     "was selected as the best\npath.  Note that multiple paths may be used or "+
     "advertised even if\nonly one path is marked as best, e.g., when using "+
     "BGP\nadd-paths.  An implementation may choose to mark multiple\npaths in "+
     "the RIB as best path by setting the flag to true for\nmultiple entries.\n"+
     "\nadj-rib-in-pre: This is a per-neighbor table containing the NLRI\nupdate"+
     "s received from the neighbor before any local input policy\nrules or "+
     "filters have been applied.  This can be considered the\n'raw' updates from"+
     " a given neighbor.\n\nadj-rib-in-post: This is a per-neighbor table "+
     "containing the\nroutes received from the neighbor that are eligible "+
     "for\nbest-path selection after local input policy rules have been\napplied"+
     ".\n\nadj-rib-out-pre: This is a per-neighbor table containing routes\nelig"+
     "ible for sending (advertising) to the neighbor before output\npolicy rules"+
     " have been applied.\n\nadj-rib-out-post: This is a per-neighbor table "+
     "containing routes\neligible for sending (advertising) to the neighbor "+
     "after output\npolicy rules have been applied.";
   oc-ext:openconfig-version "0.6.0";
   revision "2019-04-25" {
     description
       "Update last-modified timestamp to be expressed as nanoseconds\nsince the"+
       " Unix epoch.";
     reference
       "0.6.0";
   }
   revision "2019-04-16" {
     description
       "Rename the top-level BGP RIB container's name\nto RIB.";
     reference
       "0.5.0";
   }
   revision "2019-02-27" {
     description
       "Remove top-level BGP RIB container, and update list\nnames to be "+
       "compatible with path compression.";
     reference
       "0.4.0";
   }
   revision "2018-11-21" {
     description
       "Add OpenConfig module metadata extensions.";
     reference
       "0.3.1";
   }
   revision "2016-10-17" {
     description
       "OpenConfig BGP RIB refactor";
     reference
       "0.3.0";
   }
   revision "2016-04-11" {
     description
       "OpenConfig public release";
     reference
       "0.2.0";
   }
 }

/*
Copyright (C) 2021 Huawei Technologies Co., Ltd. All rights reserved.
*/

 module huawei-loadbalance-deviations-OC-NE-X8X16 {
   namespace "urn:huawei:yang:huawei-loadbalance-deviations-OC-NE-X8X16";
   prefix "loadbalance-devs-OC-NE-X8X16";
   import huawei-loadbalance {
     prefix "loadbalance";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-loadbalance module.";
   revision "2021-05-07" {
     description
       "Initial revision.";
     reference
       "Huawei private.";
   }
   typedef cx-trunk-ecmp-deviations {
     type "enumeration" {
       enum "ip" {
         value "5";
         description
           "IP mode.";
       }
       enum "mac" {
         value "6";
         description
           "MAC mode.";
       }
       enum "vll" {
         value "7";
         description
           "VLL mode.";
       }
       enum "tunnel-info" {
         value "8";
         description
           "Tunnel information.";
       }
       enum "tunnel-inner-ip" {
         value "9";
         description
           "Tunnel inner IP information.";
       }
       enum "gtp" {
         value "10";
         description
           "GTP tunnel.";
       }
       enum "gtp-inner-ip" {
         value "12";
         description
           "GTP tunnel inner IP information.";
       }
     }
     description
       "CX load balancing trunk ecmp.";
   }
   deviation "/devm:devm/devm:lpu-boards/devm:lpu-board/loadbalance:loadbalance/"+
             "loadbalance:hash-fields/loadbalance:hash-field/loadbalance:trunk-e"+
             "cmp" {
     deviate "replace" {
       type "loadbalance-devs-OC-NE-X8X16:cx-trunk-ecmp-deviations";
     }
   }
 }

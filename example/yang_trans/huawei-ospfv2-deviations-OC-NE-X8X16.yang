/*
Copyright (C) 2019 Huawei Technologies Co., Ltd. All rights reserved.
*/

 module huawei-ospfv2-deviations-OC-NE-X8X16 {
   namespace "urn:huawei:yang:huawei-ospfv2-deviations-OC-NE-X8X16";
   prefix "ospfv2-devs-OC-NE-X8X16";
   import huawei-ospfv2 {
     prefix "ospfv2";
   }
   import huawei-network-instance {
     prefix "ni";
   }
   import huawei-l3vpn {
     prefix "l3vpn";
   }
   import huawei-mpls {
     prefix "mpls";
   }
   import huawei-mpls-ldp {
     prefix "mpls-ldp";
   }
   organization
     "Huawei Technologies Co., Ltd.";
   contact
     "Huawei Industrial Base\nBantian, Longgang\nShenzhen 518129\nPeople's "+
     "Republic of China\nWebsite: http://www.huawei.com\nEmail: support@huawei.c"+
     "om";
   description
     "OSPFv2 management.";
   revision "2019-04-04" {
     description
       "Initial revision.";
     reference
       "Huawei private.";
   }
   deviation "/ni:network-instance/ni:instances/ni:instance/l3vpn:afs/l3vpn:af/o"+
             "spfv2:ospf-import-rts/ospfv2:ospf-import-rt/ospfv2:src-vrf" {
     deviate "add" {
       must "(../../../l3vpn:type='ipv4-unicast' and /ni:network-instance/ni:ins"+
            "tances/ni:instance[ni:name=current()]/l3vpn:afs/l3vpn:af[l3vpn:type"+
            "='ipv4-unicast']) or (../../../l3vpn:type='ipv6-unicast' and "+
            "/ni:network-instance/ni:instances/ni:instance[ni:name=current()]/l3"+
            "vpn:afs/l3vpn:af[l3vpn:type='ipv6-unicast'])";
     }
   }
   deviation "/ni:network-instance/ni:instances/ni:instance/ospfv2:ospfv2/ospfv2"+
             ":sites/ospfv2:site/ospfv2:mpls-ldp-auto-flag" {
     deviate "add" {
       must "/mpls:mpls/mpls-ldp:ldp/mpls-ldp:enable='true' and ../../../../ni:n"+
            "ame='_public_' or ../mpls-ldp-auto-flag='none'";
     }
   }
 }

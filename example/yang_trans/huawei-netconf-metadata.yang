/*
Copyright (C) 2019 Huawei Technologies Co., Ltd. All rights reserved.
*/

 module huawei-netconf-metadata {
   namespace "urn:huawei:yang:huawei-netconf-metadata";
   prefix "nc-md";
   import ietf-yang-metadata {
     prefix "md";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Addition of private attributes to the NETCONF standard operations.";
   revision "2019-05-27" {
     description
       "Initial revision.";
     reference
       "Huawei private.";
   }
   ext:task-name "netconf";
   md:annotation "difference" {
     type "string";
     description
       "This annotation contains the record create/modify/delete information.";
   }
   md:annotation "set-id" {
     type "string";
     description
       "This annotation used for get/get-config operation with position;\nIt can"+
       " be used to identify the previous query operation to select\nthe next "+
       "set/range of records from NETCONF server.";
   }
 }

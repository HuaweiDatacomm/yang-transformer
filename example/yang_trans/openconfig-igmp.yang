module openconfig-igmp {
   yang-version "1";
   namespace "http://openconfig.net/yang/igmp";
   prefix "oc-igmp";
   import openconfig-extensions {
     prefix "oc-ext";
   }
   organization
     "OpenConfig working group";
   contact
     "OpenConfig working group\nwww.openconfig.net";
   description
     "An OpenConfig model for Internet Group Management Protocol (IGMP).";
   oc-ext:openconfig-version "0.2.0";
   revision "2019-07-09" {
     description
       "Re-indent module to two spaces.\nNormalise timeticks64 usage to "+
       "nanoseconds.";
     reference
       "0.2.0";
   }
   revision "2018-11-21" {
     description
       "Add OpenConfig module metadata extensions.";
     reference
       "0.1.1";
   }
   revision "2018-02-19" {
     description
       "Initial revision.";
     reference
       "0.1.0";
   }
   oc-ext:regexp-posix;
   oc-ext:catalog-organization "openconfig";
   oc-ext:origin "openconfig";
 }

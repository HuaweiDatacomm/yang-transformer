module ietf-lime-time-types {
   yang-version "1.1";
   namespace "urn:ietf:params:xml:ns:yang:ietf-lime-time-types";
   prefix "lime";
   organization
     "IETF LIME Working Group";
   contact
     "WG Web:   <https://datatracker.ietf.org/wg/lime>\nWG List:  <mailto:lmap@i"+
     "etf.org>\n\nEditor:   Qin Wu\n          <bill.wu@huawei.com>";
   description
     "This module provides time-related definitions used by the data\nmodels "+
     "written for Layer Independent OAM Management in the\nMulti-Layer "+
     "Environment (LIME).  This module defines\nidentities but no schema tree "+
     "elements.\n\nCopyright (c) 2019 IETF Trust and the persons identified "+
     "as\nauthors of the code.  All rights reserved.\n\nRedistribution and use "+
     "in source and binary forms, with or\nwithout modification, is permitted "+
     "pursuant to, and subject\nto the license terms contained in, the "+
     "Simplified BSD License\nset forth in Section 4.c of the IETF Trust's Legal"+
     " Provisions\nRelating to IETF Documents\n(http://trustee.ietf.org/license-"+
     "info).\n\nThis version of this YANG module is part of RFC 8532; see\nthe "+
     "RFC itself for full legal notices.";
   revision "2019-04-16" {
     description
       "Initial version.";
     reference
       "RFC 8532: Generic YANG Data Model for the Management of\nOperations, "+
       "Administration, and Maintenance (OAM) Protocols\nThat Use Connectionless"+
       " Communications";
   }
   identity time-unit-type {
     description
       "Time unit type.";
   }
   identity hours {
     base "time-unit-type";
     description
       "Time unit in hours.";
   }
   identity minutes {
     base "time-unit-type";
     description
       "Time unit in minutes.";
   }
   identity seconds {
     base "time-unit-type";
     description
       "Time unit in seconds.";
   }
   identity milliseconds {
     base "time-unit-type";
     description
       "Time unit in milliseconds.";
   }
   identity microseconds {
     base "time-unit-type";
     description
       "Time unit in microseconds.";
   }
   identity nanoseconds {
     base "time-unit-type";
     description
       "Time unit in nanoseconds.";
   }
   identity timestamp-type {
     description
       "Base identity for Timestamp Type.";
   }
   identity truncated-ptp {
     base "timestamp-type";
     description
       "Identity for 64-bit short-format PTP timestamp.";
   }
   identity truncated-ntp {
     base "timestamp-type";
     description
       "Identity for 32-bit short-format NTP timestamp.";
   }
   identity ntp64 {
     base "timestamp-type";
     description
       "Identity for 64-bit NTP timestamp.";
   }
   identity icmp {
     base "timestamp-type";
     description
       "Identity for 32-bit ICMP timestamp.";
   }
   identity ptp80 {
     base "timestamp-type";
     description
       "Identity for 80-bit PTP timestamp.";
   }
 }

submodule ietf-snmp-tsm {
   belongs-to ietf-snmp {
     prefix "snmp";
   }
   include ietf-snmp-common;
   include ietf-snmp-target;
   include ietf-snmp-proxy;
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Martin Bjorklund\n          <mailto:mbj@tail-"+
     "f.com>\nEditor:   Juergen Schoenwaelder\n          <mailto:j.schoenwaelder"+
     "@jacobs-university.de>";
   description
     "This submodule contains a collection of YANG definitions for\nconfiguring "+
     "the Transport Security Model (TSM) of SNMP.\nCopyright (c) 2014 IETF Trust"+
     " and the persons identified as\nauthors of the code.  All rights "+
     "reserved.\nRedistribution and use in source and binary forms, with "+
     "or\nwithout modification, is permitted pursuant to, and subject\nto the "+
     "license terms contained in, the Simplified BSD License\nset forth in "+
     "Section 4.c of the IETF Trust's Legal Provisions\nRelating to IETF "+
     "Documents\n(http://trustee.ietf.org/license-info).\nThis version of this "+
     "YANG module is part of RFC 7407; see\nthe RFC itself for full legal "+
     "notices.";
   reference
     "RFC 5591: Transport Security Model for the\nSimple Network Management "+
     "Protocol (SNMP)";
   revision "2014-12-10" {
     description
       "Initial revision.";
     reference
       "RFC 7407: A YANG Data Model for SNMP Configuration";
   }
   feature tsm {
     description
       "A server implements this feature if it supports the\nTransport Security "+
       "Model for SNMP.";
     reference
       "RFC 5591: Transport Security Model for the\nSimple Network Management "+
       "Protocol (SNMP)";
   }
   augment "/snmp:snmp" {
     if-feature "tsm";
     container tsm {
       description
         "Configuration of the Transport Security Model.";
       leaf use-prefix {
         type "boolean";
         default "false";
         reference
           "RFC 5591: Transport Security Model for the Simple\nNetwork "+
           "Management Protocol (SNMP).\nSNMP-TSM-MIB.snmpTsmConfigurationUsePre"+
           "fix";
       }
     }
   }
   augment "/snmp:snmp/snmp:target-params/snmp:params" {
     if-feature "tsm";
     case tsm {
       container tsm {
         description
           "Transport-based security SNMPv3 parameters type.\nRepresents "+
           "snmpTargetParamsMPModel '3' and\nsnmpTargetParamsSecurityModel '4'.";
         leaf security-name {
           type "snmp:security-name";
           mandatory "true";
           reference
             "RFC 3413: Simple Network Management Protocol (SNMP).\nApplications"+
             ".\nSNMP-TARGET-MIB.snmpTargetParamsSecurityName";
         }
         leaf security-level {
           type "snmp:security-level";
           mandatory "true";
           reference
             "RFC 3413: Simple Network Management Protocol (SNMP).\nApplications"+
             ".\nSNMP-TARGET-MIB.snmpTargetParamsSecurityLevel";
         }
       }
     }
   }
 }

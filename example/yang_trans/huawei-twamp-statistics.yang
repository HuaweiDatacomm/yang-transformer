/*
Copyright (C) 2019-2020 Huawei Technologies Co., Ltd. All rights reserved.
*/

 module huawei-twamp-statistics {
   namespace "urn:huawei:yang:huawei-twamp-statistics";
   prefix "twamp-statistics";
   import huawei-twamp-controller {
     prefix "twamp-controller";
   }
   import huawei-extension {
     prefix "ext";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "TWAMP statistics.";
   revision "2020-09-03" {
     description
       "Add new container: link-bundle-statistics.";
     reference
       "Huawei private.";
   }
   revision "2020-03-05" {
     description
       "Modify initial revision's description.";
     reference
       "Huawei private.";
   }
   revision "2019-05-05" {
     description
       "Init revision.";
     reference
       "Huawei private.";
   }
   ext:task-name "twampclient";
   augment "/twamp-controller:twamp-controller/twamp-controller:client/twamp-con"+
           "troller:sessions/twamp-controller:session" {
     description
       "TWAMP augment.";
     container statistics {
       config "false";
       description
         "TWAMP statistics.";
       leaf avg-delay {
         type "uint32";
         units "us";
         description
           "The average delay.";
       }
       leaf avg-jitter {
         type "uint32";
         units "us";
         description
           "The average jitter.";
       }
       leaf loss-count {
         type "uint32";
         description
           "The loss count.";
       }
       leaf send-count {
         type "uint32";
         description
           "The send count.";
       }
     }
     container link-bundle-statistics {
       config "false";
       description
         "List of TWAMP link-bundle statistics.";
       list link-bundle-statistic {
         key "if-name";
         description
           "Statistics of TWAMP link-bundle.";
         leaf if-name {
           type "leafref" {
             path "/ifm:ifm/ifm:interfaces/ifm:interface/ifm:name";
           }
           description
             "Interface Name.";
         }
         leaf if-index {
           type "uint32";
           description
             "Interface ID.";
         }
         leaf loss-count {
           type "uint32";
           description
             "The loss count.";
         }
         leaf send-count {
           type "uint32";
           description
             "The send count.";
         }
         leaf avg-delay {
           type "uint32";
           units "us";
           description
             "The average delay.";
         }
         leaf avg-jitter {
           type "uint32";
           units "us";
           description
             "The average jitter.";
         }
         leaf avg-tx-jitter {
           type "uint32";
           units "us";
           description
             "The average TX jitter.";
         }
         leaf avg-rx-jitter {
           type "uint32";
           units "us";
           description
             "The average RX jitter.";
         }
         leaf max-delay {
           type "uint32";
           units "us";
           description
             "The maximum delay.";
         }
         leaf min-delay {
           type "uint32";
           units "us";
           description
             "The minimum delay.";
         }
         leaf max-jitter {
           type "uint32";
           units "us";
           description
             "The maximum jitter.";
         }
         leaf min-jitter {
           type "uint32";
           units "us";
           description
             "The minimum jitter.";
         }
         leaf max-tx-jitter {
           type "uint32";
           units "us";
           description
             "The maximum TX jitter.";
         }
         leaf min-tx-jitter {
           type "uint32";
           units "us";
           description
             "The minimum TX jitter.";
         }
         leaf max-rx-jitter {
           type "uint32";
           units "us";
           description
             "The maximum RX jitter.";
         }
         leaf min-rx-jitter {
           type "uint32";
           units "us";
           description
             "The minimum RX jitter.";
         }
         leaf member-id-error-count {
           type "uint32";
           description
             "The member-id error count.";
         }
         leaf checksum-error-count {
           type "uint32";
           description
             "The checksum error count.";
         }
       }
     }
   }
 }

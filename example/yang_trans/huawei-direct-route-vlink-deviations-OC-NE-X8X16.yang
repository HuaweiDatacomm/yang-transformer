/*
Copyright (C) 2019 Huawei Technologies Co., Ltd. All rights reserved.
*/

 module huawei-direct-route-vlink-deviations-OC-NE-X8X16 {
   yang-version "1";
   namespace "urn:huawei:yang:huawei-direct-route-vlink-deviations-OC-NE-X8X16";
   prefix "direct-route-vlink-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "This module contains a collection of YANG definitions for managing direct "+
     "route VLINK.";
   revision "2019-07-15" {
     description
       "Initial revision.";
     reference
       "Huawei private.";
   }
 }

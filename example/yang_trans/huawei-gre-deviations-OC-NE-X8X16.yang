/*
Copyright (C) 2020 Huawei Technologies Co., Ltd. All rights reserved.
*/

 module huawei-gre-deviations-OC-NE-X8X16 {
   namespace "urn:huawei:yang:huawei-gre-deviations-OC-NE-X8X16";
   prefix "gre-devs-OC-NE-X8X16";
   import huawei-gre {
     prefix "gre";
   }
   import huawei-ifm {
     prefix "ifm";
   }
   import huawei-tunnel-management {
     prefix "tnlm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-gre module.";
   revision "2020-05-10" {
     description
       "Initial revision.";
     reference
       "Huawei private.";
   }
   deviation "/ifm:ifm/ifm:interfaces/ifm:interface/tnlm:tunnel-protocol/tnlm:ty"+
             "pe/gre:gre/gre:gre-tunnel/gre:source/gre:if-info/gre:if-name" {
     deviate "add" {
       must "/ifm:ifm/ifm:interfaces/ifm:interface[ifm:name=current()]/ifm:type="+
            "'Ethernet' or /ifm:ifm/ifm:interfaces/ifm:interface[ifm:name=curren"+
            "t()]/ifm:type ='GigabitEthernet' or /ifm:ifm/ifm:interfaces/ifm:int"+
            "erface[ifm:name=current()]/ifm:type='Eth-Trunk' or /ifm:ifm/ifm:int"+
            "erfaces/ifm:interface[ifm:name=current()]/ifm:type='LoopBack' or "+
            "/ifm:ifm/ifm:interfaces/ifm:interface[ifm:name=current()]/ifm:type="+
            "'100GE' or /ifm:ifm/ifm:interfaces/ifm:interface[ifm:name=current()"+
            "]/ifm:type='40GE' or /ifm:ifm/ifm:interfaces/ifm:interface[ifm:name"+
            "=current()]/ifm:type='25GE' or /ifm:ifm/ifm:interfaces/ifm:interfac"+
            "e[ifm:name=current()]/ifm:type='10GE' or /ifm:ifm/ifm:interfaces/if"+
            "m:interface[ifm:name=current()]/ifm:type='GEBrief' or /ifm:ifm/ifm:"+
            "interfaces/ifm:interface[ifm:name=current()]/ifm:type='50GE' or "+
            "/ifm:ifm/ifm:interfaces/ifm:interface[ifm:name=current()]/ifm:type="+
            "'50|100GE' or /ifm:ifm/ifm:interfaces/ifm:interface[ifm:name=curren"+
            "t()]/ifm:type='400GE' or /ifm:ifm/ifm:interfaces/ifm:interface[ifm:"+
            "name=current()]/ifm:type='FlexE' or /ifm:ifm/ifm:interfaces/ifm:int"+
            "erface[ifm:name=current()]/ifm:type='XGigabitEthernet' or "+
            "/ifm:ifm/ifm:interfaces/ifm:interface[ifm:name=current()]/ifm:type="+
            "'Global-VE' or /ifm:ifm/ifm:interfaces/ifm:interface[ifm:name=curre"+
            "nt()]/ifm:type='MEth' or /ifm:ifm/ifm:interfaces/ifm:interface[ifm:"+
            "name=current()]/ifm:type='Vlanif'";
     }
   }
 }

/*
Copyright (C) 2021 Huawei Technologies Co., Ltd. All rights reserved.
*/

 module huawei-loopdetect-deviations-OC-NE-X8X16 {
   namespace "urn:huawei:yang:huawei-loopdetect-deviations-OC-NE-X8X16";
   prefix "loopdetect-devs-OC-NE-X8X16";
   import huawei-loopdetect {
     prefix "loopdetect";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-loopdetect module.";
   revision "2021-05-07" {
     description
       "Initial revision.";
     reference
       "Huawei private.";
   }
   deviation "/loopdetect:loopdetect/loopdetect:trigger-detect/loopdetect:global"+
             "/loopdetect:min-port-up-time" {
     deviate "replace" {
       type "uint32" {
         range "1..100";
       }
     }
   }
   deviation "/ifm:ifm/ifm:interfaces/ifm:interface/loopdetect:loopdetect/loopde"+
             "tect:loopback-detect/loopdetect:block-time" {
     deviate "replace" {
       type "uint32" {
         range "5..255";
       }
     }
   }
 }

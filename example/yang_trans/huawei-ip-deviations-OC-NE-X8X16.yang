/*
Copyright (C) 2019 Huawei Technologies Co., Ltd. All rights reserved.
*/

 module huawei-ip-deviations-OC-NE-X8X16 {
   namespace "urn:huawei:yang:huawei-ip-deviations-OC-NE-X8X16";
   prefix "ip-devs-OC-NE-X8X16";
   import huawei-ip {
     prefix "ip";
   }
   import huawei-ifm {
     prefix "ifm";
   }
   import huawei-network-instance {
     prefix "ni";
   }
   import huawei-l3vpn {
     prefix "l3vpn";
   }
   organization
     "Huawei Technologies Co., Ltd.";
   contact
     "Huawei Industrial Base\nBantian, Longgang\nShenzhen 518129\nPeople's "+
     "Republic of China\nWebsite: http://www.huawei.com\nEmail: support@huawei.c"+
     "om";
   description
     "Common interface management, which includes the public configuration of "+
     "interfaces.";
   revision "2019-04-15" {
     description
       "Init revision.";
     reference
       "Huawei private.";
   }
   deviation "/ifm:ifm/ifm:interfaces/ifm:interface/ip:ipv4/ip:address/ip:common"+
             "-address/ip:addresses/ip:address/ip:type" {
     deviate "add" {
       must "(../ip:type='sub' and /ifm:ifm/ifm:global/ifm:ipv4-ignore-primary-s"+
            "ub='false') or ../ip:type='main'";
     }
   }
   deviation "/ifm:ifm/ifm:interfaces/ifm:interface/ip:ipv4/ip:address/ip:common"+
             "-address/ip:addresses/ip:address" {
     deviate "add" {
       must "/ni:network-instance/ni:instances/ni:instance[ni:name=current()/../"+
            "../../ifm:vrf-name]/l3vpn:afs/l3vpn:af[l3vpn:type='ipv4-unicast']";
     }
   }
   deviation "/ifm:ifm/ifm:interfaces/ifm:interface/ip:ipv4/ip:address/ip:negoti"+
             "ate-address/ip:negotiation-address/ip:negotiation-type" {
     deviate "add" {
       must "/ni:network-instance/ni:instances/ni:instance[ni:name=current()/../"+
            "../../ifm:vrf-name]/l3vpn:afs/l3vpn:af[l3vpn:type='ipv4-unicast']";
     }
   }
   deviation "/ifm:ifm/ifm:interfaces/ifm:interface/ip:ipv4/ip:address/ip:unnumb"+
             "ered-address/ip:unnumbered-address/ip:unnumbered-if-name" {
     deviate "add" {
       must "(/ni:network-instance/ni:instances/ni:instance[ni:name=current()/.."+
            "/../../ifm:vrf-name]/l3vpn:afs/l3vpn:af[l3vpn:type='ipv4-unicast'])"+
            " and (../../../ifm:name!=../unnumbered-if-name) and (/ifm:ifm/ifm:i"+
            "nterfaces/ifm:interface[ifm:name=current()]/ifm:vrf-name = "+
            "../../../ifm:vrf-name)";
     }
   }
   deviation "/ifm:ifm/ifm:interfaces/ifm:interface/ip:ipv6/ip:auto-link-local" {
     deviate "add" {
       must "../auto-link-local='false' or (../auto-link-local='true' and "+
            "/ni:network-instance/ni:instances/ni:instance[ni:name=current()/../"+
            "../ifm:vrf-name]/l3vpn:afs/l3vpn:af[l3vpn:type='ipv6-unicast'])";
     }
   }
   deviation "/ifm:ifm/ifm:interfaces/ifm:interface/ip:ipv6/ip:address/ip:common"+
             "-address/ip:addresses" {
     deviate "add" {
       must "/ni:network-instance/ni:instances/ni:instance[ni:name=current()/../"+
            "../ifm:vrf-name]/l3vpn:afs/l3vpn:af[l3vpn:type='ipv6-unicast']";
     }
   }
 }

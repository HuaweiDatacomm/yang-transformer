module ietf-network {
   yang-version "1.1";
   namespace "urn:ietf:params:xml:ns:yang:ietf-network";
   prefix "nw";
   organization
     "IETF I2RS (Interface to the Routing System) Working Group";
   contact
     "WG Web:    <https://datatracker.ietf.org/wg/i2rs/>\nWG List:   <mailto:i2r"+
     "s@ietf.org>\n\nEditor:    Alexander Clemm\n           <mailto:ludwig@clemm"+
     ".org>\n\nEditor:    Jan Medved\n           <mailto:jmedved@cisco.com>\n\nE"+
     "ditor:    Robert Varga\n           <mailto:robert.varga@pantheon.tech>\n\n"+
     "Editor:    Nitin Bahadur\n           <mailto:nitin_bahadur@yahoo.com>\n\nE"+
     "ditor:    Hariharan Ananthakrishnan\n           <mailto:hari@packetdesign."+
     "com>\n\nEditor:    Xufeng Liu\n           <mailto:xufeng.liu.ietf@gmail.co"+
     "m>";
   description
     "This module defines a common base data model for a collection\nof nodes in"+
     " a network.  Node definitions are further used\nin network topologies and "+
     "inventories.\n\nCopyright (c) 2018 IETF Trust and the persons identified "+
     "as\nauthors of the code.  All rights reserved.\n\nRedistribution and use "+
     "in source and binary forms, with or\nwithout modification, is permitted "+
     "pursuant to, and subject\nto the license terms contained in, the "+
     "Simplified BSD License\nset forth in Section 4.c of the IETF Trust's Legal"+
     " Provisions\nRelating to IETF Documents\n(https://trustee.ietf.org/license"+
     "-info).\n\nThis version of this YANG module is part of RFC 8345;\nsee the "+
     "RFC itself for full legal notices.";
   revision "2018-02-26" {
     description
       "Initial revision.";
     reference
       "RFC 8345: A YANG Data Model for Network Topologies";
   }
 }

/*
Copyright (C) 2021 Huawei Technologies Co., Ltd. All rights reserved.
*/

 module huawei-bras-cu-agent-deviations-OC-NE-X8X16 {
   namespace "urn:huawei:yang:huawei-bras-cu-agent-deviations-OC-NE-X8X16";
   prefix "bras-cu-agent-devs-OC-NE-X8X16";
   import huawei-bras-cu-agent {
     prefix "bras-cu-agent";
   }
   import huawei-ifm {
     prefix "ifm";
   }
   import huawei-rbs {
     prefix "rbs";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-bras-cu-agent module.";
   revision "2021-05-07" {
     description
       "Initial revision.";
     reference
       "Huawei private.";
   }
   deviation "/ifm:ifm/ifm:interfaces/ifm:interface/bras-cu-agent:cu-agent/bras-"+
             "cu-agent:cu-multicast-rbp/bras-cu-agent:name" {
     deviate "replace" {
       type "leafref" {
         path "/rbs:rbs/rbs:profiles/rbs:profile/rbs:name";
       }
     }
   }
 }

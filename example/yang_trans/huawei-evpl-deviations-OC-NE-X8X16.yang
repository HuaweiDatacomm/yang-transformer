/*
Copyright (C) 2020 Huawei Technologies Co., Ltd. All rights reserved.
*/

 module huawei-evpl-deviations-OC-NE-X8X16 {
   yang-version "1";
   namespace "urn:huawei:yang:huawei-evpl-deviations-OC-NE-X8X16";
   prefix "evpl-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Management of EVPL.";
   revision "2020-02-15" {
     description
       "Init revision.";
     reference
       "Huawei private.";
   }
 }

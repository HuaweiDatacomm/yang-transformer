/*
Copyright (C) 2019 Huawei Technologies Co., Ltd. All rights reserved.
*/

 module huawei-pic {
   yang-version "1";
   namespace "urn:huawei:yang:huawei-pic";
   prefix "pic";
   import ietf-yang-types {
     prefix "yang";
   }
   import huawei-devm {
     prefix "devm";
   }
   import huawei-driver {
     prefix "driver";
   }
   import huawei-ifm {
     prefix "ifm";
   }
   import huawei-extension {
     prefix "ext";
   }
   import huawei-license {
     prefix "lcs";
   }
   import huawei-pub-type {
     prefix "pub-type";
   }
   organization
     "Huawei Technologies Co., Ltd.";
   contact
     "Huawei Industrial Base\nBantian, Longgang\nShenzhen 518129\nPeople's "+
     "Republic of China\nWebsite: http://www.huawei.com\nEmail: support@huawei.c"+
     "om";
   description
     "Global Configuration.";
   revision "2019-04-01" {
     description
       "Initial revision.";
     reference
       "Huawei private.";
   }
   typedef devm-trans-alarm-type {
     type "enumeration" {
       enum "AUAIS" {
         value "0";
         description
           "Line Alarm Indication Signal.";
       }
       enum "B3TCA" {
         value "1";
         description
           "B3 Threshold Crossing Alarm.";
       }
       enum "LAIS" {
         value "2";
         description
           "Line alarm indication Signal.";
       }
       enum "LOF" {
         value "3";
         description
           "Loss of Frame.";
       }
       enum "LOM" {
         value "4";
         description
           "Loss of Tributary Multiframe.";
       }
       enum "LOP" {
         value "5";
         description
           "Loss of Pointer.";
       }
       enum "LOS" {
         value "6";
         description
           "Loss of Signal.";
       }
       enum "LRDI" {
         value "7";
         description
           "Line Remote Defect Indication.";
       }
       enum "LREI" {
         value "8";
         description
           "Line Remote Error Indication.";
       }
       enum "OOF" {
         value "9";
         description
           "Out of Frame.";
       }
       enum "PAIS" {
         value "10";
         description
           "Path Alarm Indication Signal.";
       }
       enum "PRDI" {
         value "11";
         description
           "Path Remote Defect Indication.";
       }
       enum "PREI" {
         value "12";
         description
           "Path Remote Error Indication.";
       }
       enum "PPLM" {
         value "13";
         description
           "Path Payload Mismatch.";
       }
       enum "RDOOL" {
         value "14";
         description
           "Receive Data Out of Lock.";
       }
       enum "RROOL" {
         value "15";
         description
           "Receive Reference Out of Lock.";
       }
       enum "SDBERE" {
         value "16";
         description
           "Signal Degrade Threshold Alarm.";
       }
       enum "SFBERE" {
         value "17";
         description
           "Signal Fail Threshold Alarm.";
       }
       enum "TROOL" {
         value "18";
         description
           "Transmit Reference Out of Lock.";
       }
       enum "PUNEQ" {
         value "19";
         description
           "Path Unequipped Indication.";
       }
       enum "LCD" {
         value "20";
         description
           "Loss of Code Group Synchronization.";
       }
       enum "WLNK" {
         value "21";
         description
           "WLNK.";
       }
       enum "B1TCA" {
         value "40";
         description
           "B1 Threshold Crossing Alarm.";
       }
       enum "B2TCA" {
         value "41";
         description
           "B2 Threshold Crossing Alarm.";
       }
     }
     description
       "Transmission alarm type.";
   }
   typedef eth-speed-type {
     type "enumeration" {
       enum "10M" {
         value "0";
         description
           "Configure 10M.";
       }
       enum "100M" {
         value "1";
         description
           "Configure 100M.";
       }
       enum "1000M" {
         value "2";
         description
           "Configure 1000M.";
       }
       enum "2500M" {
         value "5";
         description
           "Configure 2500M.";
       }
       enum "10G" {
         value "6";
         description
           "Configure 10G.";
       }
       enum "40G" {
         value "7";
         description
           "Configure 40G.";
       }
       enum "100G" {
         value "8";
         description
           "Configure 100G.";
       }
       enum "auto" {
         value "9";
         description
           "Auto.";
       }
       enum "1G" {
         value "10";
         description
           "Configure 1G.";
       }
       enum "2G" {
         value "11";
         description
           "Configure 2G.";
       }
       enum "3G" {
         value "12";
         description
           "Configure 3G.";
       }
       enum "4G" {
         value "13";
         description
           "Configure 4G.";
       }
       enum "1.25G" {
         value "14";
         description
           "Configure 1.25G.";
       }
       enum "2.5G" {
         value "15";
         description
           "Configure 2.5G.";
       }
       enum "3.75G" {
         value "16";
         description
           "Configure 3.75G.";
       }
       enum "5G" {
         value "17";
         description
           "Configure 5G.";
       }
       enum "15G" {
         value "18";
         description
           "Configure 15G.";
       }
       enum "20G" {
         value "19";
         description
           "Configure 20G.";
       }
       enum "25G" {
         value "20";
         description
           "Configure 25G.";
       }
       enum "30G" {
         value "21";
         description
           "Configure 30G.";
       }
       enum "35G" {
         value "22";
         description
           "Configure 35G.";
       }
       enum "45G" {
         value "24";
         description
           "Configure 45G.";
       }
       enum "50G" {
         value "25";
         description
           "Configure 50G.";
       }
       enum "55G" {
         value "26";
         description
           "Configure 55G.";
       }
       enum "60G" {
         value "27";
         description
           "Configure 60G.";
       }
       enum "65G" {
         value "28";
         description
           "Configure 65G.";
       }
       enum "70G" {
         value "29";
         description
           "Configure 70G.";
       }
       enum "75G" {
         value "30";
         description
           "Configure 75G.";
       }
       enum "80G" {
         value "31";
         description
           "Configure 80G.";
       }
       enum "85G" {
         value "32";
         description
           "Configure 85G.";
       }
       enum "90G" {
         value "33";
         description
           "Configure 90G.";
       }
       enum "95G" {
         value "34";
         description
           "Configure 95G.";
       }
       enum "0G" {
         value "35";
         description
           "Configure 0G.";
       }
       enum "400G" {
         value "36";
         description
           "Configure 400G.";
       }
     }
     description
       "Speed type.";
   }
   typedef eth-duplex-type {
     type "enumeration" {
       enum "half" {
         value "1";
         description
           "Half duplex.";
       }
       enum "full" {
         value "2";
         description
           "Full duplex.";
       }
       enum "auto" {
         value "0";
         description
           "Auto-negotiation mode. By default,the mode is negotiated based on "+
           "hardware capabilities.";
       }
     }
     description
       "Duplex type.";
   }
   typedef pic-statistic-port-type {
     type "enumeration" {
       enum "ATM" {
         value "0";
         description
           "ATM port.";
       }
       enum "C37" {
         value "1";
         description
           "C37 serial port.";
       }
       enum "CODIR" {
         value "2";
         description
           "Co-directional serial port.";
       }
       enum "CPOS" {
         value "3";
         description
           "CPOS port.";
       }
       enum "E1" {
         value "4";
         description
           "E1 port.";
       }
       enum "E3" {
         value "5";
         description
           "E3 port.";
       }
       enum "ECMSERIAL" {
         value "6";
         description
           "Physical serial port.";
       }
       enum "ETH" {
         value "7";
         description
           "Ethernet port.";
       }
       enum "FLEXEPHY" {
         value "8";
         description
           "FlexE physical port.";
       }
       enum "FLEXE" {
         value "9";
         description
           "FlexE business port.";
       }
       enum "OTN" {
         value "10";
         description
           "OTN port.";
       }
       enum "POS" {
         value "11";
         description
           "POS port.";
       }
       enum "VOICE" {
         value "12";
         description
           "Voice serial port.";
       }
     }
     description
       "Pic statistic port type.";
   }
   typedef lcs-active-status-type {
     type "enumeration" {
       enum "unallocated" {
         value "0";
         description
           "Unallocated.";
       }
       enum "allocated" {
         value "1";
         description
           "Allocated.";
       }
       enum "activated" {
         value "2";
         description
           "Activated.";
       }
     }
     description
       "License active status type.";
   }
   typedef port-negotiation-mode-type {
     type "enumeration" {
       enum "slave" {
         value "0";
         description
           "Slave.";
       }
       enum "na" {
         value "1";
         description
           "NA.";
       }
       enum "auto" {
         value "2";
         description
           "Auto.";
       }
       enum "master" {
         value "3";
         description
           "Master.";
       }
     }
     description
       "Port negotiation mode type.";
   }
   typedef alarm-ais-insert-name {
     type "enumeration" {
       enum "hptim" {
         value "1";
         description
           "Hptim.";
       }
       enum "lptim" {
         value "2";
         description
           "Lptim.";
       }
       enum "rstim" {
         value "3";
         description
           "Rstim.";
       }
       enum "hptimatm" {
         value "4";
         description
           "Hptimatm.";
       }
       enum "hpuneqatm" {
         value "5";
         description
           "Hpuneqatm.";
       }
       enum "hpuneq" {
         value "6";
         description
           "Hpuneq.";
       }
       enum "hpplm" {
         value "7";
         description
           "Hpplm.";
       }
       enum "lpuneq" {
         value "8";
         description
           "Lpuneq.";
       }
     }
     description
       "Alarm Name.";
   }
   typedef port-trans-mode-type {
     type "enumeration" {
       enum "lan-mode" {
         value "0";
         description
           "LAN Mode.";
       }
       enum "wan-mode" {
         value "1";
         description
           "WAN Mode.";
       }
       enum "otn-mode" {
         value "2";
         description
           "OTN Mode.";
       }
     }
     description
       "Port transmit mode type.";
   }
   typedef tunable-wavelength-type {
     type "enumeration" {
       enum "191.15THZ-1568.362NM" {
         value "99";
         description
           "C-band:99-191.15THz-1568.362nm.";
       }
       enum "191.20THZ-1567.952NM" {
         value "98";
         description
           "C-band:98-191.20THz-1567.952nm.";
       }
       enum "191.25THZ-1567.542NM" {
         value "97";
         description
           "C-band:97-191.25THz-1567.542nm.";
       }
       enum "191.30THZ-1567.133NM" {
         value "96";
         description
           "C-band:96-191.30THz-1567.133nm.";
       }
       enum "191.35THZ-1566.723NM" {
         value "95";
         description
           "C-band:95-191.35THz-1566.723nm.";
       }
       enum "191.40THZ-1566.314NM" {
         value "94";
         description
           "C-band:94-191.40THz-1566.314nm.";
       }
       enum "191.45THZ-1565.905NM" {
         value "93";
         description
           "C-band:93-191.45THz-1565.905nm.";
       }
       enum "191.50THZ-1565.496NM" {
         value "92";
         description
           "C-band:92-191.50THz-1565.496nm.";
       }
       enum "191.55THZ-1565.087NM" {
         value "91";
         description
           "C-band:91-191.55THz-1565.087nm.";
       }
       enum "191.60THZ-1564.679NM" {
         value "90";
         description
           "C-band:90-191.60THz-1564.679nm.";
       }
       enum "191.65THZ-1564.271NM" {
         value "89";
         description
           "C-band:89-191.65THz-1564.271nm.";
       }
       enum "191.70THZ-1563.863NM" {
         value "88";
         description
           "C-band:88-191.70THz-1563.863nm.";
       }
       enum "191.75THZ-1563.455NM" {
         value "87";
         description
           "C-band:87-191.75THz-1563.455nm.";
       }
       enum "191.80THZ-1563.047NM" {
         value "86";
         description
           "C-band:86-191.80THz-1563.047nm.";
       }
       enum "191.85THZ-1562.640NM" {
         value "85";
         description
           "C-band:85-191.85THz-1562.640nm.";
       }
       enum "191.90THZ-1562.233NM" {
         value "84";
         description
           "C-band:84-191.90THz-1562.233nm.";
       }
       enum "191.95THZ-1561.826NM" {
         value "83";
         description
           "C-band:83-191.95THz-1561.826nm.";
       }
       enum "192.00THZ-1561.419NM" {
         value "82";
         description
           "C-band:82-192.00THz-1561.419nm.";
       }
       enum "192.05THZ-1561.013NM" {
         value "81";
         description
           "C-band:81-192.05THz-1561.013nm.";
       }
       enum "192.10THZ-1560.606NM" {
         value "80";
         description
           "C-band:80-192.10THz-1560.606nm.";
       }
       enum "192.15THZ-1560.200NM" {
         value "79";
         description
           "C-band:79-192.15THz-1560.200nm.";
       }
       enum "192.20THZ-1559.794NM" {
         value "78";
         description
           "C-band:78-192.20THz-1559.794nm.";
       }
       enum "192.25THZ-1559.389NM" {
         value "77";
         description
           "C-band:77-192.25THz-1559.389nm.";
       }
       enum "192.30THZ-1558.983NM" {
         value "76";
         description
           "C-band:76-192.30THz-1558.983nm.";
       }
       enum "192.35THZ-1558.578NM" {
         value "75";
         description
           "C-band:75-192.35THz-1558.578nm.";
       }
       enum "192.40THZ-1558.173NM" {
         value "74";
         description
           "C-band:74-192.40THz-1558.173nm.";
       }
       enum "192.45THZ-1557.768NM" {
         value "73";
         description
           "C-band:73-192.45THz-1557.768nm.";
       }
       enum "192.50THZ-1557.363NM" {
         value "72";
         description
           "C-band:72-192.50THz-1557.363nm.";
       }
       enum "192.55THZ-1556.959NM" {
         value "71";
         description
           "C-band:71-192.55THz-1556.959nm.";
       }
       enum "192.60THZ-1556.555NM" {
         value "70";
         description
           "C-band:70-192.60THz-1556.555nm.";
       }
       enum "192.65THZ-1556.151NM" {
         value "69";
         description
           "C-band:69-192.65THz-1556.151nm.";
       }
       enum "192.70THZ-1555.747NM" {
         value "68";
         description
           "C-band:68-192.70THz-1555.747nm.";
       }
       enum "192.75THZ-1555.343NM" {
         value "67";
         description
           "C-band:67-192.75THz-1555.343nm.";
       }
       enum "192.80THZ-1554.940NM" {
         value "66";
         description
           "C-band:66-192.80THz-1554.940nm.";
       }
       enum "192.85THZ-1554.537NM" {
         value "65";
         description
           "C-band:65-192.85THz-1554.537nm.";
       }
       enum "192.90THZ-1554.134NM" {
         value "64";
         description
           "C-band:64-192.90THz-1554.134nm.";
       }
       enum "192.95THZ-1553.731NM" {
         value "63";
         description
           "C-band:63-192.95THz-1553.731nm.";
       }
       enum "193.00THZ-1553.329NM" {
         value "62";
         description
           "C-band:62-193.00THz-1553.329nm.";
       }
       enum "193.05THZ-1552.926NM" {
         value "61";
         description
           "C-band:61-193.05THz-1552.926nm.";
       }
       enum "193.10THZ-1552.524NM" {
         value "60";
         description
           "C-band:60-193.10THz-1552.524nm.";
       }
       enum "193.15THZ-1552.122NM" {
         value "59";
         description
           "C-band:59-193.15THz-1552.122nm.";
       }
       enum "193.20THZ-1551.721NM" {
         value "58";
         description
           "C-band:58-193.20THz-1551.721nm.";
       }
       enum "193.25THZ-1551.319NM" {
         value "57";
         description
           "C-band:57-193.25THz-1551.319nm.";
       }
       enum "193.30THZ-1550.918NM" {
         value "56";
         description
           "C-band:56-193.30THz-1550.918nm.";
       }
       enum "193.35THZ-1550.517NM" {
         value "55";
         description
           "C-band:55-193.35THz-1550.517nm.";
       }
       enum "193.40THZ-1550.116NM" {
         value "54";
         description
           "C-band:54-193.40THz-1550.116nm.";
       }
       enum "193.45THZ-1549.715NM" {
         value "53";
         description
           "C-band:53-193.45THz-1549.715nm.";
       }
       enum "193.50THZ-1549.315NM" {
         value "52";
         description
           "C-band:52-193.50THz-1549.315nm.";
       }
       enum "193.55THZ-1548.915NM" {
         value "51";
         description
           "C-band:51-193.55THz-1548.915nm.";
       }
       enum "193.60THZ-1548.515NM" {
         value "50";
         description
           "C-band:50-193.60THz-1548.515nm.";
       }
       enum "193.65THZ-1548.115NM" {
         value "49";
         description
           "C-band:49-193.65THz-1548.115nm.";
       }
       enum "193.70THZ-1547.715NM" {
         value "48";
         description
           "C-band:48-193.70THz-1547.715nm.";
       }
       enum "193.75THZ-1547.316NM" {
         value "47";
         description
           "C-band:47-193.75THz-1547.316nm.";
       }
       enum "193.80THZ-1546.917NM" {
         value "46";
         description
           "C-band:46-193.80THz-1546.917nm.";
       }
       enum "193.85THZ-1546.518NM" {
         value "45";
         description
           "C-band:45-193.85THz-1546.518nm.";
       }
       enum "193.90THZ-1546.119NM" {
         value "44";
         description
           "C-band:44-193.90THz-1546.119nm.";
       }
       enum "193.95THZ-1545.720NM" {
         value "43";
         description
           "C-band:43-193.95THz-1545.720nm.";
       }
       enum "194.00THZ-1545.322NM" {
         value "42";
         description
           "C-band:42-194.00THz-1545.322nm.";
       }
       enum "194.05THZ-1544.924NM" {
         value "41";
         description
           "C-band:41-194.05THz-1544.924nm.";
       }
       enum "194.10THZ-1544.526NM" {
         value "40";
         description
           "C-band:40-194.10THz-1544.526nm.";
       }
       enum "194.15THZ-1544.128NM" {
         value "39";
         description
           "C-band:39-194.15THz-1544.128nm.";
       }
       enum "194.20THZ-1543.730NM" {
         value "38";
         description
           "C-band:38-194.20THz-1543.730nm.";
       }
       enum "194.25THZ-1543.333NM" {
         value "37";
         description
           "C-band:37-194.25THz-1543.333nm.";
       }
       enum "194.30THZ-1542.936NM" {
         value "36";
         description
           "C-band:36-194.30THz-1542.936nm.";
       }
       enum "194.35THZ-1542.539NM" {
         value "35";
         description
           "C-band:35-194.35THz-1542.539nm.";
       }
       enum "194.40THZ-1542.142NM" {
         value "34";
         description
           "C-band:34-194.40THz-1542.142nm.";
       }
       enum "194.45THZ-1541.746NM" {
         value "33";
         description
           "C-band:33-194.45THz-1541.746nm.";
       }
       enum "194.50THZ-1541.349NM" {
         value "32";
         description
           "C-band:32-194.50THz-1541.349nm.";
       }
       enum "194.55THZ-1540.953NM" {
         value "31";
         description
           "C-band:31-194.55THz-1540.953nm.";
       }
       enum "194.60THZ-1540.557NM" {
         value "30";
         description
           "C-band:30-194.60THz-1540.557nm.";
       }
       enum "194.65THZ-1540.162NM" {
         value "29";
         description
           "C-band:29-194.65THz-1540.162nm.";
       }
       enum "194.70THZ-1539.766NM" {
         value "28";
         description
           "C-band:28-194.70THz-1539.766nm.";
       }
       enum "194.75THZ-1539.371NM" {
         value "27";
         description
           "C-band:27-194.75THz-1539.371nm.";
       }
       enum "194.80THZ-1538.976NM" {
         value "26";
         description
           "C-band:26-194.80THz-1538.976nm.";
       }
       enum "194.85THZ-1538.581NM" {
         value "25";
         description
           "C-band:25-194.85THz-1538.581nm.";
       }
       enum "194.90THZ-1538.186NM" {
         value "24";
         description
           "C-band:24-194.90THz-1538.186nm.";
       }
       enum "194.95THZ-1537.792NM" {
         value "23";
         description
           "C-band:23-194.95THz-1537.792nm.";
       }
       enum "195.00THZ-1537.397NM" {
         value "22";
         description
           "C-band:22-195.00THz-1537.397nm.";
       }
       enum "195.05THZ-1537.003NM" {
         value "21";
         description
           "C-band:21-195.05THz-1537.003nm.";
       }
       enum "195.10THZ-1536.609NM" {
         value "20";
         description
           "C-band:20-195.10THz-1536.609nm.";
       }
       enum "195.15THZ-1536.216NM" {
         value "19";
         description
           "C-band:19-195.15THz-1536.216nm.";
       }
       enum "195.20THZ-1535.822NM" {
         value "18";
         description
           "C-band:18-195.20THz-1535.822nm.";
       }
       enum "195.25THZ-1535.429NM" {
         value "17";
         description
           "C-band:17-195.25THz-1535.429nm.";
       }
       enum "195.30THZ-1535.036NM" {
         value "16";
         description
           "C-band:16-195.30THz-1535.036nm.";
       }
       enum "195.35THZ-1534.643NM" {
         value "15";
         description
           "C-band:15-195.35THz-1534.643nm.";
       }
       enum "195.40THZ-1534.250NM" {
         value "14";
         description
           "C-band:14-195.40THz-1534.250nm.";
       }
       enum "195.45THZ-1533.858NM" {
         value "13";
         description
           "C-band:13-195.45THz-1533.858nm.";
       }
       enum "195.50THZ-1533.465NM" {
         value "12";
         description
           "C-band:12-195.50THz-1533.465nm.";
       }
       enum "195.55THZ-1533.073NM" {
         value "11";
         description
           "C-band:11-195.55THz-1533.073nm.";
       }
       enum "195.60THZ-1532.681NM" {
         value "10";
         description
           "C-band:10-195.60THz-1532.681nm.";
       }
       enum "195.65THZ-1532.290NM" {
         value "9";
         description
           "C-band:09-195.65THz-1532.290nm.";
       }
       enum "195.70THZ-1531.898NM" {
         value "8";
         description
           "C-band:08-195.70THz-1531.898nm.";
       }
       enum "195.75THZ-1531.507NM" {
         value "7";
         description
           "C-band:07-195.75THz-1531.507nm.";
       }
       enum "195.80THZ-1531.116NM" {
         value "6";
         description
           "C-band:06-195.80THz-1531.116nm.";
       }
       enum "195.85THZ-1530.725NM" {
         value "5";
         description
           "C-band:05-195.85THz-1530.725nm.";
       }
       enum "195.90THZ-1530.334NM" {
         value "4";
         description
           "C-band:04-195.90THz-1530.334nm.";
       }
       enum "195.95THZ-1529.944NM" {
         value "3";
         description
           "C-band:03-195.95THz-1529.944nm.";
       }
       enum "196.00THZ-1529.553NM" {
         value "2";
         description
           "C-band:02-196.00THz-1529.553nm.";
       }
       enum "196.05THZ-1529.163NM" {
         value "1";
         description
           "C-band:01-196.05THz-1529.163nm.";
       }
       enum "196.10THZ-1528.773NM" {
         value "0";
         description
           "C-band:00-196.10THz-1528.773nm.";
       }
     }
     description
       "Enum of wavelength and frequence.";
   }
   typedef panel-split-ports-split-type {
     type "enumeration" {
       enum "4X10GE" {
         value "1";
         description
           "Four 10G optical fiber ports.";
       }
       enum "1X40GE" {
         value "2";
         description
           "One 40G optical fiber port.";
       }
       enum "1X100GE" {
         value "3";
         description
           "One 100G optical fiber port.";
       }
       enum "10X10GE" {
         value "4";
         description
           "Ten 10G optical fiber ports.";
       }
       enum "4X25GE-NULL" {
         value "5";
         description
           "Four 25GE ports.";
       }
       enum "4X10GE-1X40GE" {
         value "9";
         description
           "Four 10G optical fiber ports and one 40G optical fiber port.";
       }
       enum "4X10GE-4X10GE" {
         value "10";
         description
           "Four 10G optical fiber ports and four 10G optical fiber ports.";
       }
       enum "NULL-1X100GE" {
         value "12";
         description
           "One 100GE port.";
       }
       enum "1X400GE" {
         value "13";
         description
           "One 400GE port.";
       }
       enum "NULL-2X25GE" {
         value "15";
         description
           "Two 25GE port.";
       }
       enum "1X50GE-NULL" {
         value "16";
         description
           "One 50GE port.";
       }
       enum "1X25GE-2X1GE" {
         value "17";
         description
           "One 25G optical fiber port and two 1G optical fiber ports.";
       }
       enum "1X10GE-2X10GE" {
         value "18";
         description
           "One 10G optical fiber port and two 10G optical fiber ports.";
       }
       enum "1X25GE-NULL" {
         value "19";
         description
           "One 25GE port.";
       }
       enum "1X10GE-1X10GE" {
         value "20";
         description
           "1*10GE-1*10GE.";
       }
       enum "ADAPT" {
         value "21";
         description
           "Auto-adapt.";
       }
       enum "4X25GE" {
         value "22";
         description
           "Four 25G optical fiber ports.";
       }
       enum "1X50GE" {
         value "23";
         description
           "One 50G optical fiber port.";
       }
     }
     description
       "Enum of split type.";
   }
   typedef switch-speed-type {
     type "enumeration" {
       enum "1G" {
         value "1";
         description
           "GE mode.";
       }
       enum "10G" {
         value "10";
         description
           "10GE mode.";
       }
       enum "25G" {
         value "25";
         description
           "25GE mode.";
       }
       enum "undo" {
         value "0";
         description
           "Cancel setting.";
       }
     }
     description
       "Enum of switch-speed.";
   }
   typedef fault-process-mode-type {
     type "enumeration" {
       enum "reset" {
         value "0";
         description
           "Reset.";
       }
       enum "isolate" {
         value "1";
         description
           "Isolate.";
       }
     }
     description
       "Card fault process mode type.";
   }
   container pic {
     description
       "Pic Configuration.";
     container panel-split-ports {
       description
         "List of Panel Ports.";
       list panel-split-port {
         ext:generated-by "system";
         ext:operation-exclude "create";
         key "position";
         description
           "Configure Panel Port.";
         leaf position {
           type "string" {
             length "1..32";
           }
           description
             "Panel Port Position. The position is expressed in the format of "+
             "slotID/cardID/portID. For example, 1/0/1. Here 1/0/1 is an "+
             "example. The value may vary with devices.";
         }
         leaf split-type {
           ext:dynamic-default;
           type "panel-split-ports-split-type";
           description
             "Panel port split type. Modifying the configuration affects the "+
             "instances of ports and interfaces. For details about the impact, "+
             "see the description of each enumerated item.";
         }
         container split-ports {
           config "false";
           description
             "List of Split Ports.";
           list port {
             key "split-position";
             description
               "Operational state of Split Port.";
             leaf split-position {
               type "string" {
                 length "1..32";
               }
               description
                 "Split Port Position. The position is expressed in the format "+
                 "of slotID/cardID/portID. For example, 1/0/1. Here 1/0/1 is an "+
                 "example. The value may vary with devices.";
             }
             leaf port-name {
               type "pub-type:if-name";
               description
                 "Split Port Name.";
             }
           }
         }
       }
     }
     container auto-clears {
       description
         "List of Auto Clears.";
       list auto-clear {
         ext:generated-by "system";
         ext:operation-exclude "create";
         key "type";
         description
           "Configure Auto Clear.";
         leaf type {
           type "enumeration" {
             enum "lsrclose" {
               value "7";
               description
                 "Laser Close.";
             }
             enum "physical-mode" {
               value "14";
               description
                 "Physical mode.";
             }
           }
           description
             "Auto Clear Type.";
         }
         leaf status {
           type "enumeration" {
             enum "disabled" {
               value "0";
               description
                 "Disabled.";
             }
             enum "enabled" {
               value "1";
               description
                 "Enabled.";
             }
           }
           default "enabled";
           description
             "Auto Clear Status.";
         }
         leaf time {
           ext:dynamic-default {
             ext:default-value "5" {
               when "../type = 'lsrclose'";
               description
                 "The default value is 5 when type is lsrclose.";
             }
             ext:default-value "20" {
               when "../type = 'physical-mode'";
               description
                 "The default value is 20 when type is physical-mode.";
             }
           }
           type "uint32" {
             range "1..2880";
           }
           units "min";
           description
             "Auto Clear Time.";
         }
       }
     }
     container tad-trans-alarm-if-downs {
       description
         "List of Global TAD Alarm Status Information.";
       list tad-trans-alarm-if-down {
         ext:generated-by "system";
         ext:operation-exclude "create";
         key "port-type alarm-type";
         description
           "Configure Global TAD Alarm Status Information.";
         leaf port-type {
           type "enumeration" {
             enum "wan" {
               value "1";
               description
                 "WAN port type.";
             }
             enum "pos" {
               value "2";
               description
                 "POS port type.";
             }
           }
           description
             "Global TAD Port Type. If the hardware does not support it, "+
             "returning to the current interface does not support it.";
         }
         leaf alarm-type {
           type "enumeration" {
             enum "LOS" {
               value "6";
               description
                 "Loss of Signal.";
             }
             enum "LAIS" {
               value "2";
               description
                 "Line alarm indication Signal.";
             }
             enum "LOF" {
               value "3";
               description
                 "Loss of Frame.";
             }
             enum "OOF" {
               value "9";
               description
                 "Out of Frame.";
             }
             enum "AUAIS" {
               value "0";
               description
                 "Line Alarm Indication Signal.";
             }
             enum "B3TCA" {
               value "1";
               description
                 "B3 Threshold Crossing Alarm.";
             }
             enum "B1TCA" {
               value "40";
               description
                 "B1 Threshold Crossing Alarm.";
             }
             enum "B2TCA" {
               value "41";
               description
                 "B2 Threshold Crossing Alarm.";
             }
             enum "LOM" {
               value "4";
               description
                 "Loss of Tributary Multiframe.";
             }
             enum "LOP" {
               value "5";
               description
                 "Loss of Pointer.";
             }
             enum "LRDI" {
               value "7";
               description
                 "Line Remote Defect Indication.";
             }
             enum "LREI" {
               value "8";
               description
                 "Line Remote Error Indication.";
             }
             enum "PAIS" {
               value "10";
               description
                 "Path Alarm Indication Signal.";
             }
             enum "PRDI" {
               value "11";
               description
                 "Path Remote Defect Indication.";
             }
             enum "PREI" {
               value "12";
               description
                 "Path Remote Error Indication.";
             }
             enum "PPLM" {
               value "13";
               description
                 "Path Payload Mismatch.";
             }
             enum "RDOOL" {
               value "14";
               description
                 "Receive Data Out of Lock.";
             }
             enum "RROOL" {
               value "15";
               description
                 "Receive Reference Out of Lock.";
             }
             enum "SDBERE" {
               value "16";
               description
                 "Signal Degrade Threshold Alarm.";
             }
             enum "SFBERE" {
               value "17";
               description
                 "Signal Fail Threshold Alarm.";
             }
             enum "TROOL" {
               value "18";
               description
                 "Transmit Reference Out of Lock.";
             }
             enum "PUNEQ" {
               value "19";
               description
                 "Path Unequipped Indication.";
             }
             enum "LCD" {
               value "20";
               description
                 "Loss of Code Group Synchronization.";
             }
           }
           description
             "Global TAD Alarm Type. If the hardware does not support it, "+
             "returning to the current interface does not support it.";
         }
         leaf if-down {
           ext:dynamic-default;
           type "boolean";
           description
             "Enable/disable Global TAD Alarm If down.";
         }
       }
     }
     container alarm-ais-inserts {
       description
         "List of Alarm Insert Ais Configuration.";
       list alarm-ais-insert {
         ext:generated-by "system";
         ext:operation-exclude "create";
         key "name";
         description
           "Configure Alarm Insert Ais Configuration.";
         leaf name {
           type "alarm-ais-insert-name";
           description
             "Alarm Name.";
         }
         leaf ais {
           type "boolean";
           default "false";
           description
             "Enable/disable Alarm Insert Ais Enable.";
         }
         leaf rdi {
           type "boolean";
           description
             "Enable/disable Peer Alarm Report RDI Enable.";
         }
       }
     }
     container port-statistics {
       config "false";
       description
         "List of Port statistics.";
       list statistic {
         key "chassis-id board-id port-type";
         description
           "Operational state of Port statistic.";
         leaf chassis-id {
           type "string" {
             length "1..32";
           }
           description
             "Chassis id.";
         }
         leaf board-id {
           type "uint32" {
             range "0..65535";
           }
           description
             "Board id.";
         }
         leaf port-type {
           type "pic-statistic-port-type";
           description
             "Port type.";
         }
         leaf total-port-num {
           type "uint32" {
             range "0..65535";
           }
           description
             "Total port number.";
         }
         leaf phy-up-port-num {
           type "uint32" {
             range "0..65535";
           }
           description
             "Physical up port number.";
         }
       }
     }
   }
   rpc laser-turn {
     ext:node-ref "devm/ports/port";
     description
       "Set port laser.";
     input {
       leaf laser-shutdown {
         type "enumeration" {
           enum "on" {
             value "0";
             description
               "Laser open.";
           }
           enum "off" {
             value "1";
             description
               "Laser close.";
           }
         }
         default "on";
         description
           "Laser open or shut.";
       }
       leaf laser-test-time {
         type "uint32" {
           range "200..30000";
         }
         units "10 ms";
         description
           "Laser open time.";
       }
       leaf port-position {
         type "string" {
           length "1..32";
         }
         mandatory "true";
         description
           "Port position. The position is expressed in the format of slotID/car"+
           "dID/portID. For example, 1/0/1. Here 1/0/1 is an example. The value "+
           "may vary with devices.";
       }
     }
   }
   rpc clear-port-crc-err-alarm {
     ext:node-ref "/devm/ports/port";
     description
       "Clear CRC error alarm.";
     input {
       leaf port-position {
         type "string" {
           length "1..32";
         }
         mandatory "true";
         description
           "Port Position. The position is expressed in the format of slotID/car"+
           "dID/portID. For example, 1/0/1. Here 1/0/1 is an example. The value "+
           "may vary with devices.";
       }
     }
   }
   rpc clear-port-input-err-alarm {
     ext:node-ref "/devm/ports/port";
     description
       "Clear input error alarm.";
     input {
       leaf port-position {
         type "string" {
           length "1..32";
         }
         mandatory "true";
         description
           "Port Position. The position is expressed in the format of slotID/car"+
           "dID/portID. For example, 1/0/1. Here 1/0/1 is an example. The value "+
           "may vary with devices.";
       }
     }
   }
   rpc clear-port-output-err-alarm {
     ext:node-ref "/devm/ports/port";
     description
       "Clear output error alarm.";
     input {
       leaf port-position {
         type "string" {
           length "1..32";
         }
         mandatory "true";
         description
           "Port Position. The position is expressed in the format of slotID/car"+
           "dID/portID. For example, 1/0/1. Here 1/0/1 is an example. The value "+
           "may vary with devices.";
       }
     }
   }
   rpc clear-port-sdh-err-alarm {
     ext:node-ref "/devm/ports/port";
     description
       "Clear sdh error alarm.";
     input {
       leaf port-position {
         type "string" {
           length "1..32";
         }
         mandatory "true";
         description
           "Port Position. The position is expressed in the format of slotID/car"+
           "dID/portID. For example, 1/0/1. Here 1/0/1 is an example. The value "+
           "may vary with devices.";
       }
     }
   }
   rpc clear-port-symbol-err-alarm {
     ext:node-ref "/devm/ports/port";
     description
       "Clear symbol error alarm.";
     input {
       leaf port-position {
         type "string" {
           length "1..32";
         }
         mandatory "true";
         description
           "Port Position. The position is expressed in the format of slotID/car"+
           "dID/portID. For example, 1/0/1. Here 1/0/1 is an example. The value "+
           "may vary with devices.";
       }
     }
   }
   rpc clear-port-trans-alarm {
     ext:node-ref "/devm/ports/port";
     description
       "Clear tad alarm information.";
     input {
       leaf port-position {
         type "string" {
           length "1..32";
         }
         mandatory "true";
         description
           "Port Position. The position is expressed in the format of slotID/car"+
           "dID/portID. For example, 1/0/1. Here 1/0/1 is an example. The value "+
           "may vary with devices.";
       }
     }
   }
   rpc clear-port-rx-pause-err-alarm {
     ext:node-ref "/devm/ports/port";
     description
       "Clear pause-frame error alarm.";
     input {
       leaf port-position {
         type "string" {
           length "1..32";
         }
         mandatory "true";
         description
           "Port Position. The position is expressed in the format of slotID/car"+
           "dID/portID. For example, 1/0/1. Here 1/0/1 is an example. The value "+
           "may vary with devices.";
       }
     }
   }
   rpc test-local-loopback {
     ext:node-ref "/devm:devm/devm:ports/devm:port";
     description
       "Test local Loopback.";
     input {
       leaf port-position {
         type "string" {
           length "1..32";
         }
         mandatory "true";
         description
           "Port Position. The position is expressed in the format of slotID/car"+
           "dID/portID. For example, 1/0/1. Here 1/0/1 is an example. The value "+
           "may vary with devices.";
       }
     }
   }
   augment "/driver:driver/driver:global-attribute" {
     description
       "Global configuration.";
     container global {
       description
         "Configure Ethernet port.";
       leaf hold-off-timer {
         ext:dynamic-default;
         type "uint32" {
           range "0|20..10000";
         }
         units "ms";
         description
           "Global TAD Hold Down Time.";
       }
       leaf hold-up-timer {
         ext:dynamic-default;
         type "uint32" {
           range "0|200..3600000";
         }
         units "ms";
         description
           "Global TAD Hold Up Time.";
       }
       leaf up-hold-time {
         ext:dynamic-default;
         type "uint32" {
           range "0..86400000";
         }
         units "ms";
         description
           "Global Eth Up Hold Time.";
       }
       leaf down-hold-time {
         type "uint32" {
           range "0..86400000";
         }
         units "ms";
         default "0";
         description
           "Global Eth Down Hold Time.";
       }
       leaf crc-enable {
         type "boolean";
         default "true";
         description
           "Enable/disable the crc error monitor.";
       }
       leaf symbol-enable {
         type "boolean";
         default "true";
         description
           "Enable/disable the symbol error monitor.";
       }
       leaf input-enable {
         type "boolean";
         default "true";
         description
           "Enable/disable the input error monitor.";
       }
       leaf output-enable {
         type "boolean";
         default "true";
         description
           "Enable/disable the Output error monitor.";
       }
       leaf sdh-enable {
         type "boolean";
         default "true";
         description
           "Enable/disable the sdh error monitor.";
       }
       leaf bip8-sd-enable {
         type "boolean";
         default "true";
         description
           "Enable/disable the BIP8-SD error monitor.";
       }
       leaf badbytes-enable {
         type "boolean";
         default "true";
         description
           "Enable/disable the Bad-Bytes error monitor.";
       }
       leaf optical-enable {
         type "boolean";
         default "true";
         description
           "Enable/disable the optical module abnormal monitor.";
       }
       leaf tx-pause-enable {
         type "boolean";
         default "true";
         description
           "Enable/disable the tx-pause error monitor.";
       }
       leaf loopback-clear {
         type "boolean";
         default "false";
         description
           "Enable/disable the loop auto-clear function.";
       }
       leaf loopback-clear-period {
         type "uint32" {
           range "1..2880";
         }
         units "min";
         default "5";
         description
           "The period of loop auto-clear function.";
       }
       leaf optical-certified-alarm {
         type "boolean";
         default "true";
         description
           "Enable/disable the trap function for an uncertified optical module.";
       }
       leaf optical-certified-down {
         type "boolean";
         default "false";
         description
           "Enable/disable the down function for an uncertified optical module.";
       }
       leaf non-certified-optical-status-alarm {
         type "boolean";
         default "false";
         description
           "Enable/disable the alarm function for the uncertified optical module"+
           " status.";
       }
       leaf optical-alarm-std-enable {
         type "enumeration" {
           enum "disabled" {
             value "0";
             description
               "Disabled.";
           }
           enum "enabled" {
             value "1";
             description
               "Enabled.";
           }
         }
         default "disabled";
         description
           "Enable or disable the optical module alarm threshold standardization"+
           ".";
       }
       leaf port-bandwidth-type {
         type "enumeration" {
           enum "data-link" {
             value "0";
             description
               "Data link.";
           }
           enum "physical" {
             value "1";
             description
               "Physical.";
           }
         }
         default "data-link";
         description
           "Port Bandwidth Type.";
       }
       leaf driver-mode {
         ext:dynamic-default;
         type "enumeration" {
           enum "default" {
             value "0";
             description
               "Default Mode.";
           }
           enum "lower" {
             value "1";
             description
               "Lower mode.";
           }
           enum "higher" {
             value "2";
             description
               "Higher mode.";
           }
         }
         description
           "E1 driver Mode.";
       }
     }
   }
   augment "/devm:devm/devm:ports/devm:port" {
     description
       "Ports.";
     container ethernet {
       ext:operation-exclude "create";
       description
         "Configure Ethernet port.";
       leaf speed {
         ext:dynamic-default;
         type "eth-speed-type";
         description
           "Speed of an Ethernet port. This leaf needs to be set at the same "+
           "time as other leafs.";
       }
       leaf duplex {
         ext:dynamic-default;
         type "eth-duplex-type";
         description
           "Duplex type of an Ethernet port. This leaf needs to be set at the "+
           "same time as other leafs.";
       }
       leaf negotiation {
         ext:dynamic-default;
         type "enumeration" {
           enum "enabled" {
             value "1";
             description
               "Enabled.";
           }
           enum "disabled" {
             value "0";
             description
               "Disabled.";
           }
         }
         description
           "Auto negotiation on an Ethernet port. This leaf needs to be set at "+
           "the same time as other leafs.";
       }
       leaf negotiation-mode {
         ext:dynamic-default;
         type "port-negotiation-mode-type";
         description
           "Auto negotiation mode. If the hardware does not support it, "+
           "returning to the current interface does not support it.";
       }
       leaf down-hold-time {
         ext:dynamic-default;
         type "uint32" {
           range "0..86400000";
         }
         units "ms";
         description
           "Down hold time.";
       }
       leaf up-hold-time {
         ext:dynamic-default;
         type "uint32" {
           range "0..86400000";
         }
         units "ms";
         description
           "Up hold time.";
       }
       leaf trans-mode {
         ext:dynamic-default;
         type "port-trans-mode-type";
         description
           "Transmit mode of an Ethernet port.";
       }
       leaf speed-switch-mode {
         ext:dynamic-default;
         type "enumeration" {
           enum "manual" {
             value "0";
             description
               "Manual.";
           }
           enum "auto" {
             value "1";
             description
               "Auto.";
           }
         }
         description
           "Port speed switch mode. If the hardware does not support it, "+
           "returning to the current interface does not support it.";
       }
       leaf bit-error {
         ext:dynamic-default;
         when "../trans-mode='otn-mode'";
         type "enumeration" {
           enum "crc" {
             value "0";
             description
               "CRC error.";
           }
           enum "prefec" {
             value "1";
             description
               "Prefec error.";
           }
         }
         description
           "Bit error type. If the hardware does not support it, returning to "+
           "the current interface does not support it.";
       }
       leaf trigger-time {
         ext:dynamic-default;
         when "../trans-mode='otn-mode' and ../bit-error!='crc'";
         type "uint32" {
           range "1..100";
         }
         must "(../trigger-time-type = '200ms' and ../trigger-time < 5) or "+
              "(../trigger-time-type = 'second' and ../trigger-time)";
         description
           "Prefec error detecting cycle.";
       }
       leaf trigger-time-type {
         ext:dynamic-default;
         when "../trans-mode='otn-mode' and ../bit-error!='crc'";
         type "enumeration" {
           enum "second" {
             value "0";
             description
               "Second level.";
           }
           enum "200ms" {
             value "1";
             description
               "Configure 200ms level.";
           }
         }
         must "(../trigger-time-type = '200ms' and ../trigger-time < 5) or "+
              "(../trigger-time-type = 'second' and ../trigger-time)";
         description
           "Prefec error detecting cycle type. If the hardware does not support "+
           "it, returning to the current interface does not support it.";
       }
       leaf tx-power-cfg-type {
         ext:dynamic-default;
         when "../trans-mode='otn-mode'";
         type "enumeration" {
           enum "tx-power-target" {
             value "0";
             description
               "Optical power configurations enable.";
           }
           enum "attenuation" {
             value "1";
             description
               "Optical attenuation configuration enable.";
           }
         }
         description
           "Optical power cfg type. If the hardware does not support it, "+
           "returning to the current interface does not support it.";
       }
       leaf tx-power-target-value {
         ext:dynamic-default;
         when "../trans-mode='otn-mode' and ../tx-power-cfg-type = 'tx-power-tar"+
              "get'";
         type "int32" {
           range "-180..10";
         }
         units "0.1 dB";
         description
           "Optical power target value. If the hardware does not support it, "+
           "returning to the current interface does not support it.";
       }
       leaf fec-mode {
         ext:dynamic-default;
         when "../trans-mode='otn-mode'";
         type "enumeration" {
           enum "standard" {
             value "1";
             description
               "Standard.";
           }
           enum "none" {
             value "0";
             description
               "None.";
           }
           enum "enhanced" {
             value "2";
             description
               "Enhanced.";
           }
           enum "enhanced-i-4" {
             value "4";
             description
               "Enhanced-i-4.";
           }
           enum "enhanced-i-7" {
             value "3";
             description
               "Enhanced-i-7.";
           }
           enum "lhaul-sd" {
             value "5";
             description
               "Lhaul-sd.";
           }
           enum "enhanced-pid" {
             value "8";
             description
               "Enhanced pid.";
           }
           enum "lhaul-sd-pid" {
             value "9";
             description
               "Lhaul sd pid.";
           }
         }
         description
           "Fec mode. If the hardware does not support it, returning to the "+
           "current interface does not support it.";
       }
       leaf eth-fec-mode {
         ext:dynamic-default;
         type "enumeration" {
           enum "standard" {
             value "1";
             description
               "Standard.";
           }
           enum "none" {
             value "2";
             description
               "None.";
           }
           enum "disable" {
             value "0";
             description
               "Disable.";
           }
         }
         description
           "Eth Fec Mode. If the hardware does not support it, returning to the "+
           "current interface does not support it.";
       }
       leaf fec-pre-alm-thrc {
         ext:dynamic-default;
         type "uint32" {
           range "1..999";
         }
         must "../fec-pre-alm-thrp and ../fec-pre-rsum-thrp and ../fec-pre-rsum-"+
              "thrc";
         description
           "PreFec error ratio coefficient. The configuration is delivered when "+
           "the following condition is met: (fec-pre-alm-thrc *10^ fec-pre-rsum-"+
           "thrp) > (fec-pre-rsum-thrc *10^ fec-pre-alm-thrp). If the hardware "+
           "does not support it, returning to the current interface does not "+
           "support it.";
       }
       leaf fec-pre-alm-thrp {
         ext:dynamic-default;
         type "uint32" {
           range "1..8";
         }
         must "../fec-pre-alm-thrc and ../fec-pre-rsum-thrp and ../fec-pre-rsum-"+
              "thrc";
         description
           "PreFec error ratio exponent. The configuration is delivered when the"+
           " following condition is met: (fec-pre-alm-thrc *10^ fec-pre-rsum-thr"+
           "p) > (fec-pre-rsum-thrc *10^ fec-pre-alm-thrp). If the hardware does"+
           " not support it, returning to the current interface does not support"+
           " it.";
       }
       leaf fec-pre-rsum-thrc {
         ext:dynamic-default;
         type "uint32" {
           range "1..999";
         }
         must "../fec-pre-rsum-thrp and ../fec-pre-alm-thrp and ../fec-pre-alm-t"+
              "hrc";
         description
           "For resume-threshold: PreFec error ratio coefficient. The configurat"+
           "ion is delivered when the following condition is met: (fec-pre-alm-t"+
           "hrc *10^ fec-pre-rsum-thrp) > (fec-pre-rsum-thrc *10^ fec-pre-alm-th"+
           "rp). If the hardware does not support it, returning to the current "+
           "interface does not support it.";
       }
       leaf fec-pre-rsum-thrp {
         ext:dynamic-default;
         type "uint32" {
           range "1..9";
         }
         must "../fec-pre-rsum-thrc and ../fec-pre-alm-thrp and ../fec-pre-alm-t"+
              "hrc";
         description
           "For resume-threshold: PreFec error ratio exponent. The configuration"+
           " is delivered when the following condition is met: (fec-pre-alm-thrc"+
           " *10^ fec-pre-rsum-thrp) > (fec-pre-rsum-thrc *10^ fec-pre-alm-thrp)"+
           ". If the hardware does not support it, returning to the current "+
           "interface does not support it.";
       }
       leaf jumbo-frame {
         ext:dynamic-default;
         type "uint32" {
           range "0..4294967295";
         }
         description
           "Maximum packet length of jumbo frames. If the hardware does not "+
           "support it, returning to the current interface does not support it.";
       }
       leaf flowctl {
         ext:dynamic-default;
         type "enumeration" {
           enum "all-enabled" {
             value "3";
             description
               "All Enabled.";
           }
           enum "receive-enabled" {
             value "1";
             description
               "Receive Enabled.";
           }
           enum "send-enabled" {
             value "2";
             description
               "Send Enabled.";
           }
           enum "all-disabled" {
             value "0";
             description
               "All Disabled.";
           }
           enum "default-config" {
             value "9";
             description
               "Default config.";
           }
         }
         description
           "Flow control method of an Ethernet port.";
       }
       leaf gf-media-type {
         ext:dynamic-default;
         type "enumeration" {
           enum "copper" {
             value "3";
             description
               "Copper.";
           }
           enum "fiber100" {
             value "2";
             description
               "Fiber 100M.";
           }
           enum "fiber1000" {
             value "1";
             description
               "Fiber 1000M.";
           }
           enum "auto" {
             value "0";
             description
               "Auto.";
           }
         }
         description
           "Medium type on an Ethernet GF port. This leaf needs to be set at the"+
           " same time as other leafs.";
       }
       leaf hold-up {
         ext:dynamic-default;
         type "enumeration" {
           enum "enabled" {
             value "1";
             description
               "Enabled.";
           }
           enum "disabled" {
             value "0";
             description
               "Disabled.";
           }
         }
         description
           "Whether the hold-up function is configured on a Ethernet port.";
       }
       leaf txipg {
         ext:dynamic-default;
         type "enumeration" {
           enum "shrink" {
             value "0";
             description
               "Shrink.";
           }
           enum "non-shrink" {
             value "1";
             description
               "Non-shrink.";
           }
         }
         description
           "Inter-packet Gap.";
       }
       leaf switch-speed {
         ext:dynamic-default;
         type "switch-speed-type";
         description
           "Switch GE/10GE/25GE. If the hardware does not support it, returning "+
           "to the current interface does not support it.";
       }
       leaf promiscuous-mode {
         ext:dynamic-default;
         type "enumeration" {
           enum "on" {
             value "1";
             description
               "Promiscuous mode on.";
           }
           enum "off" {
             value "0";
             description
               "Promiscuous mode off.";
           }
         }
         description
           "Promiscuous of an Ethernet MGE port.";
       }
       leaf flexphy-speed {
         ext:dynamic-default;
         type "enumeration" {
           enum "50GE" {
             value "50";
             description
               "Configure 50GE.";
           }
           enum "100GE" {
             value "100";
             description
               "Configure 100GE.";
           }
         }
         description
           "Port speed in manual switch mode. If the hardware does not support "+
           "it, returning to the current interface does not support it.";
       }
       leaf attenuation {
         ext:dynamic-default;
         when "../trans-mode='otn-mode' and ../tx-power-cfg-type = 'attenuation'"+
              "";
         type "uint32" {
           range "0..200";
         }
         units "0.1 dB";
         description
           "Optical attenuation. Default values are related to hardware types. "+
           "If the hardware does not support it, returning to the current "+
           "interface does not support it.";
       }
       leaf remote-fault {
         ext:dynamic-default;
         type "enumeration" {
           enum "disable" {
             value "0";
             description
               "Disables the function of sending remote faults to the remote "+
               "end.";
           }
           enum "enable" {
             value "1";
             description
               "Enables the function of sending remote faults to the remote "+
               "end.";
           }
         }
         description
           "Enables or disables the function of sending remote faults to the "+
           "remote end.";
       }
       leaf down-filter {
         ext:dynamic-default;
         type "enumeration" {
           enum "disable" {
             value "0";
             description
               "Disable the interface down filtering.";
           }
           enum "enable" {
             value "1";
             description
               "Enable the interface down filtering.";
           }
         }
         description
           "Controls the interface down filtering.";
       }
       leaf local-fault-status {
         type "enumeration" {
           enum "normal" {
             value "0";
             description
               "Normal.";
           }
           enum "fault" {
             value "1";
             description
               "Fault.";
           }
         }
         config "false";
         description
           "Local fault.";
       }
       leaf romote-fault-status {
         type "enumeration" {
           enum "normal" {
             value "0";
             description
               "Normal.";
           }
           enum "fault" {
             value "1";
             description
               "Fault.";
           }
         }
         config "false";
         description
           "Remote fault.";
       }
       container eth-wan-attr {
         ext:operation-exclude "create";
         when "../trans-mode='wan-mode'";
         description
           "Configure Ethernet port attributes.";
         leaf frame-format {
           ext:dynamic-default;
           type "enumeration" {
             enum "SDH" {
               value "0";
               description
                 "Synchronous Digital Hierarchy.";
             }
             enum "SONET" {
               value "1";
               description
                 "Synchronous Optical Network.";
             }
           }
           description
             "Frame format of an Ethernet WAN port. Default values are related "+
             "to hardware types. If the hardware does not support it, returning "+
             "to the current interface does not support it.";
         }
         leaf j0-mode {
           ext:dynamic-default;
           type "enumeration" {
             enum "1byte" {
               value "1";
               description
                 "Configure 1 byte mode.";
             }
             enum "16byte" {
               value "16";
               description
                 "Configure 16 bytes mode.";
             }
             enum "64byte-or-null-mode" {
               value "64";
               description
                 "Configure 64bytes or null mode.";
             }
           }
           description
             "J0 mode on an Ethernet WAN port.";
         }
         leaf j0-value {
           when "../j0-mode='1byte'";
           type "uint32" {
             range "0..255";
           }
           default "1";
           description
             "Value of j0-mode on an Ethernet WAN port.";
         }
         leaf j0-trace {
           ext:dynamic-default;
           when "../j0-mode='16byte' or ../j0-mode='64byte-or-null-mode'";
           type "string" {
             length "0..62";
           }
           must "(string-length(../j0-trace)<16 and ../j0-mode='16byte') or "+
                "../j0-mode='64byte-or-null-mode'";
           description
             "Description of the j0 mode on an Ethernet WAN port.";
         }
         leaf j1-mode {
           ext:dynamic-default;
           type "enumeration" {
             enum "1byte" {
               value "1";
               description
                 "Configure 1 byte mode.";
             }
             enum "16byte" {
               value "16";
               description
                 "Configure 16 bytes mode.";
             }
             enum "64byte-or-null-mode" {
               value "64";
               description
                 "Configure 64byte or null mode.";
             }
           }
           description
             "J1 mode on an Ethernet WAN port.";
         }
         leaf j1-value {
           when "../j1-mode='1byte'";
           type "uint32" {
             range "0..255";
           }
           default "1";
           description
             "Value of j1-mode on an Ethernet WAN port.";
         }
         leaf j1-trace {
           ext:dynamic-default;
           when "../j1-mode='16byte' or ../j1-mode='64byte-or-null-mode'";
           type "string" {
             length "0..62";
           }
           must "(string-length(../j1-trace)<16 and ../j1-mode='16byte') or "+
                "../j1-mode='64byte-or-null-mode'";
           description
             "Description of the j1 mode on an Ethernet WAN port.";
         }
         leaf c2 {
           ext:dynamic-default;
           type "uint32" {
             range "0..255";
           }
           description
             "C2 mode on an Ethernet WAN port.";
         }
         leaf clock {
           ext:dynamic-default;
           type "enumeration" {
             enum "master" {
               value "0";
               description
                 "Master clock.";
             }
             enum "slave" {
               value "1";
               description
                 "Slave clock.";
             }
           }
           description
             "Active/standby clock on an Ethernet WAN port. Default values are "+
             "related to hardware types. If the hardware does not support it, "+
             "returning to the current interface does not support it.";
         }
         leaf rx-j0-value {
           type "uint32" {
             range "0..127";
           }
           config "false";
           description
             "Receive j0 value.";
         }
         leaf rx-j0-trace {
           type "string" {
             length "0..64";
           }
           config "false";
           description
             "Receive J0 description.";
         }
         leaf rx-j1-value {
           type "uint32" {
             range "0..127";
           }
           config "false";
           description
             "Receive j1 value.";
         }
         leaf rx-j1-trace {
           type "string" {
             length "0..64";
           }
           config "false";
           description
             "Receive J1 description.";
         }
         leaf rx-c2 {
           type "uint32" {
             range "0..255";
           }
           config "false";
           description
             "Receive C2 value.";
         }
         leaf rx-j0-mode {
           type "enumeration" {
             enum "1byte" {
               value "1";
               description
                 "Configure 1byte.";
             }
             enum "16byte" {
               value "16";
               description
                 "Configure 16byte.";
             }
             enum "64byte-or-null-mode" {
               value "64";
               description
                 "Configure 64byte or null mode.";
             }
             enum "peer" {
               value "128";
               description
                 "Peer.";
             }
           }
           config "false";
           description
             "Rx j0 mode on an Ethernet WAN port.";
         }
         leaf rx-j1-mode {
           type "enumeration" {
             enum "1byte" {
               value "1";
               description
                 "Configure 1byte.";
             }
             enum "16byte" {
               value "16";
               description
                 "Configure 16byte.";
             }
             enum "64byte-or-null-mode" {
               value "64";
               description
                 "Configure 64byte or null mode.";
             }
             enum "peer" {
               value "128";
               description
                 "Peer.";
             }
           }
           config "false";
           description
             "Rx j1 mode on an Ethernet WAN port.";
         }
         leaf b1tca {
           type "string" {
             length "1..32";
           }
           config "false";
           description
             "B1TCA value.";
         }
         leaf b2tca {
           type "string" {
             length "1..32";
           }
           config "false";
           description
             "B2TCA value.";
         }
         leaf b3tca {
           type "string" {
             length "1..32";
           }
           config "false";
           description
             "B3TCA value.";
         }
       }
       container fec-error-statistics {
         config "false";
         description
           "Indicates the FEC bit error statistics.";
         leaf bit0-error-count {
           type "uint64";
           description
             "FEC can correct the number of 0bit error.";
         }
         leaf bit1-error-count {
           type "uint64";
           description
             "FEC can correct the number of 1bit error.";
         }
         leaf bit0-and-bit1-error-count {
           type "uint64";
           description
             "FEC can correct the number of 0bit and 1bit error.";
         }
         leaf symbol-error-count {
           type "uint64";
           description
             "FEC can correct the number of symbol error.";
         }
         leaf uncorrectable-error-count {
           type "uint64";
           description
             "Uncorrectable error count.";
         }
         leaf pre-fec {
           type "string" {
             length "1..32";
           }
           description
             "Pre-FEC BER.";
         }
       }
       container local-loopback-result {
         config "false";
         description
           "Operational state of local loopback result test.";
         leaf result {
           type "enumeration" {
             enum "success" {
               value "0";
               description
                 "The test is successful.";
             }
             enum "test-error" {
               value "1";
               description
                 "Loopback detection error.";
             }
             enum "no-test" {
               value "2";
               description
                 "Query without test.";
             }
             enum "test-clashes" {
               value "3";
               description
                 "Loopback detection is not supported. For example, the port is "+
                 "shut down or loopback is configured.";
             }
             enum "test-no-support" {
               value "4";
               description
                 "The device does not support loopback detection.";
             }
           }
           description
             "Test result.";
         }
         leaf last-test-time {
           type "string" {
             length "1..24";
           }
           description
             "Last test time.";
         }
         leaf link-status {
           type "enumeration" {
             enum "down" {
               value "0";
               description
                 "The interface is down.";
             }
             enum "up" {
               value "1";
               description
                 "The interface is up.";
             }
           }
           description
             "Indicates the interface status.";
         }
         leaf crc-error-packet {
           type "boolean";
           description
             "Check whether CRC error packets exist.";
         }
         leaf other-error-packet {
           type "boolean";
           description
             "Check whether there are other error packets, excluding CRC.";
         }
       }
     }
     container laser {
       ext:operation-exclude "create";
       description
         "Configure Laser. Port insertion does not support configuration for "+
         "some optical modules, such as electrical modules.";
       leaf auto-shut-enable {
         ext:dynamic-default;
         type "enumeration" {
           enum "enable" {
             value "1";
             description
               "Laser automatic shutdown enable.";
           }
           enum "disable" {
             value "0";
             description
               "Laser automatic shutdown disable.";
           }
         }
         description
           "Laser auto shutdown.";
       }
       leaf open-time {
         ext:dynamic-default;
         type "uint32" {
           range "100..300";
         }
         units "10 ms";
         description
           "Laser open time.";
       }
       leaf close-time {
         ext:dynamic-default;
         type "uint32" {
           range "200..30000";
         }
         units "10 ms";
         description
           "Laser close time.";
       }
       leaf status {
         type "enumeration" {
           enum "on" {
             value "0";
             description
               "Laser on.";
           }
           enum "off" {
             value "1";
             description
               "Laser off.";
           }
           enum "offline" {
             value "2";
             description
               "Laser offline.";
           }
         }
         config "false";
         description
           "Laser status.";
       }
     }
     container optical-module {
       ext:operation-exclude "create";
       description
         "Configure information about optical transceivers.";
       leaf rx-high-power-warn-en {
         ext:dynamic-default;
         type "boolean";
         description
           "Enable/disable receiving optical power high warning.";
       }
       leaf rx-low-power-warn-en {
         ext:dynamic-default;
         type "boolean";
         description
           "Enable/disable receiving optical power low warning.";
       }
       leaf tx-high-power-warn-en {
         ext:dynamic-default;
         type "boolean";
         description
           "Enable/disable transmit optical power high warning.";
       }
       leaf tx-low-power-warn-en {
         ext:dynamic-default;
         type "boolean";
         description
           "Enable/disable transmit optical power low warning.";
       }
       leaf volt-high-warn-en {
         ext:dynamic-default;
         type "boolean";
         description
           "Enable/disable optical module voltage high warning.";
       }
       leaf volt-low-warn-en {
         ext:dynamic-default;
         type "boolean";
         description
           "Enable/disable optical module voltage low warning.";
       }
       leaf wave-modulation-mode {
         ext:dynamic-default;
         when "../../ethernet/trans-mode='otn-mode'";
         type "enumeration" {
           enum "dqpsk" {
             value "0";
             description
               "Dqpsk.";
           }
           enum "qpsk" {
             value "1";
             description
               "Qpsk.";
           }
         }
         description
           "Lightwave modulation mode. If the hardware does not support it, "+
           "returning to the current interface does not support it.";
       }
       leaf wavelength-channel-number {
         ext:dynamic-default;
         type "tunable-wavelength-type";
         must "not(../tunable-wavelength or ../tunable-frequency)";
         description
           "Tunable optical module wave length. If the hardware does not support"+
           " it, returning to the current interface does not support it.";
       }
       leaf tunable-wavelength {
         ext:dynamic-default;
         type "uint32" {
           range "0..4294967294";
         }
         units "10 fm";
         must "not(../wavelength-channel-number or ../tunable-frequency)";
         description
           "Wavelength value of a tunable optical module. Any two of the "+
           "following cannot be set at the same time: wavelength channel number,"+
           " wavelength value, and frequency value.";
       }
       leaf tunable-frequency {
         ext:dynamic-default;
         type "uint32" {
           range "0..4294967294";
         }
         units "10 MHz";
         must "not(../tunable-wavelength or ../wavelength-channel-number)";
         description
           "Frequency value of a tunable optical module. Any two of the "+
           "following cannot be set at the same time: wavelength channel number,"+
           " wavelength value, and frequency value.";
       }
       leaf signal-dqpsk-tx {
         ext:dynamic-default;
         when "../wave-modulation-mode!='qpsk'";
         type "uint32" {
           range "1..8";
         }
         description
           "Differential quadrature phase shift keying transmit value.";
       }
       leaf signal-dqpsk-rx {
         ext:dynamic-default;
         when "../wave-modulation-mode!='qpsk'";
         type "uint32" {
           range "1..8";
         }
         description
           "Differential quadrature phase shift keying receive value.";
       }
       choice gain-power {
         description
           "Optical module gain or power value.";
         case gain {
           description
             "Optical module gain value.";
           leaf agc-value {
             type "uint32" {
               range "0..65535";
             }
             units "dB";
             description
               "Optical amplifier module gain value. The configuration range "+
               "depends on the type of the optical module.";
           }
         }
         case power {
           description
             "Optical module power value.";
           leaf apc-value {
             type "uint32" {
               range "0..65535";
             }
             units "dBm";
             description
               "Optical amplifier module power value. The configuration range "+
               "depends on the type of the optical module.";
           }
         }
       }
       leaf optical-mode {
         ext:dynamic-default;
         type "enumeration" {
           enum "osnr" {
             value "3";
             description
               "Osnr mode.";
           }
           enum "hsen" {
             value "2";
             description
               "High sensitivity mode.";
           }
         }
         description
           "Switching the optical module mode.";
       }
       leaf vendor-name {
         type "string" {
           length "0..20";
         }
         config "false";
         description
           "Name of an optical transceiver Verder.";
       }
       leaf vendor-pn {
         type "string" {
           length "0..20";
         }
         config "false";
         description
           "Optical Transceiver Verder PN.";
       }
       leaf trans-bw {
         type "string" {
           length "0..16";
         }
         units "Mbit/s";
         config "false";
         description
           "Optical transceiver bandwidth.";
       }
       leaf trans-mode {
         type "enumeration" {
           enum "unknown" {
             value "0";
             description
               "Unknown.";
           }
           enum "single-mode" {
             value "1";
             description
               "Single mode.";
           }
           enum "multi-mode" {
             value "2";
             description
               "Multi mode.";
           }
           enum "copper-mode" {
             value "3";
             description
               "Copper mode.";
           }
         }
         config "false";
         description
           "Optical transceiver transmission mode.";
       }
       leaf hot-plug {
         type "boolean";
         default "true";
         config "false";
         description
           "Hot plug.";
       }
       leaf type {
         type "enumeration" {
           enum "unknown" {
             value "0";
             description
               "Unknown.";
           }
           enum "sc" {
             value "1";
             description
               "Sc.";
           }
           enum "gbic" {
             value "2";
             description
               "Gbic.";
           }
           enum "sfp" {
             value "3";
             description
               "Sfp.";
           }
           enum "esfp" {
             value "4";
             description
               "Esfp.";
           }
           enum "copper" {
             value "5";
             description
               "Copper.";
           }
           enum "xfp" {
             value "6";
             description
               "Xfp.";
           }
           enum "xenpak" {
             value "7";
             description
               "Xenpak.";
           }
           enum "transponder" {
             value "8";
             description
               "Transponder.";
           }
           enum "cfp" {
             value "9";
             description
               "Cfp.";
           }
           enum "smb" {
             value "10";
             description
               "Smb.";
           }
           enum "sfp-plus" {
             value "11";
             description
               "Sfp+.";
           }
           enum "cxp" {
             value "12";
             description
               "Cxp.";
           }
           enum "qsfp" {
             value "13";
             description
               "Qsfp.";
           }
           enum "qsfp-plus" {
             value "14";
             description
               "Qsfp+.";
           }
           enum "cfp2" {
             value "15";
             description
               "Cfp2.";
           }
           enum "dwdmsfp" {
             value "16";
             description
               "Dwdmsfp.";
           }
           enum "msa100glh" {
             value "17";
             description
               "Msa100glh.";
           }
           enum "gps" {
             value "18";
             description
               "Gps.";
           }
           enum "csfp" {
             value "19";
             description
               "Csfp.";
           }
           enum "cfp4" {
             value "20";
             description
               "Cfp4.";
           }
           enum "qsfp28" {
             value "21";
             description
               "Qsfp28.";
           }
           enum "sfp-and-sfp-plus" {
             value "22";
             description
               "Sfp/sfp+.";
           }
           enum "cfp8" {
             value "23";
             description
               "Cfp8.";
           }
           enum "sfp28" {
             value "24";
             description
               "Sfp28.";
           }
           enum "qsfp-dd" {
             value "25";
             description
               "Qsfp-dd.";
           }
           enum "gponsfp" {
             value "26";
             description
               "Gponsfp.";
           }
           enum "cfp2dco" {
             value "27";
             description
               "Cfp2dco.";
           }
           enum "oa" {
             value "30";
             description
               "Optical Amplifier.";
           }
         }
         config "false";
         description
           "Optical type.";
       }
       leaf fiber-type {
         type "enumeration" {
           enum "unknown" {
             value "0";
             description
               "Unknown.";
           }
           enum "sc" {
             value "1";
             description
               "Sc.";
           }
           enum "style-1-copper-connector" {
             value "2";
             description
               "Style-1-copper-connector.";
           }
           enum "style-2-copper-connector" {
             value "3";
             description
               "Style-2-copper-connector.";
           }
           enum "bnc-tnc" {
             value "4";
             description
               "Bnc-tnc.";
           }
           enum "coaxial-headers" {
             value "5";
             description
               "Coaxial-headers.";
           }
           enum "fiber-jack" {
             value "6";
             description
               "Fiber-jack.";
           }
           enum "lc" {
             value "7";
             description
               "Lc.";
           }
           enum "mt-rj" {
             value "8";
             description
               "Mt-rj.";
           }
           enum "mu" {
             value "9";
             description
               "Mu.";
           }
           enum "sg" {
             value "10";
             description
               "Sg.";
           }
           enum "optical-pigtail" {
             value "11";
             description
               "Optical-pigtail.";
           }
           enum "hssdcii" {
             value "12";
             description
               "HssdcII.";
           }
           enum "copper-pigtail" {
             value "13";
             description
               "Copper-pigtail.";
           }
           enum "MPO" {
             value "14";
             description
               "MPO.";
           }
           enum "RJ45" {
             value "16";
             description
               "RJ45.";
           }
           enum "mpo-1x12" {
             value "17";
             description
               "Mpo-1x12.";
           }
           enum "mpo-2x16" {
             value "18";
             description
               "Mpo-2x16.";
           }
           enum "no-separable" {
             value "19";
             description
               "No-separable.";
           }
           enum "mxc-2x16" {
             value "20";
             description
               "Mxc-2x16.";
           }
           enum "cs-optical" {
             value "21";
             description
               "Cs-optical.";
           }
           enum "sn-optical" {
             value "22";
             description
               "Sn-optical.";
           }
           enum "mpo-2x12" {
             value "23";
             description
               "Mpo-2x12.";
           }
           enum "mpo-1x16" {
             value "24";
             description
               "Mpo-1x16.";
           }
           enum "angled-lc" {
             value "25";
             description
               "Angled lc.";
           }
         }
         config "false";
         description
           "Optical fiber type.";
       }
       leaf wavelength {
         type "string" {
           length "0..128";
         }
         units "nm";
         config "false";
         description
           "Wavelength.";
       }
       leaf transmission-distance {
         type "string" {
           length "0..32";
         }
         units "m";
         config "false";
         description
           "Transmission distance.";
       }
       leaf tx-power {
         type "string" {
           length "0..64";
         }
         units "dBm";
         config "false";
         description
           "Transmit power.";
       }
       leaf rx-power {
         type "string" {
           length "0..64";
         }
         units "dBm";
         config "false";
         description
           "Receiving power.";
       }
       leaf rx-high-warn-power {
         type "string" {
           length "0..64";
         }
         units "dBm";
         config "false";
         description
           "Receiving high warning power.";
       }
       leaf rx-low-warn-power {
         type "string" {
           length "0..64";
         }
         units "dBm";
         config "false";
         description
           "Receiving low warning power.";
       }
       leaf tx-high-warn-power {
         type "string" {
           length "0..64";
         }
         units "dBm";
         config "false";
         description
           "Transmit high warning power.";
       }
       leaf tx-low-warn-power {
         type "string" {
           length "0..64";
         }
         units "dBm";
         config "false";
         description
           "Transmit low warning power.";
       }
       leaf rx-high-alarm-power {
         type "string" {
           length "0..64";
         }
         units "dBm";
         config "false";
         description
           "Receiving high alarm power.";
       }
       leaf rx-low-alarm-power {
         type "string" {
           length "0..64";
         }
         units "dBm";
         config "false";
         description
           "Receiving low alarm power.";
       }
       leaf tx-high-alarm-power {
         type "string" {
           length "0..64";
         }
         units "dBm";
         config "false";
         description
           "Transmit high alarm power.";
       }
       leaf tx-low-alarm-power {
         type "string" {
           length "0..64";
         }
         units "dBm";
         config "false";
         description
           "Transmit low alarm power.";
       }
       leaf tunable {
         type "enumeration" {
           enum "not-supported" {
             value "1";
             description
               "Not supported.";
           }
           enum "not-tunable" {
             value "2";
             description
               "Not tunable.";
           }
           enum "tunable" {
             value "3";
             description
               "Tunable.";
           }
           enum "supported" {
             value "4";
             description
               "Supported.";
           }
         }
         config "false";
         description
           "Configure 0ptical module tunable type.";
       }
       leaf chromatic-dispersion {
         type "string" {
           length "0..32";
         }
         config "false";
         description
           "Chromatic dispersion.";
       }
       leaf polarization-mode-dispersion {
         type "string" {
           length "0..32";
         }
         config "false";
         description
           "Polarization mode dispersion.";
       }
       leaf direction-type {
         type "enumeration" {
           enum "not-supported" {
             value "1";
             description
               "Not supported.";
           }
           enum "dual-fiber-bidirection" {
             value "2";
             description
               "Dual fiber bidirectional.";
           }
           enum "single-fiber-bidirectional" {
             value "3";
             description
               "Single fiber bidirectional.";
           }
           enum "dual-fiber-two-port-bidirectional" {
             value "4";
             description
               "Dual-fiber two-port bidirectional.";
           }
         }
         config "false";
         description
           "Configure 0ptical module direction type.";
       }
       leaf total-rx-power {
         type "string" {
           length "0..64";
         }
         units "dBm";
         config "false";
         description
           "Total receive power.";
       }
       leaf total-rx-high-warn {
         type "string" {
           length "0..64";
         }
         units "dBm";
         config "false";
         description
           "Total receive high warning power.";
       }
       leaf total-rx-low-warn {
         type "string" {
           length "0..64";
         }
         units "dBm";
         config "false";
         description
           "Total receive low warning power.";
       }
       leaf total-rx-high-alarm {
         type "string" {
           length "0..64";
         }
         units "dBm";
         config "false";
         description
           "Total receive high alarm power.";
       }
       leaf total-rx-low-alarm {
         type "string" {
           length "0..64";
         }
         units "dBm";
         config "false";
         description
           "Total receive low alarm power.";
       }
       leaf bias {
         type "int32" {
           range "-99999999..99999999";
         }
         units "mA";
         config "false";
         description
           "Optical bias.";
       }
       leaf voltage {
         type "int32" {
           range "-99999999..99999999";
         }
         units "mV";
         config "false";
         description
           "Optical voltage.";
       }
       leaf temperature {
         type "int32" {
           range "-99999999..99999999";
         }
         units "°C";
         config "false";
         description
           "Optical temperature.";
       }
       leaf wavelength-channel-number-status {
         type "tunable-wavelength-type";
         config "false";
         description
           "Tunable optical module wave length.";
       }
       leaf agc-effective-value {
         type "uint32" {
           range "0..65535";
         }
         units "dB";
         config "false";
         description
           "Optical amplifier module gain value.";
       }
       leaf apc-effective-value {
         type "uint32" {
           range "0..65535";
         }
         units "dBm";
         config "false";
         description
           "Optical amplifier module power value.";
       }
       leaf optical-mode-status {
         type "enumeration" {
           enum "osnr" {
             value "3";
             description
               "Osnr mode.";
           }
           enum "hsen" {
             value "2";
             description
               "High sensitivity mode.";
           }
         }
         config "false";
         description
           "The current status of the optical module mode.";
       }
       container channels {
         config "false";
         description
           "List of Optical Channel Information.";
         list channel {
           key "number";
           config "false";
           description
             "Operational state of Optical Channel Information.";
           leaf number {
             type "uint32" {
               range "0..9";
             }
             config "false";
             description
               "Channel number.";
           }
           leaf tx-power {
             type "string" {
               length "0..64";
             }
             units "dBm";
             config "false";
             description
               "Transmit power.";
           }
           leaf rx-power {
             type "string" {
               length "0..64";
             }
             units "dBm";
             config "false";
             description
               "Receive power.";
           }
           leaf wavelength {
             type "string" {
               length "0..64";
             }
             config "false";
             description
               "Wavelength.";
           }
           leaf bias {
             type "string" {
               length "0..64";
             }
             units "mA";
             config "false";
             description
               "Bias current.";
           }
         }
       }
       container wave-mapping {
         config "false";
         description
           "Operational state of Optical Wave Map Information.";
         list wave-map {
           key "index";
           description
             "Operational state of Optical Wave Map Information.";
           leaf index {
             type "uint32" {
               range "0..4294967295";
             }
             description
               "Table index.";
           }
           leaf frequency {
             type "string" {
               length "0..64";
             }
             units "THz";
             description
               "Frequency Value.";
           }
           leaf wavelength {
             type "string" {
               length "0..64";
             }
             units "nm";
             description
               "Wavelength Value.";
           }
         }
       }
     }
     container transmission-alarm {
       ext:operation-exclude "create";
       description
         "Configure TAD Alarm Information.";
       leaf holdoff-timer {
         ext:dynamic-default;
         type "uint32" {
           range "0|20..10000";
         }
         units "ms";
         description
           "TAD Hold Down Time.";
       }
       leaf holdup-timer {
         ext:dynamic-default;
         type "uint32" {
           range "0|200..3600000";
         }
         units "ms";
         description
           "TAD Hold Up Time.";
       }
       leaf threshold-b3tca {
         ext:dynamic-default;
         type "uint32" {
           range "3..9";
         }
         description
           "TAD Alarm B3tca Threshold (x of 10e-x).";
       }
       leaf threshold-b1tca {
         ext:dynamic-default;
         type "uint32" {
           range "3..9";
         }
         description
           "TAD Alarm B1tca Threshold (x of 10e-x).";
       }
       leaf threshold-b2tca {
         ext:dynamic-default;
         type "uint32" {
           range "3..9";
         }
         description
           "TAD Alarm B2tca Threshold (x of 10e-x).";
       }
       leaf threshold-sdbere {
         ext:dynamic-default;
         type "uint32" {
           range "3..9";
         }
         must "../threshold-sdbere >= ../threshold-sfbere";
         description
           "TAD Alarm Sdbere Threshold (x of 10e-x).";
       }
       leaf threshold-sfbere {
         ext:dynamic-default;
         type "uint32" {
           range "3..9";
         }
         must "../threshold-sdbere >= ../threshold-sfbere";
         description
           "TAD Alarm Sfbere Threshold (x of 10e-x).";
       }
       leaf damp-suppress {
         type "uint32" {
           range "2..19999";
         }
         must "((../damp-suppress and ../damp-reuse and ../damp-ceiling and "+
              "../damp-decayok and ../damp-decayng) and ../damp-suppress >= "+
              "../damp-reuse and ../damp-suppress < ../damp-ceiling) or "+
              "\n(not(../damp-suppress) and not(../damp-reuse) and not(../damp-c"+
              "eiling) and not(../damp-decayok) and not(../damp-decayng))";
         description
           "TAD Alarm Damp Suppress Value.";
       }
       leaf damp-reuse {
         type "uint32" {
           range "1..19998";
         }
         must "((../damp-suppress and ../damp-reuse and ../damp-ceiling and "+
              "../damp-decayok and ../damp-decayng) and ../damp-suppress >= "+
              "../damp-reuse) or \n(not(../damp-suppress) and not(../damp-reuse)"+
              " and not(../damp-ceiling) and not(../damp-decayok) and not(../dam"+
              "p-decayng))";
         description
           "TAD Alarm Damping Reuse Value.";
       }
       leaf damp-ceiling {
         type "uint32" {
           range "1001..20000";
         }
         must "((../damp-suppress and ../damp-reuse and ../damp-ceiling and "+
              "../damp-decayok and ../damp-decayng) and ../damp-suppress < "+
              "../damp-ceiling) or \n(not(../damp-suppress) and not(../damp-reus"+
              "e) and not(../damp-ceiling) and not(../damp-decayok) and "+
              "not(../damp-decayng))";
         description
           "TAD Alarm Damping Ceiling Value.";
       }
       leaf damp-decayok {
         type "uint32" {
           range "500..10000";
         }
         units "ms";
         must "(../damp-suppress and ../damp-reuse and ../damp-ceiling and "+
              "../damp-decayok and ../damp-decayng) or \n(not(../damp-suppress) "+
              "and not(../damp-reuse) and not(../damp-ceiling) and not(../damp-d"+
              "ecayok) and not(../damp-decayng))";
         description
           "TAD Alarm OK Half Decay Value.";
       }
       leaf damp-decayng {
         type "uint32" {
           range "500..10000";
         }
         units "ms";
         must "(../damp-suppress and ../damp-reuse and ../damp-ceiling and "+
              "../damp-decayok and ../damp-decayng) or \n(not(../damp-suppress) "+
              "and not(../damp-reuse) and not(../damp-ceiling) and not(../damp-d"+
              "ecayok) and not(../damp-decayng))";
         description
           "TAD Alarm NG Half Decay Value.";
       }
       leaf alm-last-reset-time {
         type "yang:date-and-time";
         config "false";
         description
           "TAD Last Reset Time.";
       }
       leaf filter-function {
         type "boolean";
         default "false";
         config "false";
         description
           "TAD Alarm Filter Function.";
       }
       leaf damping-function {
         type "boolean";
         default "false";
         config "false";
         description
           "TAD Alarm Damping Function.";
       }
       container trans-alarm-ifdowns {
         description
           "List of TAD Alarm Status Information.";
         list trans-alarm-ifdown {
           ext:generated-by "system";
           ext:operation-exclude "create";
           key "alarm-type";
           description
             "Configure TAD Alarm Status Information.";
           leaf alarm-type {
             type "devm-trans-alarm-type";
             description
               "TAD Alarm Type.";
           }
           leaf ifdown {
             ext:dynamic-default;
             type "boolean";
             description
               "Enable/disable TAD Alarm If down. if the ifdown is true, the "+
               "alarm will cause the port down.";
           }
           leaf alarm-status {
             type "boolean";
             default "false";
             config "false";
             description
               "TAD Alarm Status.";
           }
           leaf is-in-filtering {
             type "boolean";
             default "false";
             config "false";
             description
               "TAD Alarm Is In Filtering.";
           }
           leaf is-in-suppressing {
             type "boolean";
             default "false";
             config "false";
             description
               "TAD Alarm Is In Suppressing.";
           }
           leaf is-in-aging {
             type "boolean";
             default "false";
             config "false";
             description
               "TAD Alarm Is In Aging.";
           }
           leaf flapping-count {
             type "uint32";
             config "false";
             description
               "TAD Alarm Flapping Count.";
           }
           leaf suppressing-count {
             type "uint32";
             config "false";
             description
               "TAD Alarm Suppressing Count.";
           }
           leaf figure-of-merit {
             type "string" {
               length "0..16";
             }
             config "false";
             description
               "TAD Alarm Figure Of Merit.";
           }
         }
       }
     }
     container pos {
       ext:operation-exclude "create";
       description
         "Configure Pos port.";
       leaf frame-format {
         ext:dynamic-default;
         type "enumeration" {
           enum "SDH" {
             value "0";
             description
               "Synchronous Digital Hierarchy.";
           }
           enum "SONET" {
             value "1";
             description
               "Synchronous Optical Network.";
           }
         }
         description
           "Frame format of a pos port. If the hardware does not support it, "+
           "returning to the current interface does not support it.";
       }
       leaf crc {
         ext:dynamic-default;
         type "enumeration" {
           enum "16bit" {
             value "0";
             description
               "Configure 16Bit.";
           }
           enum "32bit" {
             value "1";
             description
               "Configure 32Bit.";
           }
         }
         description
           "CRC mode of a pos port, which can be 32 or 64 bytes. If the hardware"+
           " does not support it, returning to the current interface does not "+
           "support it.";
       }
       leaf hold-up {
         ext:dynamic-default;
         type "enumeration" {
           enum "disabled" {
             value "0";
             description
               "Disabled.";
           }
           enum "enabled" {
             value "1";
             description
               "Enabled.";
           }
         }
         description
           "Whether the hold-up function is configured on a pos port.";
       }
       leaf speed {
         ext:dynamic-default;
         type "enumeration" {
           enum "undo" {
             value "0";
             description
               "Undo config.";
           }
           enum "155M" {
             value "1";
             description
               "Configure 155M.";
           }
           enum "622M" {
             value "2";
             description
               "Configure 622M.";
           }
         }
         description
           "Set 155M or 622M portrate. If the hardware does not support it, "+
           "returning to the current interface does not support it.";
       }
       leaf j0-mode {
         ext:dynamic-default;
         type "enumeration" {
           enum "1byte" {
             value "1";
             description
               "Configure 1 byte mode.";
           }
           enum "16byte" {
             value "16";
             description
               "Configure 16 bytes mode.";
           }
           enum "64byte-or-null-mode" {
             value "64";
             description
               "Configure 64bytes or null mode.";
           }
           enum "peer" {
             value "128";
             description
               "Peer.";
           }
         }
         description
           "J0 mode on a pos port.";
       }
       leaf j0-value {
         when "../j0-mode='1byte'";
         type "uint32" {
           range "0..127";
         }
         default "1";
         description
           "Value of j0-mode on a pos port.";
       }
       leaf j0-trace {
         when "../j0-mode='16byte' or ../j0-mode='64byte-or-null-mode'";
         type "string" {
           length "0..62";
         }
         must "(string-length(../j0-trace)>0 and string-length(../j0-trace)<16 "+
              "and ../j0-mode='16byte') or ../j0-mode='64byte-or-null-mode'";
         default "NetEngine";
         description
           "Description of the j0 mode on a pos port.";
       }
       leaf j1-mode {
         ext:dynamic-default;
         type "enumeration" {
           enum "1byte" {
             value "1";
             description
               "Configure 1 byte mode.";
           }
           enum "16byte" {
             value "16";
             description
               "Configure 16 bytes mode.";
           }
           enum "64byte-or-null-mode" {
             value "64";
             description
               "Configure 64byte or null mode.";
           }
           enum "peer" {
             value "128";
             description
               "Peer.";
           }
         }
         description
           "J1 mode on a pos port.";
       }
       leaf j1-value {
         when "../j1-mode='1byte'";
         type "uint32" {
           range "0..127";
         }
         default "1";
         description
           "Value of j1-mode on a pos port.";
       }
       leaf j1-trace {
         when "../j1-mode='16byte' or ../j1-mode='64byte-or-null-mode'";
         type "string" {
           length "0..62";
         }
         must "(string-length(../j1-trace)>0 and string-length(../j1-trace)<16 "+
              "and ../j1-mode='16byte') or ../j1-mode='64byte-or-null-mode'";
         default "NetEngine";
         description
           "Description of the j1 mode on a pos port.";
       }
       leaf c2 {
         ext:dynamic-default;
         type "uint32" {
           range "0..255";
         }
         description
           "C2 mode on a pos port.";
       }
       leaf clock {
         ext:dynamic-default;
         type "enumeration" {
           enum "master" {
             value "0";
             description
               "Master clock.";
           }
           enum "slave" {
             value "1";
             description
               "Slave clock.";
           }
         }
         description
           "Active/standby clock on a pos port. Default values are related to "+
           "hardware types. If the hardware does not support it, returning to "+
           "the current interface does not support it.";
       }
       leaf scramble {
         ext:dynamic-default;
         type "enumeration" {
           enum "enabled" {
             value "3";
             description
               "Enabled.";
           }
           enum "disabled" {
             value "0";
             description
               "Disabled.";
           }
         }
         description
           "Whether the scrambling function is configured on a pos port. Default"+
           " values are related to hardware types. If the hardware does not "+
           "support it, returning to the current interface does not support it.";
       }
       leaf rx-j0-value {
         type "uint32" {
           range "0..127";
         }
         config "false";
         description
           "Receive j0 value.";
       }
       leaf rx-j0-trace {
         type "string" {
           length "0..64";
         }
         config "false";
         description
           "Receive J0 description.";
       }
       leaf rx-j1-value {
         type "uint32" {
           range "0..127";
         }
         config "false";
         description
           "Receive j1 value.";
       }
       leaf rx-j1-trace {
         type "string" {
           length "0..64";
         }
         config "false";
         description
           "Receive J1 description.";
       }
       leaf rx-c2 {
         type "uint32" {
           range "0..255";
         }
         config "false";
         description
           "Receive C2 value.";
       }
       leaf rx-j0-mode {
         type "enumeration" {
           enum "1byte" {
             value "1";
             description
               "Configure 1byte.";
           }
           enum "16byte" {
             value "16";
             description
               "Configure 16byte.";
           }
           enum "64byte-or-null-mode" {
             value "64";
             description
               "Configure 64byte-or-null-mode.";
           }
           enum "peer" {
             value "128";
             description
               "Peer.";
           }
         }
         config "false";
         description
           "Receive J0 mode on a pos port.";
       }
       leaf rx-j1-mode {
         type "enumeration" {
           enum "1byte" {
             value "1";
             description
               "Configure 1byte.";
           }
           enum "16byte" {
             value "16";
             description
               "Configure 16byte.";
           }
           enum "64byte-or-null-mode" {
             value "64";
             description
               "Configure 64byte-or-null-mode.";
           }
           enum "peer" {
             value "128";
             description
               "Peer.";
           }
         }
         config "false";
         description
           "Receive J1 mode on a pos port.";
       }
       leaf b1tca {
         type "string" {
           length "1..32";
         }
         config "false";
         description
           "B1TCA value.";
       }
       leaf b2tca {
         type "string" {
           length "1..32";
         }
         config "false";
         description
           "B2TCA value.";
       }
       leaf b3tca {
         type "string" {
           length "1..32";
         }
         config "false";
         description
           "B3TCA value.";
       }
     }
     container cpos {
       ext:operation-exclude "create";
       description
         "Configure Cpos port.";
       leaf mapping-mode {
         ext:dynamic-default;
         type "enumeration" {
           enum "h-mode" {
             value "0";
             description
               "H-mode.";
           }
           enum "a-mode" {
             value "1";
             description
               "A-mode.";
           }
           enum "l-mode" {
             value "2";
             description
               "L-mode.";
           }
         }
         must "((not(../pic:e1t1s/pic:e1t1/pic:channel-sets)) and ((../mapping-m"+
              "ode='h-mode') or (../mapping-mode='a-mode') or (../mapping-mode='"+
              "l-mode'))) or (../mapping-mode='h-mode')";
         description
           "Mapping mode.";
       }
       leaf frame-format {
         ext:dynamic-default;
         type "enumeration" {
           enum "sdh" {
             value "0";
             description
               "Synchronous Digital Hierarchy.";
           }
           enum "sonet" {
             value "1";
             description
               "Synchronous Optical Network.";
           }
         }
         description
           "Cpos port frame format.";
       }
       leaf multiplex {
         ext:dynamic-default;
         type "enumeration" {
           enum "au-3" {
             value "1";
             description
               "Au-3.";
           }
           enum "au-4" {
             value "0";
             description
               "Au-4.";
           }
         }
         must "((../frame-format='sdh') and ((../multiplex='au-3') or (../multip"+
              "lex='au-4'))) or (../multiplex='au-3')";
         description
           "Multiplex mode. If the hardware does not support it, returning to "+
           "the current interface does not support it.";
       }
       leaf lb-hold-time {
         when "not(../../devm:loopback-mode='noLoopback')";
         type "uint32" {
           range "0..43200";
         }
         units "min";
         default "0";
         description
           "Cpos Port Loopback auto-clear period.";
       }
       leaf hold-up {
         ext:dynamic-default;
         type "enumeration" {
           enum "enabled" {
             value "1";
             description
               "Enabled.";
           }
           enum "disabled" {
             value "0";
             description
               "Disabled.";
           }
         }
         description
           "Whether the hold-up function is configured on a CPOS port.";
       }
       leaf hp-mapping-mode {
         ext:dynamic-default;
         type "enumeration" {
           enum "VC4" {
             value "1";
             description
               "VC4.";
           }
           enum "VC12" {
             value "0";
             description
               "VC12.";
           }
         }
         must "((not(../e1t1s)) and ((../hp-mapping-mode='VC4') or (../hp-mappin"+
              "g-mode='VC12'))) or (../hp-mapping-mode='VC12')";
         description
           "Hp mapping mode. Ports added to APS group are not allowed to be "+
           "configured.";
       }
       leaf ais-flag {
         ext:dynamic-default;
         type "enumeration" {
           enum "enable" {
             value "1";
             description
               "Enable.";
           }
           enum "disable" {
             value "0";
             description
               "Disable.";
           }
         }
         must "../hp-mapping-mode='VC12'";
         description
           "Ais flag. If the hardware does not support it, returning to the "+
           "current interface does not support it. Ports added to LMSP are not "+
           "allowed to be configured.";
       }
       leaf tuais-flag {
         ext:dynamic-default;
         type "enumeration" {
           enum "enable" {
             value "1";
             description
               "Enable.";
           }
           enum "disable" {
             value "0";
             description
               "Disable.";
           }
         }
         must "../hp-mapping-mode='VC12'";
         description
           "Tuais flag. If the hardware does not support it, returning to the "+
           "current interface does not support it. Ports added to LMSP are not "+
           "allowed to be configured. CES/PPP or CES/ATM service mix is not "+
           "supported.";
       }
       leaf j0-mode {
         ext:dynamic-default;
         type "enumeration" {
           enum "SDH" {
             value "0";
             description
               "Synchronous Digital Hierarchy.";
           }
           enum "SONET" {
             value "1";
             description
               "Synchronous Optical Network.";
           }
         }
         description
           "J0 mode on a port.";
       }
       leaf j0-value {
         when "../j0-mode='SONET'";
         type "uint32" {
           range "0..127";
         }
         default "0";
         description
           "Value of j0-mode on a port.";
       }
       leaf j0-trace {
         when "../j0-mode='SDH'";
         type "string" {
           length "1..15";
         }
         default "NetEngine";
         description
           "Description of the j0 mode on a port.";
       }
       leaf j1-mode {
         ext:dynamic-default;
         type "enumeration" {
           enum "1byte" {
             value "1";
             description
               "Configure 1 byte.";
           }
           enum "16byte" {
             value "16";
             description
               "Configure 16 bytes.";
           }
           enum "64byte-or-null-mode" {
             value "64";
             description
               "Configure 64byte-or-null-mode.";
           }
         }
         description
           "J1 mode on a port.";
       }
       leaf j1-value {
         when "../j1-mode='1byte'";
         type "uint32" {
           range "0..127";
         }
         default "1";
         description
           "Value of j1-mode on a port.";
       }
       leaf j1-trace {
         when "../j1-mode='16byte' or ../j1-mode='64byte-or-null-mode'";
         type "string" {
           length "1..62";
         }
         must "(string-length(../j1-trace)<16 and ../j1-mode='16byte') or "+
              "../j1-mode='64byte-or-null-mode'";
         default "NetEngine";
         description
           "Description of the j1 mode on a port.";
       }
       leaf c2 {
         ext:dynamic-default;
         type "uint32" {
           range "0..255";
         }
         description
           "C2 mode on a port.";
       }
       leaf clock {
         ext:dynamic-default;
         type "enumeration" {
           enum "master" {
             value "0";
             description
               "Master.";
           }
           enum "slave" {
             value "1";
             description
               "Slave.";
           }
         }
         description
           "Active/standby clock on a port. If the hardware does not support it,"+
           " returning to the current interface does not support it.";
       }
       leaf flag-space-padding {
         ext:dynamic-default;
         type "enumeration" {
           enum "disable" {
             value "0";
             description
               "Not padding spaces.";
           }
           enum "enable" {
             value "1";
             description
               "Padding spaces.";
           }
         }
         description
           "Whether to padding spaces when the flag is 16-byte-mode or "+
           "64-byte-mode.";
       }
       leaf rx-j0-value {
         type "uint32" {
           range "0..127";
         }
         config "false";
         description
           "Receive j0 value.";
       }
       leaf rx-j0-trace {
         type "string" {
           length "0..64";
         }
         config "false";
         description
           "Receive J0 description.";
       }
       leaf rx-j1-value {
         type "uint32" {
           range "0..127";
         }
         config "false";
         description
           "Receive j1 value.";
       }
       leaf rx-j1-trace {
         type "string" {
           length "0..64";
         }
         config "false";
         description
           "Receive J1 description.";
       }
       leaf rx-c2 {
         type "uint32" {
           range "0..255";
         }
         config "false";
         description
           "RxC2 on a port.";
       }
       container e1t1s {
         when "../hp-mapping-mode='VC12'";
         description
           "List of E1T1 port attributes.";
         list e1t1 {
           ext:generated-by "system";
           ext:operation-exclude "create";
           key "number";
           max-elements "63";
           description
             "Configure E1T1 port attribute.";
           leaf number {
             type "uint32" {
               range "1..63";
             }
             description
               "E1T1 number.";
           }
           leaf work-mode {
             type "enumeration" {
               enum "framed" {
                 value "0";
                 description
                   "Framed.";
               }
               enum "unframed" {
                 value "1";
                 description
                   "Unframed.";
               }
             }
             default "framed";
             description
               "E1T1 Work mode. Configuration is not allowed to join the APS "+
               "group.";
           }
           leaf clock {
             type "enumeration" {
               enum "master" {
                 value "0";
                 description
                   "Master.";
               }
               enum "slave" {
                 value "1";
                 description
                   "Slave.";
               }
               enum "domain" {
                 value "2";
                 description
                   "Domain.";
               }
             }
             default "master";
             description
               "Clock mode.";
           }
           leaf clock-recovery-domain {
             when "../clock='domain'";
             type "uint32" {
               range "1..8";
             }
             status "deprecated";
             description
               "Clock recovery-domain value.";
           }
           leaf clock-master-domain {
             when "not(../clock='master')";
             type "uint32" {
               range "1..32";
             }
             status "deprecated";
             description
               "Clock master-domain value.";
           }
           leaf frame-format {
             when "../work-mode='framed'";
             type "enumeration" {
               enum "no-crc4" {
                 value "0";
                 description
                   "No CRC4.";
               }
               enum "crc4" {
                 value "1";
                 description
                   "CRC4.";
               }
             }
             default "no-crc4";
             description
               "Frame format.";
           }
           leaf loopback {
             type "enumeration" {
               enum "none" {
                 value "0";
                 description
                   "None.";
               }
               enum "local" {
                 value "1";
                 description
                   "Local.";
               }
               enum "remote" {
                 value "2";
                 description
                   "Remote.";
               }
             }
             default "none";
             description
               "Loopback mode.";
           }
           leaf j2-trace {
             type "string" {
               length "1..15";
             }
             default "NetEngine";
             description
               "J2 trace.";
           }
           leaf v5-trace {
             ext:dynamic-default;
             type "uint32" {
               range "0..7";
             }
             description
               "V5trace.";
           }
           leaf auto-clr-period {
             when "not(../loopback='none')";
             type "uint32" {
               range "0..43200";
             }
             units "min";
             default "0";
             description
               "Loopback auto-clear period.";
           }
           leaf rx-j2-trace {
             type "string" {
               length "1..15";
             }
             config "false";
             description
               "Rx j2Trace.";
           }
           container channel-sets {
             when "../work-mode='framed'";
             description
               "List of Channel sets.";
             list channel-set {
               key "number timeslot-list";
               unique "number";
               unique "timeslot-list";
               max-elements "31";
               description
                 "Configure Channel-sets.";
               leaf number {
                 type "uint32" {
                   range "0..30";
                 }
                 description
                   "Set number.";
               }
               leaf timeslot-list {
                 type "string" {
                   length "1..83";
                   pattern "((3[0-1]|[1-2][0-9]|[1-9])(-(3[0-1]|[1-2][0-9]|[1-9]"+
                           "))?(,((3[0-1]|[1-2][0-9]|[1-9])(-(3[0-1]|[1-2][0-9]|"+
                           "[1-9]))?))*)";
                 }
                 description
                   "Timeslot list. The timeslot-list must be integer values "+
                   "([1,31]) or range values separated by ',' or '-'. If the "+
                   "values are separated by '-', they must be in ascending "+
                   "order. For example, correct range values are (1,3,5-12) and "+
                   "incorrect range values are (1,3,12-5).";
               }
             }
           }
         }
       }
     }
     container port-alarm {
       ext:operation-exclude "create";
       description
         "Configure port alarm information.";
       leaf crc-enabled-down {
         ext:dynamic-default;
         type "boolean";
         description
           "Enable/disable CRC error enable down.";
       }
       leaf input-enabled-down {
         ext:dynamic-default;
         type "boolean";
         description
           "Enable/disable input error enable down.";
       }
       leaf input-error-high-threshold {
         ext:dynamic-default;
         type "uint32" {
           range "1..4294967295";
         }
         must "../input-error-high-threshold >= ../input-error-low-threshold";
         description
           "The high threshold of input error alarm threshold. The number of "+
           "error packets counted in the time in interval exceeds this threshold"+
           " will produce input-error alarm.";
       }
       leaf input-error-low-threshold {
         ext:dynamic-default;
         type "uint32" {
           range "1..4294967295";
         }
         must "../input-error-high-threshold >= ../input-error-low-threshold";
         description
           "The low threshold of input error alarm threshold. The number of "+
           "error packets counted in the time in interval less than this "+
           "threshold will recover input-error alarm.";
       }
       leaf input-error-interval {
         ext:dynamic-default;
         type "uint32" {
           range "1..65535";
         }
         units "s";
         description
           "Time interval for statistical input-error alarm.";
       }
       leaf output-enabled-down {
         ext:dynamic-default;
         type "boolean";
         description
           "Enable/disable output error enable down.";
       }
       leaf output-error-high-threshold {
         ext:dynamic-default;
         type "uint32" {
           range "1..4294967295";
         }
         must "../output-error-high-threshold >= ../output-error-low-threshold";
         description
           "The high threshold of output error alarm threshold. The number of "+
           "error packets counted in the time in interval exceeds this threshold"+
           " will produce output-error alarm.";
       }
       leaf output-error-low-threshold {
         ext:dynamic-default;
         type "uint32" {
           range "1..4294967295";
         }
         must "../output-error-high-threshold >= ../output-error-low-threshold";
         description
           "The low threshold of output error alarm threshold. The number of "+
           "error packets counted in the time in interval less than this "+
           "threshold will recover output-error alarm.";
       }
       leaf output-error-interval {
         ext:dynamic-default;
         type "uint32" {
           range "1..65535";
         }
         units "s";
         description
           "Time interval for statistical output-error alarm.";
       }
       leaf phy-updown-en {
         ext:dynamic-default;
         type "boolean";
         description
           "Enable/disable phyUpDownEn.";
       }
       leaf crc-per-cur {
         type "string" {
           length "0..8";
         }
         config "false";
         description
           "Current Value of packet error ratio.";
       }
       container eth-port-alarm {
         ext:operation-exclude "create";
         description
           "Configure ethernet port alarm information.";
         leaf symbol-enabled-down {
           ext:dynamic-default;
           type "boolean";
           description
             "Enable/disable symbol error enable down.";
         }
         leaf symbol-error-high-threshold {
           ext:dynamic-default;
           type "uint32" {
             range "1..4294967295";
           }
           must "../symbol-error-high-threshold >= ../symbol-error-low-threshold"+
                "";
           description
             "The high threshold of symbol error alarm threshold. The number of "+
             "error packets counted in the time in interval exceeds this "+
             "threshold will produce symbol-error alarm.";
         }
         leaf symbol-error-low-threshold {
           ext:dynamic-default;
           type "uint32" {
             range "1..4294967295";
           }
           must "../symbol-error-high-threshold >= ../symbol-error-low-threshold"+
                "";
           description
             "The low threshold of symbol error alarm threshold. The number of "+
             "error packets counted in the time in interval less than this "+
             "threshold will recover symbol-error alarm.";
         }
         leaf symbol-error-interval {
           ext:dynamic-default;
           type "uint32" {
             range "1..65535";
           }
           units "s";
           description
             "Time interval for statistical symbol-error alarm.";
         }
         leaf bip8-sd-enabled-down {
           ext:dynamic-default;
           type "boolean";
           description
             "Enable/disable BIP8-SD error enable down.";
         }
         leaf bip8-sd-error-high-threshold {
           ext:dynamic-default;
           type "uint32" {
             range "6..9";
           }
           description
             "The high threshold of BIP8-SD error alarm threshold (x of 10Ex). "+
             "The number of error packets counted in the time in interval "+
             "exceeds this threshold will produce bip8-sd-error alarm.";
         }
         leaf bad-bytes-threshold {
           ext:dynamic-default;
           type "uint32" {
             range "1..65535";
           }
           description
             "Bad-bytes alarm Threshold.";
         }
         leaf bad-bytes-interval {
           ext:dynamic-default;
           type "uint32" {
             range "1..65535";
           }
           units "s";
           description
             "Time interval for statistical bad-bytes alarm.";
         }
         leaf tx-pause-error-high-threshold {
           ext:dynamic-default;
           type "uint32" {
             range "1..4294967295";
           }
           must "../tx-pause-error-high-threshold >= ../tx-pause-error-low-thres"+
                "hold";
           description
             "The high threshold of tx-pause error alarm threshold. The number "+
             "of error packets counted in the time in interval exceeds this "+
             "threshold will produce tx-pause-error alarm.";
         }
         leaf tx-pause-error-low-threshold {
           ext:dynamic-default;
           type "uint32" {
             range "1..4294967295";
           }
           must "../tx-pause-error-high-threshold >= ../tx-pause-error-low-thres"+
                "hold";
           description
             "The low threshold of tx-pause error alarm threshold. The number of"+
             " error packets counted in the time in interval less than this "+
             "threshold will recover tx-pause-error alarm.";
         }
         leaf tx-pause-error-interval {
           ext:dynamic-default;
           type "uint32" {
             range "1..65535";
           }
           units "s";
           description
             "Time interval for statistical tx-pause-error alarm.";
         }
         leaf rx-pause-error-high-threshold {
           ext:dynamic-default;
           type "uint32" {
             range "1..4294967295";
           }
           must "../rx-pause-error-high-threshold >= ../rx-pause-error-low-thres"+
                "hold";
           description
             "The high threshold of rx-pause error alarm threshold. The number "+
             "of error packets counted in the time in interval exceeds this "+
             "threshold will produce rx-pause-error alarm.";
         }
         leaf rx-pause-error-low-threshold {
           ext:dynamic-default;
           type "uint32" {
             range "1..4294967295";
           }
           must "../rx-pause-error-high-threshold >= ../rx-pause-error-low-thres"+
                "hold";
           description
             "The low threshold of rx-pause error alarm threshold. The number of"+
             " error packets counted in the time in interval less than this "+
             "threshold will recover rx-pause-error alarm.";
         }
         leaf rx-pause-error-interval {
           ext:dynamic-default;
           type "uint32" {
             range "1..65535";
           }
           units "s";
           description
             "Time interval for statistical rx-pause-error alarm.";
         }
       }
       container sdh-port-alarm {
         ext:operation-exclude "create";
         description
           "Configure SDH port alarm information.";
         leaf sdh-enabled-down {
           ext:dynamic-default;
           type "boolean";
           description
             "Enable/disable SDH error enable down.";
         }
         leaf sdh-error-high-threshold {
           ext:dynamic-default;
           type "uint32" {
             range "1..4294967295";
           }
           must "../sdh-error-high-threshold >= ../sdh-error-low-threshold";
           description
             "The high threshold of SDH error alarm threshold. The number of "+
             "error packets counted in the time in interval exceeds this "+
             "threshold will produce sdh-error alarm.";
         }
         leaf sdh-error-low-threshold {
           ext:dynamic-default;
           type "uint32" {
             range "1..4294967295";
           }
           must "../sdh-error-high-threshold >= ../sdh-error-low-threshold";
           description
             "The low threshold of SDH error alarm threshold. The number of "+
             "error packets counted in the time in interval less than this "+
             "threshold will recover sdh-error alarm.";
         }
         leaf sdh-error-interval {
           ext:dynamic-default;
           type "uint32" {
             range "1..65535";
           }
           units "s";
           description
             "Time interval for statistical sdh-error alarm.";
         }
         leaf sdh-b1-err-threshold {
           ext:dynamic-default;
           type "uint32" {
             range "1..65535";
           }
           units "s";
           description
             "B1 Error Threshold.";
         }
         leaf sdh-b2-err-threshold {
           ext:dynamic-default;
           type "uint32" {
             range "1..65535";
           }
           units "s";
           description
             "B2 Error Threshold.";
         }
         leaf sdh-b1-err-interval {
           ext:dynamic-default;
           type "uint32" {
             range "1..65535";
           }
           units "s";
           description
             "B1 error interval.";
         }
         leaf sdh-b2-err-interval {
           ext:dynamic-default;
           type "uint32" {
             range "1..65535";
           }
           units "s";
           description
             "B2 error interval.";
         }
       }
       container pdh-port-alarm {
         ext:operation-exclude "create";
         must "trigger-thres > resume-thres or (not(trigger-thres) and "+
              "not(resume-thres))";
         description
           "Configure PDH port alarm information.";
         leaf trigger-thres {
           ext:dynamic-default;
           type "uint32" {
             range "1..900";
           }
           description
             "The value of pdh-port-alarm trigger-threshold.";
         }
         leaf resume-thres {
           ext:dynamic-default;
           type "uint32" {
             range "1..899";
           }
           description
             "The value of pdh-port-alarm resume-threshold.";
         }
       }
       container crc-mfe-alarm {
         when "../crc-mfs-alarm";
         must "(crc-mfe-alm-thr-coefficient > crc-mfe-rsum-thr-coefficient and "+
              "crc-mfe-alm-thr-power = crc-mfe-rsum-thr-power) or (crc-mfe-alm-t"+
              "hr-power < crc-mfe-rsum-thr-power)";
         presence "Enable mfe alarm threshold.";
         description
           "Enable/disable CRC MFE ALARM.";
         leaf crc-mfe-alm-thr-coefficient {
           ext:dynamic-default;
           type "uint32" {
             range "1..9";
           }
           mandatory "true";
           description
             "Mac fcs exc coefficient (x of xE-y). The range is 1 to 9.";
         }
         leaf crc-mfe-alm-thr-power {
           ext:dynamic-default;
           type "uint32" {
             range "2..5";
           }
           mandatory "true";
           description
             "Mac fcs exc exponent (y of xE-y). The range is 2 to 5.";
         }
         leaf crc-mfe-rsum-thr-coefficient {
           ext:dynamic-default;
           type "uint32" {
             range "1..9";
           }
           mandatory "true";
           description
             "For resume-threshold: mac fcs exc coefficient (x of xE-y). The "+
             "range is 1 to 9.";
         }
         leaf crc-mfe-rsum-thr-power {
           ext:dynamic-default;
           type "uint32" {
             range "2..6";
           }
           mandatory "true";
           description
             "For resume-threshold: mac fcs exc exponent (y of xE-y). The range "+
             "is 2 to 6.";
         }
         leaf crc-mfe-alm-lsp-en {
           ext:dynamic-default;
           type "boolean";
           mandatory "true";
           description
             "Enable/disable configure MFE (mac fcs exc) of crc-error trigger "+
             "LSP.";
         }
       }
       container crc-sample {
         ext:operation-exclude "create";
         when "../crc-per-alarm";
         must "crc-per-child-win-alarm-num <= crc-per-child-win-max-num and "+
              "crc-per-child-win-resume-num <= crc-per-child-win-max-num";
         description
           "Configure crc error windows.";
         leaf crc-per-samp-win-factor {
           ext:dynamic-default;
           type "uint32" {
             range "10..100";
           }
           description
             "Sample window factor.";
         }
         leaf crc-per-child-win-max-num {
           ext:dynamic-default;
           type "uint32" {
             range "10..100";
           }
           description
             "Maximum number of child windows.";
         }
         leaf crc-per-child-win-alarm-num {
           ext:dynamic-default;
           type "uint32" {
             range "1..100";
           }
           description
             "Minimal number of child windows for alarm generating.";
         }
         leaf crc-per-child-win-resume-num {
           ext:dynamic-default;
           type "uint32" {
             range "1..100";
           }
           description
             "Minimal number of child windows for alarm resuming.";
         }
         leaf crc-alg-realtime-factor {
           ext:dynamic-default;
           type "uint32" {
             range "0..10";
           }
           description
             "Realtime factor template for crc-error algorithm.";
         }
       }
       choice alarm-type {
         default "crc-error-threshold";
         description
           "CRC alarm config.";
         case crc-error-threshold {
           description
             "Configure set crc error threshold.";
           container crc-error-threshold {
             description
               "Configure set crc error threshold.";
             leaf crc-error-high {
               ext:dynamic-default;
               type "uint32" {
                 range "1..4294967295";
               }
               must "(../crc-error-high >= ../crc-error-low) and not(../crc-erro"+
                    "r-percent-alm-thr)";
               description
                 "The high threshold of CRC error alarm threshold. The number of"+
                 " error packets counted in the time in interval exceeds this "+
                 "threshold will produce crc-error alarm.";
             }
             leaf crc-error-low {
               ext:dynamic-default;
               type "uint32" {
                 range "1..4294967295";
               }
               must "(../crc-error-high >= ../crc-error-low) and not(../crc-erro"+
                    "r-percent-alm-thr)";
               description
                 "The low threshold of CRC error alarm threshold. The number of "+
                 "error packets counted in the time in interval less than this "+
                 "threshold will recover crc-error alarm.";
             }
             leaf crc-error-interval {
               ext:dynamic-default;
               type "uint32" {
                 range "1..65535";
               }
               units "s";
               description
                 "Time interval for statistical crc-error alarm.";
             }
             leaf crc-shutdown-en {
               ext:dynamic-default;
               type "boolean";
               must "not(../crc-error-percent-alm-thr)";
               description
                 "Enable/disable crc shutdown. The port will shutdown when the "+
                 "number of error packets counted in the time in interval "+
                 "exceeds threshold.";
             }
             leaf crc-error-percent-alm-thr {
               ext:dynamic-default;
               type "uint32" {
                 range "1..100";
               }
               units "%";
               must "not(../crc-error-high) and not(../crc-error-low) and "+
                    "not(../crc-error-interval) and not(../crc-shutdown-en)";
               description
                 "Crc-error alarm percent threshold, Higher than this threshold "+
                 "will produce crc-error alarm, lower than this threshold will "+
                 "recover crc-error alarm.";
             }
           }
         }
         case link-crc {
           description
             "Enable/disable set link quality bit error ratio threshold and crc "+
             "packet-error-ratio alarm threshold.";
           container link-quality {
             must "(link-quality-alm-thr-coefficient > link-quality-rsum-thr-coe"+
                  "fficient and link-quality-alm-thr-power = link-quality-rsum-t"+
                  "hr-power) or (link-quality-alm-thr-power < link-quality-rsum-"+
                  "thr-power)";
             presence "Enable link quality threshold.";
             description
               "Enable/disable set link quality bit error ratio threshold.";
             leaf link-quality-alm-thr-coefficient {
               ext:dynamic-default;
               type "uint32" {
                 range "1..9";
               }
               mandatory "true";
               description
                 "Link-quality alarm bit error ratio trigger coefficient.";
             }
             leaf link-quality-alm-thr-power {
               ext:dynamic-default;
               type "uint32" {
                 range "1..7";
               }
               mandatory "true";
               description
                 "Link-quality alarm bit error ratio trigger power.";
             }
             leaf link-quality-rsum-thr-coefficient {
               ext:dynamic-default;
               type "uint32" {
                 range "1..9";
               }
               mandatory "true";
               description
                 "Link-quality alarm bit error ratio recovery coefficient.";
             }
             leaf link-quality-rsum-thr-power {
               ext:dynamic-default;
               type "uint32" {
                 range "1..7";
               }
               mandatory "true";
               description
                 "Link-quality alarm bit error ratio recovery power.";
             }
           }
           container crc-per-alarm {
             must "((crc-per-alm-thr-coefficient > crc-per-rsum-thr-coefficient "+
                  "and crc-per-alm-thr-power = crc-per-rsum-thr-power) or "+
                  "(crc-per-alm-thr-power < crc-per-rsum-thr-power))";
             must "((crc-per-alm-sec-en='false' and crc-per-alm-lsp-en='true') "+
                  "or (crc-per-alm-sec-en='true' and crc-per-alm-lsp-en='false')"+
                  " or (crc-per-alm-sec-en='false' and crc-per-alm-lsp-en='false"+
                  "'))";
             presence "Enable crc alarm threshold.";
             description
               "Enable/disable set crc packet-error-ratio alarm threshold.";
             leaf crc-per-alm-thr-coefficient {
               type "uint32" {
                 range "1..9";
               }
               mandatory "true";
               description
                 "Packet error ratio coefficient (x of xE-y). The range is 1 to "+
                 "9.";
             }
             leaf crc-per-alm-thr-power {
               type "uint32" {
                 range "1..7";
               }
               mandatory "true";
               description
                 "Packet error ratio exponent (y of xE-y). The range is 1 to 7.";
             }
             leaf crc-per-rsum-thr-coefficient {
               type "uint32" {
                 range "1..9";
               }
               mandatory "true";
               description
                 "For resume-threshold: Packet error ratio coefficient (x of "+
                 "xE-y). The range is 1 to 9.";
             }
             leaf crc-per-rsum-thr-power {
               type "uint32" {
                 range "1..8";
               }
               mandatory "true";
               description
                 "For resume-threshold: Packet error ratio exponent (y of xE-y)."+
                 " The range is 1 to 8.";
             }
             leaf crc-per-alm-lsp-en {
               type "boolean";
               mandatory "true";
               description
                 "Enable/disable configure PER (packet error ratio) of crc-error"+
                 " trigger LSP.";
             }
             leaf crc-per-alm-sec-en {
               type "boolean";
               mandatory "true";
               description
                 "Enable/disable configure PER (packet error ratio) of crc-error"+
                 " trigger section.";
             }
           }
         }
         case crc-mfs-alarm {
           description
             "Enable/disable CRC MFS ALARM.";
           container crc-mfs-alarm {
             must "(crc-mfs-alm-thr-coefficient > crc-mfs-rsum-thr-coefficient "+
                  "and crc-mfs-alm-thr-power = crc-mfs-rsum-thr-power) or "+
                  "(crc-mfs-alm-thr-power < crc-mfs-rsum-thr-power)";
             presence "Enable mfs alarm threshold.";
             description
               "Enable/disable CRC MFS ALARM.";
             leaf crc-mfs-alm-thr-coefficient {
               type "uint32" {
                 range "1..9";
               }
               mandatory "true";
               description
                 "Mac fcs sd coefficient (x of xE-y). The range is 1 to 9.";
             }
             leaf crc-mfs-alm-thr-power {
               type "uint32" {
                 range "5..9";
               }
               mandatory "true";
               description
                 "Mac fcs sd exponent (y of xE-y). The range is 5 to 9.";
             }
             leaf crc-mfs-rsum-thr-coefficient {
               type "uint32" {
                 range "1..9";
               }
               mandatory "true";
               description
                 "For resume-threshold: mac fcs sd coefficient (x of xE-y). The "+
                 "range is 1 to 9.";
             }
             leaf crc-mfs-rsum-thr-power {
               type "uint32" {
                 range "5..10";
               }
               mandatory "true";
               description
                 "For resume-threshold: mac fcs sd exponent (y of xE-y). The "+
                 "range is 5 to 10.";
             }
             leaf crc-mfs-alm-lsp-en {
               type "boolean";
               mandatory "true";
               description
                 "Enable/disable configure MFS (mac fcs sd) of crc-error trigger"+
                 " LSP.";
             }
           }
         }
       }
     }
     container adm-port {
       ext:operation-exclude "create";
       description
         "Configure ADM Port.";
       leaf descriton {
         type "string" {
           length "1..242";
         }
         description
           "Adm port description.";
       }
       leaf conect-relation {
         type "leafref" {
           path "/ifm:ifm/ifm:interfaces/ifm:interface/ifm:name";
         }
         description
           "Connection relation.";
       }
       leaf direction {
         type "string" {
           length "0..8";
         }
         config "false";
         description
           "Direction.";
       }
       leaf wave-band {
         type "string" {
           length "0..8";
         }
         config "false";
         description
           "Wave band.";
       }
       leaf wavelength-num {
         type "string" {
           length "0..8";
         }
         config "false";
         description
           "Wavelength number.";
       }
       leaf tx-wavelength {
         type "string" {
           length "0..8";
         }
         units "nm";
         config "false";
         description
           "Length of wave-TX.";
       }
       leaf rx-wavelength {
         type "string" {
           length "0..8";
         }
         units "nm";
         config "false";
         description
           "Length of wave-RX.";
       }
       leaf tx-wavelength-num {
         type "string" {
           length "0..8";
         }
         config "false";
         description
           "Wave length number tx.";
       }
       leaf rx-wavelength-num {
         type "string" {
           length "0..8";
         }
         config "false";
         description
           "Wave length number rx.";
       }
     }
     container e1t1 {
       ext:operation-exclude "create";
       description
         "Configure E1T1 port.";
       leaf work-mode {
         ext:dynamic-default;
         type "enumeration" {
           enum "framed" {
             value "0";
             description
               "Framed.";
           }
           enum "unframed" {
             value "1";
             description
               "Unframed.";
           }
         }
         description
           "E1T1 work mode.";
       }
       leaf frame-format {
         ext:dynamic-default;
         when "../work-mode='framed'";
         type "enumeration" {
           enum "no-crc4" {
             value "0";
             description
               "No crc4.";
           }
           enum "crc4" {
             value "1";
             description
               "CRC4.";
           }
         }
         description
           "E1T1 port frame format.";
       }
       leaf clock {
         ext:dynamic-default;
         type "enumeration" {
           enum "master" {
             value "0";
             description
               "Master.";
           }
           enum "slave" {
             value "1";
             description
               "Slave.";
           }
         }
         must "(../clock='master' and (../../devm:loopback-mode ='localLoopback'"+
              " or ../../devm:loopback-mode ='noLoopback')) or (../clock='slave'"+
              " and (../../devm:loopback-mode ='remoteLoopback' or ../../devm:lo"+
              "opback-mode ='noLoopback'))";
         description
           "Clock mode.";
       }
       leaf code {
         ext:dynamic-default;
         type "enumeration" {
           enum "hdb3" {
             value "0";
             description
               "Hdb3.";
           }
           enum "ami" {
             value "1";
             description
               "Ami.";
           }
         }
         description
           "Code. If the hardware does not support it, returning to the current "+
           "interface does not support it.";
       }
       leaf loopback-holdtime {
         when "not(../../devm:loopback-mode='noLoopback')";
         type "uint32" {
           range "0..43200";
         }
         units "min";
         default "0";
         description
           "E1T1 Port Loopback auto-clear period.";
       }
       container channel-sets {
         when "../work-mode='framed'";
         description
           "List of Channel sets.";
         list channel-set {
           key "number timeslot-list";
           unique "number";
           unique "timeslot-list";
           max-elements "31";
           description
             "Configure Channel-sets.";
           leaf number {
             type "uint32" {
               range "0..30";
             }
             description
               "Set number.";
           }
           leaf timeslot-list {
             type "string" {
               length "1..83";
               pattern "((3[0-1]|[1-2][0-9]|[1-9])(-(3[0-1]|[1-2][0-9]|[1-9]))?("+
                       ",((3[0-1]|[1-2][0-9]|[1-9])(-(3[0-1]|[1-2][0-9]|[1-9]))?"+
                       "))*)";
             }
             description
               "Timeslot list. The timeslot-list must be integer values ([1,31])"+
               " or range values separated by ',' or '-'. If the values are "+
               "separated by '-', they must be in ascending order. For example, "+
               "correct range values are (1,3,5-12) and incorrect range values "+
               "are (1,3,12-5).";
           }
         }
       }
     }
   }
   augment "/ifm:ifm/ifm:interfaces/ifm:interface/ifm:mib-statistics" {
     description
       "Error packet statistics on an Ethernet interface.";
     container eth-port-err-sts {
       config "false";
       description
         "Operational state of error packet statistics on an Ethernet interface."+
         "";
       leaf rx-pause {
         type "uint64";
         default "0";
         description
           "Receive PAUSE packets.";
       }
       leaf rx-jumbo-octets {
         type "uint64";
         default "0";
         description
           "The packet length is longer than 1518 bytes.";
       }
       leaf rx-crc {
         type "uint64";
         default "0";
         description
           "CRC error packet.";
       }
       leaf rx-symbol {
         type "uint64";
         default "0";
         description
           "Invalid symbol packet.";
       }
       leaf rx-over-run {
         type "uint64";
         default "0";
         description
           "Packet overflowed from the FIFO in the inbound direction.";
       }
       leaf rx-inrange-len {
         type "uint64";
         default "0";
         description
           "Packet with unmatched length.";
       }
       leaf rx-long {
         type "uint64";
         default "0";
         description
           "Oversized packet.";
       }
       leaf rx-jabber {
         type "uint64";
         default "0";
         description
           "CRC error packet whose length is longer than 1518 bytes.";
       }
       leaf rx-alignment {
         type "uint64";
         default "0";
         description
           "Packet whose length is not an integer multiply of 8 bits.";
       }
       leaf rx-fragment {
         type "uint64";
         default "0";
         description
           "CRC packet whose length is shorter than 64 bytes.";
       }
       leaf rx-undersize {
         type "uint64";
         default "0";
         description
           "Packet whose length is shorter than 64 bytes.";
       }
       leaf tx-pause {
         type "uint64";
         default "0";
         description
           "Send PAUSE packets.";
       }
       leaf tx-jumbo-octets {
         type "uint64";
         default "0";
         description
           "The length of a packet sent is longer than 1518 bytes.";
       }
       leaf tx-over-run {
         type "uint64";
         default "0";
         description
           "Overflow statistics in the transmit direction.";
       }
       leaf tx-under-run {
         type "uint64";
         default "0";
         description
           "Underflow statistics in the transmit direction.";
       }
       leaf tx-system {
         type "uint64";
         default "0";
         description
           "There is no EOP or SOP packet.";
       }
       leaf tx-lost {
         type "uint64";
         default "0";
         description
           "Discarded packet in the transmit direction.";
       }
     }
   }
   augment "/lcs:license" {
     description
       "Port basic license.";
     container lcs-ports {
       description
         "List of all Port basic License Information.";
       list port-basic {
         key "position";
         description
           "Configure Port basic License Information.";
         leaf position {
           type "string" {
             length "1..32";
           }
           description
             "Port position. The position is expressed in the format of "+
             "slotID/cardID/portID. For example, 1/0/1. Here 1/0/1 is an "+
             "example. The value may vary with devices.";
         }
         leaf port-band {
           type "enumeration" {
             enum "200G" {
               value "1";
               description
                 "Upgrade to 200G.";
             }
             enum "400G" {
               value "2";
               description
                 "Upgrade to 400G.";
             }
           }
           description
             "Port Bandwidth Type.";
         }
         leaf active-status {
           type "lcs-active-status-type";
           config "false";
           description
             "Activated State.";
         }
       }
     }
     container flexe-ports {
       description
         "List of all FlexE License Information.";
       list port-flexe {
         key "position";
         description
           "Configure FlexE License Information.";
         leaf position {
           type "string" {
             length "1..32";
           }
           description
             "Position. The position is expressed in the format of slotID/cardID"+
             "/portID. For example, 1/0/1. Here 1/0/1 is an example. The value "+
             "may vary with devices.";
         }
         leaf active-status {
           type "lcs-active-status-type";
           config "false";
           description
             "Activated State.";
         }
       }
     }
     container rtus {
       description
         "List of all RTU License Information.";
       list rtu {
         key "position";
         description
           "Configure RTU License Information.";
         leaf position {
           type "string" {
             length "1..32";
           }
           description
             "Position. The position is expressed in the format of slotID. For "+
             "example, 1. Here 1 is an example. The value may vary with "+
             "devices.";
         }
         leaf active-status {
           type "lcs-active-status-type";
           config "false";
           description
             "Activated State.";
         }
       }
     }
   }
   augment "/devm:devm/devm:cards/devm:card" {
     description
       "Flexible card.";
     container card-tdm-param {
       ext:operation-exclude "create";
       description
         "Configure card tdm param.";
       leaf idle-code {
         ext:dynamic-default;
         ext:case-sensitivity "lower-only";
         type "string" {
           length "1..2";
           pattern "\\s*[a-f0-9]+";
         }
         description
           "Idle code.";
       }
       leaf idle-code-e1 {
         ext:dynamic-default;
         type "string" {
           length "1..2";
           pattern "\\s*0|ff";
         }
         description
           "E1 port idle code.";
       }
     }
     container service-mode {
       ext:operation-exclude "create";
       description
         "Configure serviceMode.";
       leaf bandwidth-mode {
         ext:dynamic-default;
         type "enumeration" {
           enum "ETH-28X10GF" {
             value "1";
             description
               "Twenty-eight 10G optical fiber ports.";
           }
           enum "ETH-26X10GF-18XGF" {
             value "2";
             description
               "Twenty-six 10G optical fiber ports and eighteen 1G optical fiber"+
               " ports.";
           }
           enum "ETH-20X10GF-24XGF" {
             value "3";
             description
               "Twenty 10G optical fiber ports and twenty-four 1G optical fiber "+
               "ports.";
           }
           enum "ETH-2X100GE-30X10GF-10XGF" {
             value "4";
             description
               "Two 100G optical fiber ports, thirty 10G optical fiber ports and"+
               " ten 1G optical fiber ports.";
           }
           enum "ETH-2X100GE-26X10GF-14XGF" {
             value "5";
             description
               "Two 100G optical fiber ports, twenty-six 10G optical fiber ports"+
               " and fourteen 1G optical fiber ports.";
           }
           enum "ETH-2X100GE" {
             value "6";
             description
               "Two 100G optical fiber ports.";
           }
           enum "ETH-1X100GE-4X10GF" {
             value "7";
             description
               "One 100G optical fiber port and four 10G optical fiber ports.";
           }
           enum "POS-8X622M" {
             value "12";
             description
               "Eight 622M POS port.";
           }
           enum "POS-4X2.5G" {
             value "13";
             description
               "Four 2.5G POS port.";
           }
           enum "POS-1X10G" {
             value "14";
             description
               "One 10G POS port.";
           }
           enum "POS-8X155M" {
             value "15";
             description
               "Eight 155M POS port.";
           }
         }
         description
           "Bandwidth Mode. Modifying the configuration affects the instances of"+
           " ports and interfaces. For details about the impact, see the "+
           "description of each enumerated item.";
       }
     }
     container port-group-modes {
       description
         "List of switch mode supported by port group.";
       list port-group-mode {
         ext:generated-by "system";
         ext:operation-exclude "create";
         key "port-groupid";
         description
           "Configure switch mode supported by port group.";
         leaf port-groupid {
           type "uint32" {
             range "1..10000";
           }
           description
             "Index of Port Group.";
         }
         leaf port-list {
           type "string" {
             length "0..64";
           }
           config "false";
           description
             "Port list in group.";
         }
         leaf mode-type {
           ext:dynamic-default;
           type "enumeration" {
             enum "25GE-10GE" {
               value "1";
               description
                 "Configure 25GE-10GE.";
             }
             enum "10GE-1GE" {
               value "2";
               description
                 "Configure 10GE-1GE.";
             }
             enum "25GE" {
               value "3";
               description
                 "Configure to 25GE.";
             }
             enum "10GE" {
               value "4";
               description
                 "Configure to 10GE.";
             }
           }
           description
             "Switch mode.";
         }
       }
     }
     container queue-priority {
       ext:operation-exclude "create";
       description
         "Configure MAC Queue Priority Enable.";
       leaf queue-pri-enable {
         ext:dynamic-default;
         type "enumeration" {
           enum "disable" {
             value "0";
             description
               "Disable.";
           }
           enum "enable" {
             value "1";
             description
               "Enable.";
           }
         }
         description
           "MAC Queue Priority Enable.";
       }
     }
     container process-mode {
       ext:operation-exclude "create";
       must "(shield-mode = 'disabled' and process-mode = 'reset') or (shield-mo"+
            "de = 'enabled') or (shield-mode = 'disabled' and not(process-mode))"+
            " or (not(process-mode) or not(shield-mode))";
       description
         "Configure subcard fault process mode.";
       leaf process-mode {
         ext:dynamic-default;
         type "fault-process-mode-type";
         description
           "Card fault process mode.";
       }
       leaf shield-mode {
         ext:dynamic-default;
         type "enumeration" {
           enum "disabled" {
             value "0";
             description
               "Disabled.";
           }
           enum "enabled" {
             value "1";
             description
               "Enabled.";
           }
         }
         description
           "Shield Card-Fault Process-Mode Global-Config.";
       }
       leaf fault-process-mode-status {
         type "fault-process-mode-type";
         config "false";
         description
           "Configure subcard fault process mode.";
       }
     }
     container panel-slots {
       config "false";
       description
         "Operational state of card panel extend slots.";
       leaf slot {
         type "string" {
           length "0..32";
         }
         config "false";
         description
           "Card Panel Slots.";
       }
     }
   }
   augment "/devm:devm/devm:mpu-boards/devm:mpu-board" {
     description
       "Mac set.";
   }
   augment "/devm:devm/devm:lpu-boards/devm:lpu-board" {
     description
       "Mac set.";
   }
   ext:task-name "device-mgr";
 }

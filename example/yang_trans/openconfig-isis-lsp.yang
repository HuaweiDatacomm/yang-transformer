submodule openconfig-isis-lsp {
   belongs-to openconfig-isis {
     prefix "oc-isis";
   }
   import openconfig-extensions {
     prefix "oc-ext";
   }
   organization
     "OpenConfig working group";
   contact
     "OpenConfig working group\nwww.openconfig.net ";
   description
     "This sub-module describes a YANG model for the IS-IS Link State\nDatabase "+
     "(LSDB).\n\nPortions of this code were derived from IETF RFCs relating to "+
     "the\nIS-IS protocol.\nPlease reproduce this note if possible.\nIETF code "+
     "is subject to the following copyright and license:\nCopyright (c) IETF "+
     "Trust and the persons identified as authors of\nthe code.\nAll rights "+
     "reserved.\nRedistribution and use in source and binary forms, with or "+
     "without\nmodification, is permitted pursuant to, and subject to the "+
     "license\nterms contained in, the Simplified BSD License set forth "+
     "in\nSection 4.c of the IETF Trust's Legal Provisions Relating\nto IETF "+
     "Documents (http://trustee.ietf.org/license-info).";
   oc-ext:openconfig-version "0.4.2";
   revision "2018-11-21" {
     description
       "Add OpenConfig module metadata extensions.";
     reference
       "0.4.2";
   }
   revision "2018-06-05" {
     description
       "Fix bugs in when statements.";
     reference
       "0.4.1";
   }
   revision "2018-05-14" {
     description
       "Update LSDB model to correct Extended IS reach TLV\nbug. This change is "+
       "backwards incompatible due to\nadding an additional level of hierarchy "+
       "to support\nmultiple instances of the TLV.";
     reference
       "0.4.0";
   }
   revision "2017-07-26" {
     description
       "Update LSDB and fix bugs.";
     reference
       "0.3.2";
   }
   revision "2017-05-15" {
     description
       "Refactor LSDB.";
     reference
       "0.3.0";
   }
   revision "2017-01-13" {
     description
       "Remove top-level /isis container";
     reference
       "0.2.1";
   }
   revision "2016-12-15" {
     description
       "Add segment routing to IS-IS module";
     reference
       "0.2.0";
   }
   revision "2016-10-18" {
     description
       "Initial revision of IS-IS models.";
     reference
       "0.1.0";
   }
 }

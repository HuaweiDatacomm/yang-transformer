/*
Copyright (C) 2020 Huawei Technologies Co., Ltd. All rights reserved.
*/

 module huawei-bgp-rpd {
   yang-version "1";
   namespace "urn:huawei:yang:huawei-bgp-rpd";
   prefix "bgp-rpd";
   import huawei-extension {
     prefix "ext";
   }
   import huawei-network-instance {
     prefix "ni";
   }
   import huawei-bgp {
     prefix "bgp";
   }
   import huawei-bgp-routing-table {
     prefix "bgp-rt";
   }
   import huawei-pub-type {
     prefix "pub-type";
   }
   organization
     "Huawei Technologies Co., Ltd.";
   contact
     "Huawei Industrial Base\nBantian, Longgang\nShenzhen 518129\nPeople's "+
     "Republic of China\nWebsite: http://www.huawei.com\nEmail: support@huawei.c"+
     "om";
   description
     "Inter-AS routing protocol that exchanges Network Layer Reachability "+
     "Information (NLRI) with other BGP systems.";
   revision "2020-08-30" {
     description
       "Initial revision.";
     reference
       "Huawei private.";
   }
   ext:task-name "bgp";
   augment "/ni:network-instance/ni:instances/ni:instance/bgp:bgp/bgp:base-proce"+
           "ss/bgp:afs/bgp:af" {
     description
       "BGP RPD address family configuration.";
     container rpd {
       when "../bgp:type='rpd'";
       description
         "Configure RPD address family.";
       container common {
         description
           "Configure BGP RPD common options.";
         leaf router-id-filter {
           type "boolean";
           default "true";
           description
             "Enable/disable router ID filter.";
         }
       }
     }
   }
   augment "/ni:network-instance/ni:instances/ni:instance/bgp:bgp/bgp:base-proce"+
           "ss/bgp:peers/bgp:peer/bgp:afs/bgp:af" {
     description
       "BGP RPD address family configuration.";
     container rpd {
       when "../bgp:type = 'rpd'";
       description
         "Configure RPD options.";
       leaf graceful-restart-static-timer {
         type "uint32" {
           range "3600..2147483647";
         }
         units "s";
         description
           "Specifies the maximum time during which a peer waits for a BGP "+
           "session reestablishment.";
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
   }
   augment "/bgp:bgp/bgp:base-process/bgp-rt:bgp-route" {
     description
       "BGP RPD address family routes information.";
     container rpd {
       config "false";
       description
         "Statistics of RPD routes.";
       container statistic {
         description
           "Statistics of BGP routes information of RPD address family.";
         leaf total-number {
           type "uint32";
           description
             "Total number of routes.";
         }
       }
     }
   }
 }

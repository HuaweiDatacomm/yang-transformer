module ietf-yang-schema-mount {
   yang-version "1.1";
   namespace "urn:ietf:params:xml:ns:yang:ietf-yang-schema-mount";
   prefix "yangmnt";
   import ietf-inet-types {
     prefix "inet";
     reference
       "RFC 6991: Common YANG Data Types";
   }
   import ietf-yang-types {
     prefix "yang";
     reference
       "RFC 6991: Common YANG Data Types";
   }
   organization
     "IETF NETMOD (NETCONF Data Modeling Language) Working Group";
   contact
     "WG Web:   <https://datatracker.ietf.org/wg/netmod/>\nWG List:  <mailto:net"+
     "mod@ietf.org>\n\nEditor:   Martin Bjorklund\n          <mailto:mbj@tail-f."+
     "com>\nEditor:   Ladislav Lhotka\n          <mailto:lhotka@nic.cz>";
   description
     "This module defines a YANG extension statement that can be used\nto "+
     "incorporate data models defined in other YANG modules in a\nmodule. It "+
     "also defines operational state data that specify the\noverall structure of"+
     " the data model.\n\nThe key words 'MUST', 'MUST NOT', 'REQUIRED', 'SHALL',"+
     " 'SHALL\nNOT', 'SHOULD', 'SHOULD NOT', 'RECOMMENDED', 'NOT RECOMMENDED',\n"+
     "'MAY', and 'OPTIONAL' in this document are to be interpreted as\ndescribed"+
     " in BCP 14 (RFC 2119) (RFC 8174) when, and only when,\nthey appear in all "+
     "capitals, as shown here.\n\nCopyright (c) 2019 IETF Trust and the persons "+
     "identified as\nauthors of the code. All rights reserved.\n\nRedistribution"+
     " and use in source and binary forms, with or\nwithout modification, is "+
     "permitted pursuant to, and subject to\nthe license terms contained in, the"+
     " Simplified BSD License set\nforth in Section 4.c of the IETF Trust's "+
     "Legal Provisions\nRelating to IETF Documents\n(https://trustee.ietf.org/li"+
     "cense-info).\n\nThis version of this YANG module is part of RFC 8528;\nsee"+
     " the RFC itself for full legal notices.";
   revision "2019-01-14" {
     description
       "Initial revision.";
     reference
       "RFC 8528: YANG Schema Mount";
   }
   extension mount-point {
     argument label;
     description
       "The argument 'label' is a YANG identifier, i.e., it is of the\ntype "+
       "'yang:yang-identifier'.\n\nThe 'mount-point' statement MUST NOT be used "+
       "in a YANG\nversion 1 module, neither explicitly nor via a 'uses'\nstatem"+
       "ent.\nThe 'mount-point' statement MAY be present as a substatement\nof "+
       "'container' and 'list' and MUST NOT be present elsewhere.\nThere MUST "+
       "NOT be more than one 'mount-point' statement in a\ngiven 'container' or "+
       "'list' statement.\n\nIf a mount point is defined within a grouping, its "+
       "label is\nbound to the module where the grouping is used.\n\nA mount "+
       "point defines a place in the node hierarchy where\nother data models may"+
       " be attached. A server that implements a\nmodule with a mount point "+
       "populates the\n'/schema-mounts/mount-point' list with detailed "+
       "information on\nwhich data models are mounted at each mount point.\n\nNo"+
       "te that the 'mount-point' statement does not define a new\ndata node.";
   }
   container schema-mounts {
     config "false";
     description
       "Contains information about the structure of the overall\nmounted data "+
       "model implemented in the server.";
     list namespace {
       key "prefix";
       description
         "This list provides a mapping of namespace prefixes that are\nused in "+
         "XPath expressions of 'parent-reference' leafs to the\ncorresponding "+
         "namespace URI references.";
       leaf prefix {
         type "yang:yang-identifier";
         description
           "Namespace prefix.";
       }
       leaf uri {
         type "inet:uri";
         description
           "Namespace URI reference.";
       }
     }
     list mount-point {
       key "module label";
       description
         "Each entry of this list specifies a schema for a particular\nmount "+
         "point.\n\nEach mount point MUST be defined using the 'mount-point'\nex"+
         "tension in one of the modules listed in the server's\nYANG library "+
         "instance with conformance type 'implement'.";
       leaf module {
         type "yang:yang-identifier";
         description
           "Name of a module containing the mount point.";
       }
       leaf label {
         type "yang:yang-identifier";
         description
           "Label of the mount point defined using the 'mount-point'\nextension."+
           "";
       }
       leaf config {
         type "boolean";
         default "true";
         description
           "If this leaf is set to 'false', then all data nodes in the\nmounted "+
           "schema are read-only ('config false'), regardless\nof their 'config'"+
           " property.";
       }
       choice schema-ref {
         mandatory "true";
         description
           "Alternatives for specifying the schema.";
         container inline {
           presence "A complete self-contained schema is mounted at the\nmount "+
                    "point.";
           description
             "This node indicates that the server has mounted at least\nthe "+
             "module 'ietf-yang-library' at the mount point, and\nits instantiat"+
             "ion provides the information about the\nmounted schema.\n\nDiffere"+
             "nt instances of the mount point may have\ndifferent schemas "+
             "mounted.";
         }
         container shared-schema {
           presence "The mounted schema together with the 'parent-reference'\nma"+
                    "ke up the schema for this mount point.";
           description
             "This node indicates that the server has mounted at least\nthe "+
             "module 'ietf-yang-library' at the mount point, and\nits instantiat"+
             "ion provides the information about the\nmounted schema.  When "+
             "XPath expressions in the mounted\nschema are evaluated, the "+
             "'parent-reference' leaf-list\nis taken into account.\n\nDifferent "+
             "instances of the mount point MUST have the\nsame schema mounted.";
           leaf-list parent-reference {
             type "yang:xpath1.0";
             description
               "Entries of this leaf-list are XPath 1.0 expressions\nthat are "+
               "evaluated in the following context:\n\n- The context node is the"+
               " node in the parent data tree\n  where the mount-point is "+
               "defined.\n\n- The accessible tree is the parent data tree\n  "+
               "*without* any nodes defined in modules that are\n  mounted "+
               "inside the parent schema.\n\n- The context position and context "+
               "size are both equal\n  to 1.\n\n- The set of variable bindings "+
               "is empty.\n\n- The function library is the core function "+
               "library\n  defined in the W3C XPath 1.0 document\n  (http://www."+
               "w3.org/TR/1999/REC-xpath-19991116) and\n  the functions defined "+
               "in Section 10 of RFC 7950.\n\n- The set of namespace declaration"+
               "s is defined by the\n  'namespace' list under 'schema-mounts'.\n"+
               "\nEach XPath expression MUST evaluate to a node-set\n(possibly "+
               "empty).  For the purposes of evaluating\nXPath expressions whose"+
               " context nodes are defined in\nthe mounted schema, the union of "+
               "all these node-sets\ntogether with ancestor nodes are added to "+
               "the\naccessible data tree.\n\nNote that in the case 'ietf-yang-s"+
               "chema-mount' is\nitself mounted, a 'parent-reference' in the "+
               "mounted\nmodule may refer to nodes that were brought into "+
               "the\naccessible tree through a 'parent-reference' in the\nparent"+
               " schema.";
           }
         }
       }
     }
   }
 }

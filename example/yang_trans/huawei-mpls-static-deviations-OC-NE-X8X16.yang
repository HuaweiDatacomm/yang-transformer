/*
Copyright (C) 2020 Huawei Technologies Co., Ltd. All rights reserved.
*/

 module huawei-mpls-static-deviations-OC-NE-X8X16 {
   namespace "urn:huawei:yang:huawei-mpls-static-deviations-OC-NE-X8X16";
   prefix "mpls-static-devs-OC-NE-X8X16";
   import huawei-mpls {
     prefix "mpls";
   }
   import huawei-mpls-static {
     prefix "mpls-static";
   }
   organization
     "Huawei Technologies Co., Ltd.";
   contact
     "Huawei Industrial Base\nBantian, Longgang\nShenzhen 518129\nPeople's "+
     "Republic of China\nWebsite: http://www.huawei.com\nEmail: support@huawei.c"+
     "om";
   description
     "Specifies the multi-protocol label switching protocol.";
   revision "2020-04-18" {
     description
       "Initial revision.";
     reference
       "Huawei private.";
   }
   deviation "/mpls:mpls/mpls-static:static/mpls-static:lsps/mpls-static:lsp/mpl"+
             "s-static:egress/mpls-static:in-label" {
     deviate "replace" {
       type "uint32" {
         range "16..65551";
       }
     }
   }
   deviation "/mpls:mpls/mpls-static:static/mpls-static:lsps/mpls-static:lsp/mpl"+
             "s-static:transit/mpls-static:in-label" {
     deviate "replace" {
       type "uint32" {
         range "16..65551";
       }
     }
   }
 }

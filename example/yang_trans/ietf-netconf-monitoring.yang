module ietf-netconf-monitoring {
   namespace "urn:ietf:params:xml:ns:yang:ietf-netconf-monitoring";
   prefix "ncm";
   import ietf-yang-types {
     prefix "yang";
   }
   import ietf-inet-types {
     prefix "inet";
   }
   organization
     "IETF NETCONF (Network Configuration) Working Group";
   contact
     "WG Web:   <http://tools.ietf.org/wg/netconf/>\nWG List:  <mailto:netconf@i"+
     "etf.org>\n\nWG Chair: Mehmet Ersue\n          <mailto:mehmet.ersue@nsn.com"+
     ">\n\nWG Chair: Bert Wijnen\n          <mailto:bertietf@bwijnen.net>\n\nEdi"+
     "tor:   Mark Scott\n          <mailto:mark.scott@ericsson.com>\n\nEditor:  "+
     " Martin Bjorklund\n          <mailto:mbj@tail-f.com>";
   description
     "NETCONF Monitoring Module.\nAll elements in this module are read-only.\n\n"+
     "Copyright (c) 2010 IETF Trust and the persons identified as\nauthors of "+
     "the code. All rights reserved.\n\nRedistribution and use in source and "+
     "binary forms, with or\nwithout modification, is permitted pursuant to, and"+
     " subject\nto the license terms contained in, the Simplified BSD\n\nLicense"+
     " set forth in Section 4.c of the IETF Trust's\nLegal Provisions Relating "+
     "to IETF Documents\n(http://trustee.ietf.org/license-info).\n\nThis version"+
     " of this YANG module is part of RFC 6022; see\nthe RFC itself for full "+
     "legal notices.";
   revision "2010-10-04" {
     description
       "Initial revision.";
     reference
       "RFC 6022: YANG Module for NETCONF Monitoring";
   }
   typedef netconf-datastore-type {
     type "enumeration" {
       enum "running";
       enum "candidate";
       enum "startup";
     }
     description
       "Enumeration of possible NETCONF datastore types.";
     reference
       "RFC 4741: NETCONF Configuration Protocol";
   }
   identity transport {
     description
       "Base identity for NETCONF transport types.";
   }
   identity netconf-ssh {
     base "transport";
     description
       "NETCONF over Secure Shell (SSH).";
     reference
       "RFC 4742: Using the NETCONF Configuration Protocol\n        over Secure "+
       "SHell (SSH)";
   }
   identity netconf-soap-over-beep {
     base "transport";
     description
       "NETCONF over Simple Object Access Protocol (SOAP) over\nBlocks "+
       "Extensible Exchange Protocol (BEEP).";
     reference
       "RFC 4743: Using NETCONF over the Simple Object\n        Access Protocol "+
       "(SOAP)";
   }
   identity netconf-soap-over-https {
     base "transport";
     description
       "NETCONF over Simple Object Access Protocol (SOAP)\nover Hypertext "+
       "Transfer Protocol Secure (HTTPS).";
     reference
       "RFC 4743: Using NETCONF over the Simple Object\n        Access Protocol "+
       "(SOAP)";
   }
   identity netconf-beep {
     base "transport";
     description
       "NETCONF over Blocks Extensible Exchange Protocol (BEEP).";
     reference
       "RFC 4744: Using the NETCONF Protocol over the\n        Blocks Extensible"+
       " Exchange Protocol (BEEP)";
   }
   identity netconf-tls {
     base "transport";
     description
       "NETCONF over Transport Layer Security (TLS).";
     reference
       "RFC 5539: NETCONF over Transport Layer Security (TLS)";
   }
   identity schema-format {
     description
       "Base identity for data model schema languages.";
   }
   identity xsd {
     base "schema-format";
     description
       "W3C XML Schema Definition.";
     reference
       "W3C REC REC-xmlschema-1-20041028:\nXML Schema Part 1: Structures";
   }
   identity yang {
     base "schema-format";
     description
       "The YANG data modeling language for NETCONF.";
     reference
       "RFC 6020:  YANG - A Data Modeling Language for the\n         Network "+
       "Configuration Protocol (NETCONF)";
   }
   identity yin {
     base "schema-format";
     description
       "The YIN syntax for YANG.";
     reference
       "RFC 6020:  YANG - A Data Modeling Language for the\n         Network "+
       "Configuration Protocol (NETCONF)";
   }
   identity rng {
     base "schema-format";
     description
       "Regular Language for XML Next Generation (RELAX NG).";
     reference
       "ISO/IEC 19757-2:2008: RELAX NG";
   }
   identity rnc {
     base "schema-format";
     description
       "Relax NG Compact Syntax";
     reference
       "ISO/IEC 19757-2:2008: RELAX NG";
   }
   container netconf-state {
     config "false";
     description
       "The netconf-state container is the root of the monitoring\ndata model.";
     container capabilities {
       description
         "Contains the list of NETCONF capabilities supported by the\nserver.";
       leaf-list capability {
         type "inet:uri";
         description
           "List of NETCONF capabilities supported by the server.";
       }
     }
     container datastores {
       description
         "Contains the list of NETCONF configuration datastores.";
       list datastore {
         key "name";
         description
           "List of NETCONF configuration datastores supported by\nthe NETCONF "+
           "server and related information.";
         leaf name {
           type "netconf-datastore-type";
           description
             "Name of the datastore associated with this list entry.";
         }
         container locks {
           presence "This container is present only if the datastore\nis "+
                    "locked.";
           description
             "The NETCONF <lock> and <partial-lock> operations allow\na client "+
             "to lock specific resources in a datastore.  The\nNETCONF server "+
             "will prevent changes to the locked\nresources by all sessions "+
             "except the one that acquired\nthe lock(s).\n\nMonitoring "+
             "information is provided for each datastore\nentry including "+
             "details such as the session that acquired\nthe lock, the type of "+
             "lock (global or partial) and the\nlist of locked resources.  "+
             "Multiple locks per datastore\nare supported.";
           choice lock-type {
             description
               "Indicates if a global lock or a set of partial locks\nare set.";
             container global-lock {
               description
                 "Present if the global lock is set.";
               leaf locked-by-session {
                 type "uint32";
                 mandatory "true";
                 description
                   "The session ID of the session that has locked\nthis "+
                   "resource.  Both a global lock and a partial\nlock MUST "+
                   "contain the NETCONF session-id.\n\nIf the lock is held by a "+
                   "session that is not managed\nby the NETCONF server (e.g., a "+
                   "CLI session), a session\nid of 0 (zero) is reported.";
                 reference
                   "RFC 4741: NETCONF Configuration Protocol";
               }
               leaf locked-time {
                 type "yang:date-and-time";
                 mandatory "true";
                 description
                   "The date and time of when the resource was\nlocked.";
               }
             }
           }
         }
       }
     }
     container schemas {
       description
         "Contains the list of data model schemas supported by the\nserver.";
       list schema {
         key "identifier version format";
         description
           "List of data model schemas supported by the server.";
         leaf identifier {
           type "string";
           description
             "Identifier to uniquely reference the schema.  The\nidentifier is "+
             "used in the <get-schema> operation and may\nbe used for other "+
             "purposes such as file retrieval.\n\nFor modeling languages that "+
             "support or require a data\nmodel name (e.g., YANG module name) the"+
             " identifier MUST\nmatch that name.  For YANG data models, the "+
             "identifier is\nthe name of the module or submodule.  In other "+
             "cases, an\nidentifier such as a filename MAY be used instead.";
         }
         leaf version {
           type "string";
           description
             "Version of the schema supported.  Multiple versions MAY be\nsuppor"+
             "ted simultaneously by a NETCONF server.  Each\nversion MUST be "+
             "reported individually in the schema list,\ni.e., with same "+
             "identifier, possibly different location,\nbut different version.\n"+
             "\nFor YANG data models, version is the value of the most\nrecent "+
             "YANG 'revision' statement in the module or\nsubmodule, or the "+
             "empty string if no 'revision' statement\nis present.";
         }
         leaf format {
           type "identityref" {
             base "schema-format";
           }
           description
             "The data modeling language the schema is written\nin (currently "+
             "xsd, yang, yin, rng, or rnc).\n\nFor YANG data models, 'yang' "+
             "format MUST be supported and\n'yin' format MAY also be provided.";
         }
         leaf namespace {
           type "inet:uri";
           mandatory "true";
           description
             "The XML namespace defined by the data model.\n\nFor YANG data "+
             "models, this is the module's namespace.\nIf the list entry "+
             "describes a submodule, this field\ncontains the namespace of the "+
             "module to which the\nsubmodule belongs.";
         }
         leaf-list location {
           type "union" {
             type "enumeration" {
               enum "NETCONF";
             }
             type "inet:uri";
           }
           description
             "One or more locations from which the schema can be\nretrieved.  "+
             "This list SHOULD contain at least one\nentry per schema.\n\nA "+
             "schema entry may be located on a remote file system\n(e.g., "+
             "reference to file system for ftp retrieval) or\nretrieved directly"+
             " from a server supporting the\n<get-schema> operation (denoted by "+
             "the value 'NETCONF').";
         }
       }
     }
     container sessions {
       description
         "The sessions container includes session-specific data for\nNETCONF "+
         "management sessions.  The session list MUST include\nall currently "+
         "active NETCONF sessions.";
       list session {
         key "session-id";
         description
           "All NETCONF sessions managed by the NETCONF server\nMUST be reported"+
           " in this list.";
         leaf session-id {
           type "uint32" {
             range "1..max";
           }
           description
             "Unique identifier for the session.  This value is the\nNETCONF "+
             "session identifier, as defined in RFC 4741.";
           reference
             "RFC 4741: NETCONF Configuration Protocol";
         }
         leaf transport {
           type "identityref" {
             base "transport";
           }
           mandatory "true";
           description
             "Identifies the transport for each session, e.g.,\n'netconf-ssh', "+
             "'netconf-soap', etc.";
         }
         leaf username {
           type "string";
           mandatory "true";
           description
             "The username is the client identity that was authenticated\nby the"+
             " NETCONF transport protocol.  The algorithm used to\nderive the "+
             "username is NETCONF transport protocol specific\nand in addition "+
             "specific to the authentication mechanism\nused by the NETCONF "+
             "transport protocol.";
         }
         leaf source-host {
           type "inet:host";
           description
             "Host identifier of the NETCONF client.  The value\nreturned is "+
             "implementation specific (e.g., hostname,\nIPv4 address, IPv6 "+
             "address)";
         }
         leaf login-time {
           type "yang:date-and-time";
           mandatory "true";
           description
             "Time at the server at which the session was established.";
         }
         leaf in-rpcs {
           type "yang:zero-based-counter32";
           description
             "Number of correct <rpc> messages received.";
         }
         leaf in-bad-rpcs {
           type "yang:zero-based-counter32";
           description
             "Number of messages received when an <rpc> message was expected,\nt"+
             "hat were not correct <rpc> messages.  This includes XML parse\nerr"+
             "ors and errors on the rpc layer.";
         }
         leaf out-rpc-errors {
           type "yang:zero-based-counter32";
           description
             "Number of <rpc-reply> messages sent that contained an\n<rpc-error>"+
             " element.";
         }
         leaf out-notifications {
           type "yang:zero-based-counter32";
           description
             "Number of <notification> messages sent.";
         }
       }
     }
     container statistics {
       description
         "Statistical data pertaining to the NETCONF server.";
       leaf netconf-start-time {
         type "yang:date-and-time";
         description
           "Date and time at which the management subsystem was\nstarted.";
       }
       leaf in-bad-hellos {
         type "yang:zero-based-counter32";
         description
           "Number of sessions silently dropped because an\ninvalid <hello> "+
           "message was received.  This includes <hello>\nmessages with a "+
           "'session-id' attribute, bad namespace, and\nbad capability "+
           "declarations.";
       }
       leaf in-sessions {
         type "yang:zero-based-counter32";
         description
           "Number of sessions started.  This counter is incremented\nwhen a "+
           "<hello> message with a <session-id> is sent.\n\n'in-sessions' - "+
           "'in-bad-hellos' =\n    'number of correctly started netconf "+
           "sessions'";
       }
       leaf dropped-sessions {
         type "yang:zero-based-counter32";
         description
           "Number of sessions that were abnormally terminated, e.g.,\ndue to "+
           "idle timeout or transport close.  This counter is not\nincremented "+
           "when a session is properly closed by a\n<close-session> operation, "+
           "or killed by a <kill-session>\noperation.";
       }
       leaf in-rpcs {
         type "yang:zero-based-counter32";
         description
           "Number of correct <rpc> messages received.";
       }
       leaf in-bad-rpcs {
         type "yang:zero-based-counter32";
         description
           "Number of messages received when an <rpc> message was expected,\ntha"+
           "t were not correct <rpc> messages.  This includes XML parse\nerrors "+
           "and errors on the rpc layer.";
       }
       leaf out-rpc-errors {
         type "yang:zero-based-counter32";
         description
           "Number of <rpc-reply> messages sent that contained an\n<rpc-error> "+
           "element.";
       }
       leaf out-notifications {
         type "yang:zero-based-counter32";
         description
           "Number of <notification> messages sent.";
       }
     }
   }
   rpc get-schema {
     description
       "This operation is used to retrieve a schema from the\nNETCONF server.\n"+
       "\nPositive Response:\n  The NETCONF server returns the requested "+
       "schema.\n\nNegative Response:\n  If requested schema does not exist, the"+
       " <error-tag> is\n  'invalid-value'.\n\n  If more than one schema matches"+
       " the requested parameters, the\n  <error-tag> is 'operation-failed', and"+
       " <error-app-tag> is\n  'data-not-unique'.";
     input {
       leaf identifier {
         type "string";
         mandatory "true";
         description
           "Identifier for the schema list entry.";
       }
       leaf version {
         type "string";
         description
           "Version of the schema requested.  If this parameter is not\npresent,"+
           " and more than one version of the schema exists on\nthe server, a "+
           "'data-not-unique' error is returned, as\ndescribed above.";
       }
       leaf format {
         type "identityref" {
           base "schema-format";
         }
         description
           "The data modeling language of the schema.  If this\nparameter is not"+
           " present, and more than one formats of\nthe schema exists on the "+
           "server, a 'data-not-unique' error\nis returned, as described above.";
       }
     }
     output {
       anyxml data {
         description
           "Contains the schema content.";
       }
     }
   }
 }

/*
Copyright (C) 2021 Huawei Technologies Co., Ltd. All rights reserved.
*/

 module huawei-said-frame-deviations-OC-NE-X8X16 {
   namespace "urn:huawei:yang:huawei-said-frame-deviations-OC-NE-X8X16";
   prefix "sf-devs-OC-NE-X8X16";
   import huawei-said-frame {
     prefix "sf";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-said-frame module.";
   revision "2021-05-07" {
     description
       "Initial revision.";
     reference
       "Huawei private.";
   }
   typedef said-name-lpu-deviations {
     type "enumeration" {
       enum "ping" {
         value "2";
         description
           "Said ping node.";
       }
       enum "traffic-fail" {
         value "4";
         description
           "Said traffic-fail node.";
       }
       enum "aaa" {
         value "8";
         description
           "Said aaa node.";
       }
       enum "seuloop" {
         value "22";
         description
           "Said seuloop node.";
       }
       enum "reset-board" {
         value "25";
         description
           "Said reset board node.";
       }
     }
     description
       "Said node name lpu deviations.";
   }
   typedef said-name-mpu-deviations {
     type "enumeration" {
       enum "ping-trunk" {
         value "3";
         description
           "Said ping-trunk node.";
       }
       enum "aaa" {
         value "8";
         description
           "Said aaa node.";
       }
       enum "seu-trunk" {
         value "20";
         description
           "Said seu-trunk node.";
       }
       enum "reset-board" {
         value "25";
         description
           "Said reset board node.";
       }
       enum "cfc" {
         value "26";
         description
           "Said cfc node.";
       }
       enum "ipnice" {
         value "28";
         description
           "SAID ipnice node.";
       }
     }
     description
       "Said node name mpu deviations.";
   }
   deviation "/sf:said-frame/sf:lpu-nodes/sf:lpu-node/sf:said-name" {
     deviate "replace" {
       type "sf-devs-OC-NE-X8X16:said-name-lpu-deviations";
     }
   }
   deviation "/sf:said-frame/sf:lpu-nodes/sf:lpu-node/sf:slot-id" {
     deviate "replace" {
       type "leafref" {
         path "/devm:devm/devm:lpu-boards/devm:lpu-board/devm:position";
       }
     }
   }
   deviation "/sf:said-frame/sf:lpunodecfgs/sf:lpunodecfg/sf:said-name" {
     deviate "replace" {
       type "sf-devs-OC-NE-X8X16:said-name-lpu-deviations";
     }
   }
   deviation "/sf:said-frame/sf:lpunodecfgs/sf:lpunodecfg/sf:slot-id" {
     deviate "replace" {
       type "leafref" {
         path "/devm:devm/devm:lpu-boards/devm:lpu-board/devm:position";
       }
     }
   }
   deviation "/sf:said-frame/sf:mpu-nodes/sf:mpu-node/sf:said-name" {
     deviate "replace" {
       type "sf-devs-OC-NE-X8X16:said-name-mpu-deviations";
     }
   }
   deviation "/sf:said-frame/sf:mpunodecfgs/sf:mpunodecfg/sf:said-name" {
     deviate "replace" {
       type "sf-devs-OC-NE-X8X16:said-name-mpu-deviations";
     }
   }
 }

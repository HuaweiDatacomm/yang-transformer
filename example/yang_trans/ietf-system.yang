module ietf-system {
   namespace "urn:ietf:params:xml:ns:yang:ietf-system";
   prefix "sys";
   import ietf-yang-types {
     prefix "yang";
   }
   import ietf-inet-types {
     prefix "inet";
   }
   import ietf-netconf-acm {
     prefix "nacm";
   }
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Andy Bierman\n          <mailto:andy@yumawork"+
     "s.com>\nEditor:   Martin Bjorklund\n          <mailto:mbj@tail-f.com>";
   description
     "This module contains a collection of YANG definitions for the\nconfigurati"+
     "on and identification of some common system\nproperties within a device "+
     "containing a NETCONF server.  This\nincludes data node definitions for "+
     "system identification,\ntime-of-day management, user management, DNS "+
     "resolver\nconfiguration, and some protocol operations for system\nmanageme"+
     "nt.\nCopyright (c) 2014 IETF Trust and the persons identified as\nauthors "+
     "of the code.  All rights reserved.\nRedistribution and use in source and "+
     "binary forms, with or\nwithout modification, is permitted pursuant to, and"+
     " subject\nto the license terms contained in, the Simplified BSD License\ns"+
     "et forth in Section 4.c of the IETF Trust's Legal Provisions\nRelating to "+
     "IETF Documents\n(http://trustee.ietf.org/license-info).\nThis version of "+
     "this YANG module is part of RFC 7317; see\nthe RFC itself for full legal "+
     "notices.";
   revision "2014-08-06" {
     description
       "Initial revision.";
     reference
       "RFC 7317: A YANG Data Model for System Management";
   }
   feature radius {
     description
       "Indicates that the device can be configured as a RADIUS\nclient.";
     reference
       "RFC 2865: Remote Authentication Dial In User Service (RADIUS)";
   }
   feature authentication {
     description
       "Indicates that the device supports configuration of\nuser authentication"+
       ".";
   }
   feature local-users {
     if-feature "authentication";
     description
       "Indicates that the device supports configuration of\nlocal user "+
       "authentication.";
   }
   feature radius-authentication {
     if-feature "radius";
     if-feature "authentication";
     description
       "Indicates that the device supports configuration of user\nauthentication"+
       " over RADIUS.";
     reference
       "RFC 2865: Remote Authentication Dial In User Service (RADIUS)\nRFC 5607:"+
       " Remote Authentication Dial-In User Service (RADIUS)\n          "+
       "Authorization for Network Access Server (NAS)\n          Management";
   }
   feature ntp {
     description
       "Indicates that the device can be configured to use one or\nmore NTP "+
       "servers to set the system date and time.";
   }
   feature ntp-udp-port {
     if-feature "ntp";
     description
       "Indicates that the device supports the configuration of\nthe UDP port "+
       "for NTP servers.\nThis is a 'feature', since many implementations do not"+
       " support\nany port other than the default port.";
   }
   feature timezone-name {
     description
       "Indicates that the local time zone on the device\ncan be configured to "+
       "use the TZ database\nto set the time zone and manage daylight saving "+
       "time.";
     reference
       "RFC 6557: Procedures for Maintaining the Time Zone Database";
   }
   feature dns-udp-tcp-port {
     description
       "Indicates that the device supports the configuration of\nthe UDP and TCP"+
       " port for DNS servers.\nThis is a 'feature', since many implementations "+
       "do not support\nany port other than the default port.";
   }
   identity authentication-method {
     description
       "Base identity for user authentication methods.";
   }
   identity radius {
     base "authentication-method";
     description
       "Indicates user authentication using RADIUS.";
     reference
       "RFC 2865: Remote Authentication Dial In User Service (RADIUS)\nRFC 5607:"+
       " Remote Authentication Dial-In User Service (RADIUS)\n          "+
       "Authorization for Network Access Server (NAS)\n          Management";
   }
   identity local-users {
     base "authentication-method";
     description
       "Indicates password-based authentication of locally\nconfigured users.";
   }
   identity radius-authentication-type {
     description
       "Base identity for RADIUS authentication types.";
   }
   identity radius-pap {
     base "radius-authentication-type";
     description
       "The device requests Password Authentication Protocol (PAP)\nauthenticati"+
       "on from the RADIUS server.";
     reference
       "RFC 2865: Remote Authentication Dial In User Service (RADIUS)";
   }
   identity radius-chap {
     base "radius-authentication-type";
     description
       "The device requests Challenge Handshake Authentication\nProtocol (CHAP) "+
       "authentication from the RADIUS server.";
     reference
       "RFC 2865: Remote Authentication Dial In User Service (RADIUS)";
   }
   container system {
     description
       "System group configuration.";
     leaf hostname {
       type "string" {
         length "1..246";
       }
       description
         "The name of the host.  This name can be a single domain\nlabel or the "+
         "fully qualified domain name of the host.";
       default "HUAWEI";
     }
     container clock {
       description
         "Configuration of the system date and time properties.";
       choice timezone {
         description
           "The system time zone information.";
         case timezone-utc-offset {
           leaf timezone-utc-offset {
             type "int16" {
               range "-1080..1080";
             }
             units "minutes";
             description
               "The number of minutes to add to UTC time to\nidentify the time "+
               "zone for this system.  For example,\n'UTC - 8:00 hours' would be"+
               " represented as '-480'.\nNote that automatic daylight saving "+
               "time adjustment\nis not provided if this object is used.";
             default "0";
           }
         }
       }
     }
     container ntp {
       if-feature "ntp";
       presence "Enables the NTP client unless the 'enabled' leaf\n(which "+
                "defaults to 'true') is set to 'false'";
       description
         "Configuration of the NTP client.";
       leaf enabled {
         type "boolean";
         default "true";
         description
           "Indicates that the system should attempt to\nsynchronize the system "+
           "clock with an NTP server\nfrom the 'ntp/server' list.";
       }
       list server {
         key "name";
         description
           "List of NTP servers to use for system clock\nsynchronization.  If "+
           "'/system/ntp/enabled'\nis 'true', then the system will attempt "+
           "to\ncontact and utilize the specified NTP servers.";
         leaf name {
           type "string" {
             length "1..63";
           }
           description
             "An arbitrary name for the NTP server.";
         }
         choice transport {
           mandatory "true";
           description
             "The transport-protocol-specific parameters for this\nserver.";
           case udp {
             container udp {
               description
                 "Contains UDP-specific configuration parameters\nfor NTP.";
               leaf address {
                 type "inet:host";
                 mandatory "true";
                 description
                   "The address of the NTP server.";
               }
               leaf port {
                 if-feature "ntp-udp-port";
                 type "uint16" {
                   range "123|1025..65535";
                 }
                 default "123";
                 description
                   "The port number of the NTP server.";
               }
             }
           }
         }
         leaf association-type {
           type "enumeration" {
             enum "server" {
               value "0";
               description
                 "Use client association mode. This device\nwill not provide "+
                 "synchronization to the\nconfigured NTP server.";
             }
             enum "peer" {
               value "1";
               description
                 "Use symmetric active association mode.\nThis device may "+
                 "provide synchronization\nto the configured NTP server.";
             }
           }
           default "server";
           description
             "The desired association type for this NTP server.";
         }
         leaf iburst {
           type "boolean";
           default "false";
           description
             "Indicates whether this server should enable burst\nsynchronization"+
             " or not.";
         }
         leaf prefer {
           type "boolean";
           default "false";
           description
             "Indicates whether this server should be preferred\nor not.";
         }
       }
     }
   }
   container system-state {
     config "false";
     description
       "System group operational state.";
     container clock {
       description
         "Monitoring of the system date and time properties.";
       leaf current-datetime {
         type "yang:date-and-time";
         description
           "The current system date and time.";
       }
       leaf boot-datetime {
         type "yang:date-and-time";
         description
           "The system date and time when the system last restarted.";
       }
     }
   }
   rpc set-current-datetime {
     nacm:default-deny-all;
     description
       "Set the /system-state/clock/current-datetime leaf\nto the specified "+
       "value.\nIf the system is using NTP (i.e., /system/ntp/enabled\nis set to"+
       " 'true'), then this operation will fail with\nerror-tag 'operation-faile"+
       "d' and error-app-tag value of\n'ntp-active'.";
     input {
       leaf current-datetime {
         type "yang:date-and-time";
         mandatory "true";
         description
           "The current system date and time.";
       }
     }
   }
   rpc system-restart {
     nacm:default-deny-all;
     description
       "Request that the entire system be restarted immediately.\nA server "+
       "SHOULD send an rpc reply to the client before\nrestarting the system.";
   }
 }

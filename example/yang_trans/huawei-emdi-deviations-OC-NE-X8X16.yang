/*
Copyright (C) 2019 Huawei Technologies Co., Ltd. All rights reserved.
*/

 module huawei-emdi-deviations-OC-NE-X8X16 {
   namespace "urn:huawei:yang:huawei-emdi-deviations-OC-NE-X8X16";
   prefix "emdi-devs-OC-NE-X8X16";
   import huawei-emdi {
     prefix "emdi";
   }
   import huawei-vlan {
     prefix "vlan";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-emdi module.";
   revision "2019-11-06" {
     description
       "Initial revision.";
     reference
       "Huawei private.";
   }
   deviation "/emdi:emdi/emdi:emdi-enable/emdi:emdi-channel-groups/emdi:emdi-cha"+
             "nnel-group/emdi:channel-type/emdi:emdi-channel/emdi:emdi-channels/"+
             "emdi:emdi-channel/emdi:channel-group-parameters/emdi:vlan-id/emdi:"+
             "vlan-id" {
     deviate "replace" {
       type "leafref" {
         path "/vlan:vlan/vlan:vlans/vlan:vlan/vlan:id";
       }
     }
   }
   deviation "/emdi:emdi/emdi:emdi-enable/emdi:emdi-lpu-groups/emdi:emdi-lpu-gro"+
             "up/emdi:bind-lpu/emdi:bind-slots/emdi:slot" {
     deviate "replace" {
       type "leafref" {
         path "/devm:devm/devm:lpu-boards/devm:lpu-board/devm:position";
       }
     }
   }
 }

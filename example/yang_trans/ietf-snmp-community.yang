submodule ietf-snmp-community {
   belongs-to ietf-snmp {
     prefix "snmp";
   }
   import ietf-netconf-acm {
     prefix "nacm";
   }
   include ietf-snmp-common;
   include ietf-snmp-target;
   include ietf-snmp-proxy;
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Martin Bjorklund\n          <mailto:mbj@tail-"+
     "f.com>\nEditor:   Juergen Schoenwaelder\n          <mailto:j.schoenwaelder"+
     "@jacobs-university.de>";
   description
     "This submodule contains a collection of YANG definitions\nfor configuring "+
     "community-based SNMP.\nCopyright (c) 2014 IETF Trust and the persons "+
     "identified as\nauthors of the code.  All rights reserved.\nRedistribution "+
     "and use in source and binary forms, with or\nwithout modification, is "+
     "permitted pursuant to, and subject\nto the license terms contained in, the"+
     " Simplified BSD License\nset forth in Section 4.c of the IETF Trust's "+
     "Legal Provisions\nRelating to IETF Documents\n(http://trustee.ietf.org/lic"+
     "ense-info).\nThis version of this YANG module is part of RFC 7407; "+
     "see\nthe RFC itself for full legal notices.";
   reference
     "RFC 3584: Coexistence between Version 1, Version 2, and\nVersion 3 of the "+
     "Internet-standard Network\nManagement Framework";
   revision "2014-12-10" {
     description
       "Initial revision.";
     reference
       "RFC 7407: A YANG Data Model for SNMP Configuration";
   }
   augment "/snmp:snmp" {
     list community {
       key "index";
       description
         "List of communities.";
       reference
         "RFC 3584: Coexistence between Version 1, Version 2,\nand Version 3 of "+
         "the Internet-standard\nNetwork Management Framework.\nSNMP-COMMUNITY-M"+
         "IB.snmpCommunityTable";
       leaf index {
         type "snmp:identifier";
         description
           "Index into the community list.";
         reference
           "RFC 3584: Coexistence between Version 1, Version 2,\nand Version 3 "+
           "of the Internet-standard\nNetwork Management Framework.\nSNMP-COMMUN"+
           "ITY-MIB.snmpCommunityIndex";
       }
       choice name {
         nacm:default-deny-all;
         description
           "The community name, specified as either a string or\na binary value."+
           "  The binary name is used when the\ncommunity name contains "+
           "characters that are not legal\nin a string.\nIf not set, the value "+
           "of 'security-name' is operationally\nused as the snmpCommunityName.";
         reference
           "RFC 3584: Coexistence between Version 1, Version 2,\nand Version 3 "+
           "of the Internet-standard\nNetwork Management Framework.\nSNMP-COMMUN"+
           "ITY-MIB.snmpCommunityName";
         leaf text-name {
           type "string" {
             length "1..255";
           }
           description
             "A community name that can be represented as a\nYANG string.";
         }
         mandatory "true";
       }
       leaf security-name {
         type "snmp:security-name";
         mandatory "true";
         nacm:default-deny-all;
         description
           "The snmpCommunitySecurityName of this entry.";
         reference
           "RFC 3584: Coexistence between Version 1, Version 2,\nand Version 3 "+
           "of the Internet-standard\nNetwork Management Framework.\nSNMP-COMMUN"+
           "ITY-MIB.snmpCommunitySecurityName";
         must "../security-name = ../index";
       }
       leaf engine-id {
         if-feature "snmp:proxy";
         type "snmp:engine-id";
         description
           "If not set, the value of the local SNMP engine is\noperationally "+
           "used by the device.";
         reference
           "RFC 3584: Coexistence between Version 1, Version 2,\nand Version 3 "+
           "of the Internet-standard\nNetwork Management Framework.\nSNMP-COMMUN"+
           "ITY-MIB.snmpCommunityContextEngineID";
       }
       leaf context {
         type "snmp:context-name";
         default "";
         description
           "The context in which management information is accessed\nwhen using "+
           "the community string specified by this entry.";
         reference
           "RFC 3584: Coexistence between Version 1, Version 2,\nand Version 3 "+
           "of the Internet-standard\nNetwork Management Framework.\nSNMP-COMMUN"+
           "ITY-MIB.snmpCommunityContextName";
       }
       unique "snmp:name/snmp:text-name/snmp:text-name";
     }
   }
   augment "/snmp:snmp/snmp:target-params/snmp:params" {
     case v1 {
       container v1 {
         description
           "SNMPv1 parameters type.\nRepresents snmpTargetParamsMPModel "+
           "'0',\nsnmpTargetParamsSecurityModel '1', and\nsnmpTargetParamsSecuri"+
           "tyLevel 'noAuthNoPriv'.";
         leaf security-name {
           type "string" {
             length "1..168";
           }
           mandatory "true";
           description
             "Implementations MAY restrict the values of this leaf\nto be one of"+
             " the available values of\n/snmp/community/security-name in a valid"+
             " configuration.";
           reference
             "RFC 3413: Simple Network Management Protocol (SNMP).\nApplications"+
             ".\nSNMP-TARGET-MIB.snmpTargetParamsSecurityName";
         }
       }
     }
     case v2c {
       container v2c {
         description
           "SNMPv2 community parameters type.\nRepresents snmpTargetParamsMPMode"+
           "l '1',\nsnmpTargetParamsSecurityModel '2', and\nsnmpTargetParamsSecu"+
           "rityLevel 'noAuthNoPriv'.";
         leaf security-name {
           type "string" {
             length "1..168";
           }
           mandatory "true";
           description
             "Implementations MAY restrict the values of this leaf\nto be one of"+
             " the available values of\n/snmp/community/security-name in a valid"+
             " configuration.";
           reference
             "RFC 3413: Simple Network Management Protocol (SNMP).\nApplications"+
             ".\nSNMP-TARGET-MIB.snmpTargetParamsSecurityName";
         }
       }
     }
   }
 }

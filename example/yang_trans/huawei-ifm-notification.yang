/*
Copyright (C) 2020 Huawei Technologies Co., Ltd. All rights reserved.
*/

 module huawei-ifm-notification {
   yang-version "1";
   namespace "urn:huawei:yang:huawei-ifm-notification";
   prefix "ifm-notification";
   import huawei-pub-type {
     prefix "pub-type";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of ifm.";
   revision "2020-05-30" {
     description
       "Initial revision.";
     reference
       "Huawei private.";
   }
   ext:task-name "interface-mgr";
   typedef port-status {
     type "enumeration" {
       enum "up" {
         value "1";
         description
           "The interface is in Up state.";
       }
       enum "down" {
         value "2";
         description
           "The interface is in Down state.";
       }
     }
     description
       "Interface suppression status.";
   }
   typedef suppress-status {
     type "enumeration" {
       enum "unsuppress" {
         value "0";
         description
           "The interface is not suppressed.";
       }
       enum "suppress" {
         value "1";
         description
           "The interface is suppressed.";
       }
     }
     description
       "Interface suppression status.";
   }
   notification error-down {
     description
       "Error-down occurred.";
     leaf index {
       type "uint32";
       mandatory "true";
       description
         "Index of an interface.";
     }
     leaf name {
       type "pub-type:if-name";
       mandatory "true";
       description
         "Interface name.";
     }
     leaf cause {
       type "string" {
         length "1..50";
       }
       mandatory "true";
       description
         "Cause of the errordown event.";
     }
     leaf recovery-type {
       type "string" {
         length "1..20";
       }
       mandatory "true";
       description
         "Specifies the alarm clearance type. The value is auto recovery or "+
         "Null. The alarm clearance type triggered by restarting an interface is"+
         " auto recovery.";
     }
   }
   notification error-down-recovery {
     description
       "Error-down recovered.";
     leaf index {
       type "uint32";
       mandatory "true";
       description
         "Index of an interface.";
     }
     leaf name {
       type "pub-type:if-name";
       mandatory "true";
       description
         "Interface name.";
     }
     leaf cause {
       type "string" {
         length "1..50";
       }
       mandatory "true";
       description
         "Cause of the errordown event.";
     }
     leaf recovery-type {
       type "string" {
         length "1..20";
       }
       mandatory "true";
       description
         "Specifies the alarm clearance type. The value is auto recovery or "+
         "Null. The alarm clearance type triggered by restarting an interface is"+
         " auto recovery.";
     }
   }
   notification if-damp-suppress {
     description
       "The state of interface changed from unsuppress to suppress.";
     leaf interface-name {
       type "pub-type:if-name";
       description
         "Interface name.";
     }
     leaf suppress-state {
       type "suppress-status";
       description
         "Interface suppression status: - 0: The interface is not suppressed. - "+
         "1: The interface is suppressed.";
     }
   }
   notification if-damp-resume {
     description
       "The state of interface changed from suppress to unsuppress.";
     leaf interface-name {
       type "pub-type:if-name";
       description
         "Interface name.";
     }
     leaf suppress-state {
       type "suppress-status";
       description
         "Interface suppression status: - 0: The interface is not suppressed. - "+
         "1: The interface is suppressed.";
     }
   }
   notification ipv6-if-state-change {
     description
       "The IPv6 status changes.";
     leaf index {
       type "uint32";
       mandatory "true";
       description
         "Interface index.";
     }
     leaf name {
       type "pub-type:if-name";
       mandatory "true";
       description
         "Indicates the interface name.";
     }
     leaf oper-status {
       type "port-status";
       mandatory "true";
       description
         "Indicates the current status of an interface.";
     }
     leaf admin-status {
       type "port-status";
       mandatory "true";
       description
         "Indicates the administrative status of an interface.";
     }
     leaf main-if-name {
       type "pub-type:if-name";
       mandatory "true";
       description
         "Main interface name.";
     }
     leaf reason-code {
       type "uint32";
       mandatory "true";
       description
         "Cause for trap generation.";
     }
   }
   notification link-down {
     description
       "The interface status changes.";
     leaf index {
       type "uint32";
       mandatory "true";
       description
         "Interface index.";
     }
     leaf admin-status {
       type "port-status";
       mandatory "true";
       description
         "Configured interface status.";
     }
     leaf oper-status {
       type "port-status";
       mandatory "true";
       description
         "Current interface status.";
     }
     leaf name {
       type "pub-type:if-name";
       mandatory "true";
       description
         "Interface name.";
     }
     leaf reason-code {
       type "uint32";
       mandatory "true";
       description
         "Cause for trap generation.";
     }
     leaf main-if-name {
       type "pub-type:if-name";
       mandatory "true";
       description
         "Name of the main interface.";
     }
   }
   notification link-up {
     description
       "The interface status changes.";
     leaf index {
       type "uint32";
       mandatory "true";
       description
         "Interface index.";
     }
     leaf admin-status {
       type "port-status";
       mandatory "true";
       description
         "Configured interface status.";
     }
     leaf oper-status {
       type "port-status";
       mandatory "true";
       description
         "Current interface status.";
     }
     leaf name {
       type "pub-type:if-name";
       mandatory "true";
       description
         "Interface name.";
     }
     leaf reason-code {
       type "uint32";
       mandatory "true";
       description
         "Cause for trap generation.";
     }
     leaf main-if-name {
       type "pub-type:if-name";
       mandatory "true";
       description
         "Name of the main interface.";
     }
   }
 }

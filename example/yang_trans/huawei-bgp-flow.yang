/*
Copyright (C) 2019-2021 Huawei Technologies Co., Ltd. All rights reserved.
*/

 module huawei-bgp-flow {
   yang-version "1";
   namespace "urn:huawei:yang:huawei-bgp-flow";
   prefix "bgp-flow";
   import huawei-extension {
     prefix "ext";
   }
   import huawei-network-instance {
     prefix "ni";
   }
   import huawei-bgp {
     prefix "bgp";
   }
   import huawei-routing-policy {
     prefix "rtp";
   }
   import huawei-xpl {
     prefix "xpl";
   }
   import huawei-bgp-routing-table {
     prefix "bgp-rt";
   }
   import huawei-l3vpn {
     prefix "l3vpn";
   }
   import ietf-inet-types {
     prefix "inet";
   }
   import huawei-pub-type {
     prefix "pub-type";
   }
   organization
     "Huawei Technologies Co., Ltd.";
   contact
     "Huawei Industrial Base\nBantian, Longgang\nShenzhen 518129\nPeople's "+
     "Republic of China\nWebsite: http://www.huawei.com\nEmail: support@huawei.c"+
     "om";
   description
     "Inter-AS routing protocol that exchanges Network Layer Reachability "+
     "Information (NLRI) with other BGP systems.";
   revision "2021-09-07" {
     description
       "The YANG descriptions are modified according to new standards.";
     reference
       "Huawei private.";
   }
   revision "2019-03-22" {
     description
       "Initial revision.";
     reference
       "Huawei private.";
   }
   ext:task-name "bgp";
   typedef rpd-cap-type {
     type "enumeration" {
       enum "receive" {
         value "1";
         description
           "Converts received BGP FlowSpec routes to common IP routes if these "+
           "BGP FlowSpec routes carry the RPD attribute.";
       }
     }
     description
       "The type of FlowSpec Route Policy Distribute.";
   }
   typedef flow-validation-result-type {
     type "enumeration" {
       enum "not-enable" {
         value "0";
         description
           "Not enable.";
       }
       enum "checking" {
         value "1";
         description
           "Check.";
       }
       enum "accept" {
         value "2";
         description
           "Accept.";
       }
       enum "discard" {
         value "3";
         description
           "Discard.";
       }
     }
     description
       "BGP FLOW route validation result.";
   }
   typedef flow-operation-code {
     type "enumeration" {
       enum "redirect" {
         value "0";
         description
           "Redirect.";
       }
       enum "copy" {
         value "1";
         description
           "Copy.";
       }
     }
     description
       "Operation type of redirect.";
   }
   typedef flow-color {
     type "string" {
       length "1..26";
       pattern "(0:(([0-9]\\d{0,8})|([1-3]\\d{9})|(4[0-1]\\d{8})|(42[0-8]"+
               "\\d{7})|(429[0-3]\\d{6})|(4294[0-8]\\d{5})|(42949[0-5]"+
               "\\d{4})|(429496[0-6]\\d{3})|(4294967[0-1]\\d{2})|(42949672"+
               "[0-8]\\d{1})|(429496729[0-5]))|-:-)";
     }
     description
       "Type of color.";
   }
   augment "/ni:network-instance/ni:instances/ni:instance/bgp:bgp/bgp:base-proce"+
           "ss/bgp:afs/bgp:af" {
     description
       "BGP flow address family configuration.";
     container ipv4-flow {
       when "../bgp:type='ipv4flow'";
       must "../../../../../l3vpn:afs/l3vpn:af[l3vpn:type='ipv4-unicast']";
       description
         "Configure IPv4-family flow options.";
       container common {
         description
           "Configure BGP IPv4-family flow common options.";
         leaf route-match-destination {
           type "boolean";
           default "false";
           description
             "Enable/disable matching the route destination.";
         }
         leaf validation-mode-as {
           type "boolean";
           default "false";
           description
             "Enable/disable using the route validation-mode include-as command,"+
             " you can configure flow-route validation mode include as.";
         }
         leaf redirect-ip-relay-tnl-enable {
           when "../../../../../../../ni:name='_public_'";
           type "boolean";
           default "false";
           description
             "Enable/disable flow-route recursive-lookup tunnel.";
         }
         leaf redirect-ipv6-relay-tnl-sel-name {
           when "../../../../../../../ni:name='_public_'";
           type "leafref" {
             path "/rtp:routing-policy/rtp:tunnel-selectors/rtp:tunnel-selector/"+
                  "rtp:name";
           }
           description
             "Flow-route tunnel selector name.";
         }
         leaf redirect-ip-relay-tunnel-selector-name {
           when "../redirect-ip-relay-tnl-enable = 'true'";
           type "leafref" {
             path "/rtp:routing-policy/rtp:tunnel-selectors/rtp:tunnel-selector/"+
                  "rtp:name";
           }
           description
             "Specifies the name of a tunnel selector.";
         }
         choice reflector-type {
           description
             "Set IPv4 address or id.";
           case address {
             description
               "IPv4 address.";
             leaf reflector-cluster-ipv4 {
               type "inet:ipv4-address-no-zone";
               description
                 "Set a cluster ID. The value is expressed in the format of an "+
                 "IPv4 address. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
           case id {
             description
               "Set value.";
             leaf reflector-cluster-id {
               type "uint32" {
                 range "1..4294967295";
               }
               description
                 "Set a cluster ID. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
         }
         leaf reflect-between-client {
           type "boolean";
           default "true";
           description
             "Enable/disable route reflection between clients. If clients of a "+
             "route reflector (RR) are fully meshed, you can disable route "+
             "reflection among clients to reduce the cost.";
         }
         leaf check-origin-as-enable {
           when "../../../../../../../ni:name='_public_'";
           type "boolean";
           default "false";
           description
             "Enable/disable the received BGP Flow Specification routes carrying"+
             " a filtering rule that is based on the origin AS number of the "+
             "destination IP address to be valid.";
         }
       }
       container routing-table-rib-only {
         description
           "Configure disable route delivery to the IP routing table.";
         leaf enable {
           type "boolean";
           default "false";
           description
             "Enable/disable prevent BGP routes from being added to the IP "+
             "routing table.";
         }
         choice policy-type {
           description
             "Set route policy or filter.";
           case rtp-ref {
             description
               "Route policy.";
             leaf policy-name {
               when "../enable = 'true'";
               type "leafref" {
                 path "/rtp:routing-policy/rtp:policy-definitions/rtp:policy-def"+
                      "inition/rtp:name";
               }
               description
                 "When routes are imported from other routing protocols, the "+
                 "route-policy filter can be used to filter the routes and "+
                 "change route attributes.";
             }
           }
           case xpl-ref {
             description
               "Route filter.";
             leaf filter-name {
               when "../enable = 'true'";
               type "leafref" {
                 path "/xpl:xpl/xpl:route-filters/xpl:route-filter/xpl:name";
               }
               description
                 "Specify a route-filter name.";
             }
             leaf filter-parameter {
               when "../filter-name";
               type "xpl:filter-parameter-type";
               description
                 "Specify a route-filter parameter.";
             }
           }
         }
       }
     }
     container ipv6-flow {
       when "../bgp:type='ipv6flow'";
       must "../../../../../l3vpn:afs/l3vpn:af[l3vpn:type='ipv6-unicast']";
       description
         "Configure IPv6-family flow options.";
       container common {
         description
           "Configure BGP IPv6-family flow common options.";
         leaf route-match-destination {
           type "boolean";
           default "false";
           description
             "Enable/disable matchingatch the route destination.";
         }
         leaf validation-mode-as {
           type "boolean";
           default "false";
           description
             "Enable/disable using the route validation-mode include-as command,"+
             " you can configure flow-route validation mode include as.";
         }
         leaf reflect-between-client {
           type "boolean";
           default "true";
           description
             "Enable/disable route reflection between clients. If clients of a "+
             "route reflector (RR) are fully meshed, you can disable route "+
             "reflection among clients to reduce the cost.";
         }
         choice reflector-type {
           description
             "Set IPv4 address or id.";
           case address {
             description
               "IPv4 address.";
             leaf reflector-cluster-ipv4 {
               type "inet:ipv4-address-no-zone";
               description
                 "Set a cluster ID. The value is expressed in the format of an "+
                 "IPv4 address. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
           case id {
             description
               "Set value.";
             leaf reflector-cluster-id {
               type "uint32" {
                 range "1..4294967295";
               }
               description
                 "Set a cluster ID. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
         }
         leaf local-redirect-ipv6-relay-ip {
           when "../../../../../../../ni:name='_public_'";
           type "boolean";
           default "false";
           description
             "Enable/disable local route redirect IPv6 recursive-lookup ip "+
             "function.";
         }
         leaf local-redirect-ipv6-relay-tunnel-seletor {
           when "../../../../../../../ni:name='_public_'";
           type "leafref" {
             path "/rtp:routing-policy/rtp:tunnel-selectors/rtp:tunnel-selector/"+
                  "rtp:name";
           }
           description
             "Enable/disable local route redirect IPv6 recursive-lookup tunnel "+
             "by tunnel selector name.";
         }
       }
       container routing-table-rib-only {
         description
           "Configure disable route delivery to the IP routing table.";
         leaf enable {
           type "boolean";
           default "false";
           description
             "Enable/disable prevent BGP routes from being added to the IP "+
             "routing table.";
         }
         choice policy-type {
           description
             "Set route policy or filter.";
           case rtp-ref {
             description
               "Route policy.";
             leaf policy-name {
               when "../enable = 'true'";
               type "leafref" {
                 path "/rtp:routing-policy/rtp:policy-definitions/rtp:policy-def"+
                      "inition/rtp:name";
               }
               description
                 "When routes are imported from other routing protocols, the "+
                 "route-policy filter can be used to filter the routes and "+
                 "change route attributes.";
             }
           }
           case xpl-ref {
             description
               "Route filter.";
             leaf filter-name {
               when "../enable = 'true'";
               type "leafref" {
                 path "/xpl:xpl/xpl:route-filters/xpl:route-filter/xpl:name";
               }
               description
                 "Specify a route-filter name.";
             }
             leaf filter-parameter {
               when "../filter-name";
               type "xpl:filter-parameter-type";
               description
                 "Specify a route-filter parameter.";
             }
           }
         }
       }
     }
     container vpnv4-flow {
       when "../bgp:type='vpnv4flow'";
       description
         "Configure IPv4 VPN flow options.";
       container common {
         description
           "Configure IPv4 VPN flow common options.";
         leaf policy-vpntarget {
           type "boolean";
           default "true";
           description
             "Enable/disable VPN target-based filtering for the received VPN "+
             "routes. Only the VPN route whose Export RT attribute matches the "+
             "local Import RT attribute can be added to the routing table. This "+
             "option can be used in the inter-AS VPN Option B solution and the "+
             "ASBR MP-EBGP inter-AS L2VPN solution in Kompella mode.";
         }
         choice reflector-type {
           description
             "Set IPv4 address or id.";
           case address {
             description
               "IPv4 address.";
             leaf reflector-cluster-ipv4 {
               type "inet:ipv4-address-no-zone";
               description
                 "Set a cluster ID. The value is expressed in the format of an "+
                 "IPv4 address. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
           case id {
             description
               "Set value.";
             leaf reflector-cluster-id {
               type "uint32" {
                 range "1..4294967295";
               }
               description
                 "Set a cluster ID. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
         }
         leaf reflect-between-client {
           type "boolean";
           default "true";
           description
             "Enable/disable route reflection between clients.";
         }
       }
     }
     container vpnv6-flow {
       when "../bgp:type='vpnv6flow'";
       description
         "Configure IPv6 VPN flow options.";
       container common {
         description
           "Configure IPv6 VPN flow common options.";
         leaf policy-vpntarget {
           type "boolean";
           default "true";
           description
             "Enable/disable VPN target-based filtering for the received VPN "+
             "routes. Only the VPN route whose Export RT attribute matches the "+
             "local Import RT attribute can be added to the routing table. This "+
             "option can be used in the inter-AS VPN Option B solution and the "+
             "ASBR MP-EBGP inter-AS L2VPN solution in Kompella mode.";
         }
         choice reflector-type {
           description
             "Set IPv4 address or id.";
           case address {
             description
               "IPv4 address.";
             leaf reflector-cluster-ipv4 {
               type "inet:ipv4-address-no-zone";
               description
                 "Set a cluster ID. The value is expressed in the format of an "+
                 "IPv4 address. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
           case id {
             description
               "Set value.";
             leaf reflector-cluster-id {
               type "uint32" {
                 range "1..4294967295";
               }
               description
                 "Set a cluster ID. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
         }
         leaf reflect-between-client {
           type "boolean";
           default "true";
           description
             "Enable/disable route reflection between clients.";
         }
       }
     }
   }
   augment "/ni:network-instance/ni:instances/ni:instance/bgp:bgp/bgp:base-proce"+
           "ss/bgp:peers/bgp:peer/bgp:afs/bgp:af" {
     description
       "BGP flow address family configuration.";
     container ipv4-flow {
       when "../bgp:type='ipv4flow'";
       must "../../../../../../../l3vpn:afs/l3vpn:af[l3vpn:type='ipv4-unicast']";
       description
         "Configure IPv4-family flow options.";
       leaf advertise-community {
         type "boolean";
         default "false";
         description
           "Enable/disable advertise the community attribute to a peer or a peer"+
           " group.";
       }
       leaf reflect-client {
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf validation-disable {
         type "boolean";
         default "false";
         description
           "Enable/disable route validation.";
       }
       leaf redirect-ip {
         type "boolean";
         default "false";
         description
           "Enable/disable peer handle the extended community attribute "+
           "redirect-ip.";
       }
       leaf redirect-ip-vaildation {
         type "boolean";
         default "false";
         description
           "Enable/disable the function to indicate whether validation redirect "+
           "ip, and this command only support IPv4-family flow address family.";
       }
       leaf redirect-ip-rfc-compatible {
         type "boolean";
         must "not(../redirect-ip-rfc-compatible='true' and ../redirect-ip-draft"+
              "-compatible='true')";
         default "false";
         description
           "Enable/disable sending both number for the apply redirect IPv4 "+
           "action.";
       }
       leaf redirect-ip-draft-compatible {
         type "boolean";
         default "false";
         description
           "Enable/disable sending both number for the apply redirect IPv4 "+
           "action.";
       }
       leaf redirect-tunnelv6 {
         type "boolean";
         default "false";
         description
           "Enable/disable the function to handle the extended community "+
           "attribute redirect-tunnelv6.";
       }
       leaf graceful-restart-static-timer {
         type "uint32" {
           range "3600..2147483647";
         }
         units "s";
         description
           "Specifies the maximum time during which a peer waits for a BGP "+
           "session reestablishment.";
       }
       leaf destination-origin-as {
         type "boolean";
         default "false";
         description
           "Enable/disable the BGP peer origin validation.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-large-community {
         type "bgp:peer-enable-config-type";
         default "default";
         description
           "Enable large-community attribute advertisement. The Link-state "+
           "address family and the RPD address family do not support this "+
           "element.";
       }
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       leaf update-group-independent {
         type "bgp:peer-comm-config-type";
         default "default";
         description
           "Enable/disable the peer which can reside in an independent peer "+
           "group.";
       }
       leaf route-policy-distribute {
         when "../../../../../../../../ni:name='_public_'";
         type "rpd-cap-type";
         description
           "Enable/disable route policy distribution (RPD) on a BGP device.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
     container ipv6-flow {
       when "../bgp:type='ipv6flow'";
       must "../../../../../../../l3vpn:afs/l3vpn:af[l3vpn:type='ipv6-unicast']";
       description
         "Configure IPv6-family flow options.";
       leaf advertise-community {
         type "boolean";
         default "false";
         description
           "Enable/disable advertise the community attribute to a peer or a peer"+
           " group.";
       }
       leaf reflect-client {
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf validation-disable {
         type "boolean";
         default "false";
         description
           "Enable/disable route validation.";
       }
       leaf graceful-restart-static-timer {
         type "uint32" {
           range "3600..2147483647";
         }
         units "s";
         description
           "Specifies the maximum time during which a peer waits for a BGP "+
           "session reestablishment.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-large-community {
         type "bgp:peer-enable-config-type";
         default "default";
         description
           "Enable large-community attribute advertisement. The Link-state "+
           "address family and the RPD address family do not support this "+
           "element.";
       }
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       leaf update-group-independent {
         type "bgp:peer-comm-config-type";
         default "default";
         description
           "Enable/disable the peer which can reside in an independent peer "+
           "group.";
       }
       leaf redirect-ipv6-validation-disable {
         when "../../../../../../../../ni:name='_public_'";
         type "boolean";
         default "false";
         description
           "Enable/disable redirect IPv6 route validation.";
       }
       leaf redirect-ipv6-relay-ip {
         when "../../../../../../../../ni:name='_public_'";
         type "boolean";
         default "false";
         description
           "Enable/disable redirect IPv6 recursive-lookup ip function.";
       }
       leaf redirect-ipv6-relay-tunnel-seletor {
         when "../../../../../../../../ni:name='_public_'";
         type "leafref" {
           path "/rtp:routing-policy/rtp:tunnel-selectors/rtp:tunnel-selector/rt"+
                "p:name";
         }
         description
           "Enable/disable redirect IPv6 recursive-lookup tunnel by tunnel "+
           "selector name.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
     container vpnv4-flow {
       when "../bgp:type='vpnv4flow'";
       description
         "Configure IPv4 VPN flow options.";
       leaf advertise-large-community {
         type "bgp:peer-enable-config-type";
         default "default";
         description
           "Enable large-community attribute advertisement.";
       }
       leaf reflect-client {
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf graceful-restart-static-timer {
         type "uint32" {
           range "3600..2147483647";
         }
         units "s";
         description
           "Specifies the maximum time during which a peer waits for a BGP "+
           "session reestablishment.";
       }
       leaf update-group-independent {
         type "bgp:peer-comm-config-type";
         default "default";
         description
           "Enable/disable the peer which can reside in an independent peer "+
           "group.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-community {
         type "boolean";
         default "false";
         description
           "Enable/disable advertise the community attribute to a peer or a peer"+
           " group.";
       }
       leaf redirect-ip-rfc-compatible {
         type "boolean";
         must "not(../redirect-ip-rfc-compatible='true' and ../redirect-ip-draft"+
              "-compatible='true')";
         default "false";
         description
           "Enable/disable sending both number for the apply redirect IPv4 "+
           "action.";
       }
       leaf redirect-ip-draft-compatible {
         type "boolean";
         default "false";
         description
           "Enable/disable sending both number for the apply redirect IPv4 "+
           "action.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
     container vpnv6-flow {
       when "../bgp:type='vpnv6flow'";
       description
         "Configure IPv6 VPN flow options.";
       leaf advertise-large-community {
         type "bgp:peer-enable-config-type";
         default "default";
         description
           "Enable large-community attribute advertisement.";
       }
       leaf reflect-client {
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf graceful-restart-static-timer {
         type "uint32" {
           range "3600..2147483647";
         }
         units "s";
         description
           "Specifies the maximum time during which a peer waits for a BGP "+
           "session reestablishment.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-community {
         type "boolean";
         default "false";
         description
           "Enable/disable advertise the community attribute to a peer or a peer"+
           " group.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
   }
   augment "/bgp:bgp/bgp:base-process/bgp-rt:bgp-route" {
     description
       "BGP flow address family routes information.";
     container ipv4-flow {
       config "false";
       description
         "Statistics of BGP routes information of IPv4 flow address family.";
       container routes {
         description
           "List of displayed BGP FLOW route information.";
         list route {
           key "vpn-name route-distinguisher index route-generate-identity from "+
               "route-type path-id";
           description
             "BGP FLOW route state.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf index {
             type "uint32" {
               range "1..4294967295";
             }
             description
               "BGP Flow Specification route index. The value is an integer "+
               "ranging from 1 to 4294967295.";
           }
           leaf route-generate-identity {
             type "string" {
               length "1..36";
             }
             description
               "Local BGP Flow route identify, Format:local:<name> or others.";
           }
           leaf from {
             type "inet:ip-address-no-zone";
             description
               "Source peer that sends a route.";
           }
           leaf route-type {
             type "bgp-rt:bgp-route-type-flag";
             description
               "Route type.";
           }
           leaf path-id {
             type "string" {
               length "1..50";
             }
             description
               "Path ID.";
           }
           leaf remote-route-id {
             type "inet:ipv4-address-no-zone";
             description
               "Router ID of a peer.";
           }
           leaf relay-tunnel-name {
             type "string" {
               length "1..64";
             }
             description
               "Flow Route Redirect Relay Tunnel.";
           }
           leaf validation-result {
             type "flow-validation-result-type";
             description
               "EBGP redirect IP validate result.";
           }
           leaf reflect-client {
             type "boolean";
             description
               "The device is an RR.";
           }
           leaf unknown-rule {
             type "boolean";
             description
               "Unknown rule.";
           }
           leaf med {
             type "uint32";
             description
               "Route MED.The attribute is only fit for the routes from EBGP "+
               "peer, not suit for which of IBGP peer.";
           }
           leaf preferred-value {
             type "uint32";
             description
               "Preferred value of a protocol.";
           }
           leaf local-preference {
             type "uint32";
             description
               "Local priority. The attribute is only fit for the routes from "+
               "IBGP peer, not suit for which of EBGP peer.";
           }
           leaf origin {
             type "bgp-rt:bgp-origin-type";
             description
               "Route origin.";
           }
           leaf originator {
             type "inet:ipv4-address-no-zone";
             description
               "Router ID of the route initiator.";
           }
           leaf time {
             type "pub-type:time-tick";
             description
               "Time stamp of a route.";
           }
           leaf flag-string {
             type "string" {
               length "1..100";
             }
             description
               "Route flag that contains a string of characters.";
           }
           leaf worse-reason {
             type "string" {
               length "1..50";
             }
             description
               "Reason why a route is not selected.";
           }
           leaf route-policy-distribute {
             type "boolean";
             description
               "RPD flag.";
           }
           leaf invalid-reason {
             type "string" {
               length "1..50";
             }
             description
               "Why a route cannot be delivered to the FIB.";
           }
           leaf relay-tunnel-id {
             type "string" {
               length "1..25";
             }
             description
               "Tunnel id.";
           }
         }
       }
       container statistics {
         description
           "List of BGP routes statistics information of the address family.";
         list statistic {
           key "vpn-name";
           description
             "BGP address family routes statistics.";
           leaf vpn-name {
             type "leafref" {
               path "/ni:network-instance/ni:instances/ni:instance/ni:name";
             }
             description
               "VPN name of a BGP instance.";
           }
           leaf total-number {
             type "uint32";
             description
               "Total number of routes.";
           }
         }
       }
       container redirect-ip-relay-infos {
         description
           "List of redirection IP relay result.";
         list redirect-ip-relay-info {
           key "vpn-name route-distinguisher index route-generate-identity from "+
               "route-type path-id address color";
           description
             "Statistics of redirection IP relay information.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf index {
             type "uint32" {
               range "1..4294967295";
             }
             description
               "BGP Flow Specification route index. The value is an integer "+
               "ranging from 1 to 4294967295.";
           }
           leaf route-generate-identity {
             type "string" {
               length "1..36";
             }
             description
               "Local BGP Flow route identify, Format:local:<name> or others.";
           }
           leaf from {
             type "inet:ip-address-no-zone";
             description
               "Source peer that sends a route.";
           }
           leaf route-type {
             type "bgp-rt:bgp-route-type-flag";
             description
               "Route type.";
           }
           leaf path-id {
             type "string" {
               length "1..50";
             }
             description
               "Path ID.";
           }
           leaf address {
             type "inet:ipv4-address-no-zone";
             description
               "Redirection IP address.";
           }
           leaf color {
             type "flow-color";
             description
               "Color. By default, color is -:-.";
           }
           leaf operation-code {
             type "flow-operation-code";
             description
               "Operation code.";
           }
           leaf relay-ip-next-hop {
             type "inet:ipv4-address-no-zone";
             description
               "IP iteration next hop.";
           }
           leaf relay-ip-interface-name {
             type "string" {
               length "1..63";
             }
             description
               "IP iteration outbound interface.";
           }
           leaf relay-tunnel-next-hop {
             type "inet:ipv4-address-no-zone";
             description
               "Tunnel iteration next hop.";
           }
           leaf relay-tunnel-interface-name {
             type "string" {
               length "1..63";
             }
             description
               "Tunnel iteration outbund interface.";
           }
           leaf relay-tunnel-id {
             type "string" {
               length "1..25";
             }
             description
               "Tunnel id.";
           }
         }
       }
       container redirect-ipv6-relay-infos {
         description
           "List of redirection IPv6 relay result.";
         list redirect-ipv6-relay-info {
           key "vpn-name route-distinguisher index route-generate-identity from "+
               "route-type path-id address color";
           description
             "Statistics of redirection IPv6 relay information.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf index {
             type "uint32" {
               range "1..4294967295";
             }
             description
               "BGP Flow Specification route index. The value is an integer "+
               "ranging from 1 to 4294967295.";
           }
           leaf route-generate-identity {
             type "string" {
               length "1..36";
             }
             description
               "Local BGP Flow route identify, Format:local:<name> or others.";
           }
           leaf from {
             type "inet:ip-address-no-zone";
             description
               "Source peer that sends a route.";
           }
           leaf route-type {
             type "bgp-rt:bgp-route-type-flag";
             description
               "Route type.";
           }
           leaf path-id {
             type "string" {
               length "1..50";
             }
             description
               "Path ID.";
           }
           leaf address {
             type "inet:ipv6-address-no-zone";
             description
               "Redirection IP address.";
           }
           leaf color {
             type "flow-color";
             description
               "Color. By default, color is -:-.";
           }
           leaf operation-code {
             type "flow-operation-code";
             description
               "Operation code.";
           }
           leaf relay-tunnel-interface-name {
             type "string" {
               length "1..63";
             }
             description
               "Tunnel iteration outbund interface.";
           }
           leaf relay-tunnel-id {
             type "string" {
               length "1..25";
             }
             description
               "Tunnel id.";
           }
           leaf prefix-sid {
             type "inet:ipv6-address-no-zone";
             description
               "Prefix SID attribute information of route.";
           }
         }
       }
     }
     container ipv6-flow {
       config "false";
       description
         "Statistics of BGP routes information of IPv6 flow address family.";
       container routes {
         description
           "List of displayed BGP FLOW route information.";
         list route {
           key "vpn-name route-distinguisher index route-generate-identity from "+
               "route-type path-id";
           description
             "BGP FLOW route state.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf index {
             type "uint32" {
               range "1..4294967295";
             }
             description
               "BGP Flow Specification route index. The value is an integer "+
               "ranging from 1 to 4294967295.";
           }
           leaf route-generate-identity {
             type "string" {
               length "1..36";
             }
             description
               "Local BGP Flow route identify, Format:local:<name> or others.";
           }
           leaf from {
             type "inet:ip-address-no-zone";
             description
               "Source peer that sends a route.";
           }
           leaf route-type {
             type "bgp-rt:bgp-route-type-flag";
             description
               "Route type.";
           }
           leaf path-id {
             type "string" {
               length "1..50";
             }
             description
               "Path ID.";
           }
           leaf remote-route-id {
             type "inet:ipv4-address-no-zone";
             description
               "Router ID of a peer.";
           }
           leaf relay-tunnel-name {
             type "string" {
               length "1..64";
             }
             description
               "Flow Route Redirect Relay Tunnel.";
           }
           leaf validation-result {
             type "flow-validation-result-type";
             description
               "EBGP redirect IP validate result.";
           }
           leaf reflect-client {
             type "boolean";
             description
               "The device is an RR.";
           }
           leaf unknown-rule {
             type "boolean";
             description
               "Unknown rule.";
           }
           leaf med {
             type "uint32";
             description
               "Route MED.The attribute is only fit for the routes from EBGP "+
               "peer, not suit for which of IBGP peer.";
           }
           leaf preferred-value {
             type "uint32";
             description
               "Preferred value of a protocol.";
           }
           leaf local-preference {
             type "uint32";
             description
               "Local priority. The attribute is only fit for the routes from "+
               "IBGP peer, not suit for which of EBGP peer.";
           }
           leaf origin {
             type "bgp-rt:bgp-origin-type";
             description
               "Route origin.";
           }
           leaf originator {
             type "inet:ipv4-address-no-zone";
             description
               "Router ID of the route initiator.";
           }
           leaf time {
             type "pub-type:time-tick";
             description
               "Time stamp of a route.";
           }
           leaf flag-string {
             type "string" {
               length "1..100";
             }
             description
               "Route flag that contains a string of characters.";
           }
           leaf worse-reason {
             type "string" {
               length "1..50";
             }
             description
               "Reason why a route is not selected.";
           }
           leaf route-policy-distribute {
             type "boolean";
             description
               "RPD flag.";
           }
           leaf invalid-reason {
             type "string" {
               length "1..50";
             }
             description
               "Why a route cannot be delivered to the FIB.";
           }
           leaf relay-tunnel-id {
             type "string" {
               length "1..25";
             }
             description
               "Tunnel id.";
           }
         }
       }
       container statistics {
         description
           "List of BGP routes statistics information of the address family.";
         list statistic {
           key "vpn-name";
           description
             "BGP address family routes statistics.";
           leaf vpn-name {
             type "leafref" {
               path "/ni:network-instance/ni:instances/ni:instance/ni:name";
             }
             description
               "VPN name of a BGP instance.";
           }
           leaf total-number {
             type "uint32";
             description
               "Total number of routes.";
           }
         }
       }
       container redirect-ipv6-relay-infos {
         description
           "List of redirection IPv6 relay result.";
         list redirect-ipv6-relay-info {
           key "vpn-name route-distinguisher index route-generate-identity from "+
               "route-type path-id address color";
           description
             "Statistics of redirection IPv6 relay information.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf index {
             type "uint32" {
               range "1..4294967295";
             }
             description
               "BGP Flow Specification route index. The value is an integer "+
               "ranging from 1 to 4294967295.";
           }
           leaf route-generate-identity {
             type "string" {
               length "1..36";
             }
             description
               "Local BGP Flow route identify, Format:local:<name> or others.";
           }
           leaf from {
             type "inet:ip-address-no-zone";
             description
               "Source peer that sends a route.";
           }
           leaf route-type {
             type "bgp-rt:bgp-route-type-flag";
             description
               "Route type.";
           }
           leaf path-id {
             type "string" {
               length "1..50";
             }
             description
               "Path ID.";
           }
           leaf address {
             type "inet:ipv6-address-no-zone";
             description
               "Redirection IP address.";
           }
           leaf color {
             type "flow-color";
             description
               "Color. By default, color is -:-.";
           }
           leaf operation-code {
             type "flow-operation-code";
             description
               "Operation code.";
           }
           leaf relay-tunnel-interface-name {
             type "string" {
               length "1..63";
             }
             description
               "Tunnel iteration outbund interface.";
           }
           leaf relay-tunnel-id {
             type "string" {
               length "1..25";
             }
             description
               "Tunnel id.";
           }
           leaf prefix-sid {
             type "inet:ipv6-address-no-zone";
             description
               "Prefix SID attribute information of route.";
           }
         }
       }
     }
     container vpnv4-flow {
       config "false";
       description
         "Statistics of BGP routes information of vpnv4 flow address family.";
       container routes {
         description
           "List of displayed BGP FLOW route information.";
         list route {
           key "vpn-name route-distinguisher index route-generate-identity from "+
               "route-type path-id";
           description
             "BGP FLOW route state.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf index {
             type "uint32" {
               range "1..4294967295";
             }
             description
               "BGP Flow Specification route index. The value is an integer "+
               "ranging from 1 to 4294967295.";
           }
           leaf route-generate-identity {
             type "string" {
               length "1..36";
             }
             description
               "Local BGP Flow route identify, Format:local:<name> or others.";
           }
           leaf from {
             type "inet:ip-address-no-zone";
             description
               "Source peer that sends a route.";
           }
           leaf route-type {
             type "bgp-rt:bgp-route-type-flag";
             description
               "Route type.";
           }
           leaf path-id {
             type "string" {
               length "1..50";
             }
             description
               "Path ID.";
           }
           leaf remote-route-id {
             type "inet:ipv4-address-no-zone";
             description
               "Router ID of a peer.";
           }
           leaf relay-tunnel-name {
             type "string" {
               length "1..64";
             }
             description
               "Flow Route Redirect Relay Tunnel.";
           }
           leaf validation-result {
             type "flow-validation-result-type";
             description
               "EBGP redirect IP validate result.";
           }
           leaf reflect-client {
             type "boolean";
             description
               "The device is an RR.";
           }
           leaf unknown-rule {
             type "boolean";
             description
               "Unknown rule.";
           }
           leaf med {
             type "uint32";
             description
               "Route MED.The attribute is only fit for the routes from EBGP "+
               "peer, not suit for which of IBGP peer.";
           }
           leaf preferred-value {
             type "uint32";
             description
               "Preferred value of a protocol.";
           }
           leaf local-preference {
             type "uint32";
             description
               "Local priority. The attribute is only fit for the routes from "+
               "IBGP peer, not suit for which of EBGP peer.";
           }
           leaf origin {
             type "bgp-rt:bgp-origin-type";
             description
               "Route origin.";
           }
           leaf originator {
             type "inet:ipv4-address-no-zone";
             description
               "Router ID of the route initiator.";
           }
           leaf time {
             type "pub-type:time-tick";
             description
               "Time stamp of a route.";
           }
           leaf flag-string {
             type "string" {
               length "1..100";
             }
             description
               "Route flag that contains a string of characters.";
           }
           leaf worse-reason {
             type "string" {
               length "1..50";
             }
             description
               "Reason why a route is not selected.";
           }
           leaf route-policy-distribute {
             type "boolean";
             description
               "RPD flag.";
           }
           leaf invalid-reason {
             type "string" {
               length "1..50";
             }
             description
               "Why a route cannot be delivered to the FIB.";
           }
           leaf relay-tunnel-id {
             type "string" {
               length "1..25";
             }
             description
               "Tunnel id.";
           }
         }
       }
       container statistics {
         description
           "List of BGP routes statistics information of the address family.";
         list statistic {
           key "vpn-name";
           description
             "BGP address family routes statistics.";
           leaf vpn-name {
             type "leafref" {
               path "/ni:network-instance/ni:instances/ni:instance/ni:name";
             }
             description
               "VPN name of a BGP instance.";
           }
           leaf total-number {
             type "uint32";
             description
               "Total number of routes.";
           }
         }
       }
     }
     container vpnv6-flow {
       config "false";
       description
         "Statistics of BGP routes information of vpnv6 flow address family.";
       container routes {
         description
           "List of displayed BGP FLOW route information.";
         list route {
           key "vpn-name route-distinguisher index route-generate-identity from "+
               "route-type path-id";
           description
             "BGP FLOW route state.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf index {
             type "uint32" {
               range "1..4294967295";
             }
             description
               "BGP Flow Specification route index. The value is an integer "+
               "ranging from 1 to 4294967295.";
           }
           leaf route-generate-identity {
             type "string" {
               length "1..36";
             }
             description
               "Local BGP Flow route identify, Format:local:<name> or others.";
           }
           leaf from {
             type "inet:ip-address-no-zone";
             description
               "Source peer that sends a route.";
           }
           leaf route-type {
             type "bgp-rt:bgp-route-type-flag";
             description
               "Route type.";
           }
           leaf path-id {
             type "string" {
               length "1..50";
             }
             description
               "Path ID.";
           }
           leaf remote-route-id {
             type "inet:ipv4-address-no-zone";
             description
               "Router ID of a peer.";
           }
           leaf relay-tunnel-name {
             type "string" {
               length "1..64";
             }
             description
               "Flow Route Redirect Relay Tunnel.";
           }
           leaf validation-result {
             type "flow-validation-result-type";
             description
               "EBGP redirect IP validate result.";
           }
           leaf reflect-client {
             type "boolean";
             description
               "The device is an RR.";
           }
           leaf unknown-rule {
             type "boolean";
             description
               "Unknown rule.";
           }
           leaf med {
             type "uint32";
             description
               "Route MED.The attribute is only fit for the routes from EBGP "+
               "peer, not suit for which of IBGP peer.";
           }
           leaf preferred-value {
             type "uint32";
             description
               "Preferred value of a protocol.";
           }
           leaf local-preference {
             type "uint32";
             description
               "Local priority. The attribute is only fit for the routes from "+
               "IBGP peer, not suit for which of EBGP peer.";
           }
           leaf origin {
             type "bgp-rt:bgp-origin-type";
             description
               "Route origin.";
           }
           leaf originator {
             type "inet:ipv4-address-no-zone";
             description
               "Router ID of the route initiator.";
           }
           leaf time {
             type "pub-type:time-tick";
             description
               "Time stamp of a route.";
           }
           leaf flag-string {
             type "string" {
               length "1..100";
             }
             description
               "Route flag that contains a string of characters.";
           }
           leaf worse-reason {
             type "string" {
               length "1..50";
             }
             description
               "Reason why a route is not selected.";
           }
           leaf route-policy-distribute {
             type "boolean";
             description
               "RPD flag.";
           }
           leaf invalid-reason {
             type "string" {
               length "1..50";
             }
             description
               "Why a route cannot be delivered to the FIB.";
           }
           leaf relay-tunnel-id {
             type "string" {
               length "1..25";
             }
             description
               "Tunnel id.";
           }
         }
       }
       container statistics {
         description
           "List of BGP routes statistics information of the address family.";
         list statistic {
           key "vpn-name";
           description
             "BGP address family routes statistics.";
           leaf vpn-name {
             type "leafref" {
               path "/ni:network-instance/ni:instances/ni:instance/ni:name";
             }
             description
               "VPN name of a BGP instance.";
           }
           leaf total-number {
             type "uint32";
             description
               "Total number of routes.";
           }
         }
       }
     }
   }
 }

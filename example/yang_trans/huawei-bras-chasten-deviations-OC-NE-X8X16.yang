/*
Copyright (C) 2019 Huawei Technologies Co., Ltd. All rights reserved.
*/

 module huawei-bras-chasten-deviations-OC-NE-X8X16 {
   namespace "urn:huawei:yang:huawei-bras-chasten-deviations-OC-NE-X8X16";
   prefix "bras-chasten-devs-OC-NE-X8X16";
   import huawei-bras-chasten {
     prefix "bras-chasten";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module contains a collection of YANG definitions for managing "+
     "chasten.";
   revision "2019-09-06" {
     description
       "Initial revision.";
     reference
       "Huawei private.";
   }
   deviation "/bras-chasten:reset-ipv6-user/bras-chasten:input/bras-chasten:slot"+
             "-id" {
     deviate "replace" {
       type "leafref" {
         path "/devm:devm/devm:lpu-boards/devm:lpu-board/devm:position";
       }
     }
   }
   deviation "/bras-chasten:reset-ipv4-user/bras-chasten:input/bras-chasten:slot"+
             "-id" {
     deviate "replace" {
       type "leafref" {
         path "/devm:devm/devm:lpu-boards/devm:lpu-board/devm:position";
       }
     }
   }
   deviation "/bras-chasten:bras-chasten/bras-chasten:ipv6-slots/bras-chasten:ip"+
             "v6-slot/bras-chasten:slot-id" {
     deviate "replace" {
       type "leafref" {
         path "/devm:devm/devm:lpu-boards/devm:lpu-board/devm:position";
       }
     }
   }
   deviation "/bras-chasten:bras-chasten/bras-chasten:ipv4-slots/bras-chasten:ip"+
             "v4-slot/bras-chasten:slot-id" {
     deviate "replace" {
       type "leafref" {
         path "/devm:devm/devm:lpu-boards/devm:lpu-board/devm:position";
       }
     }
   }
   deviation "/bras-chasten:bras-chasten/bras-chasten:ipv6-users/bras-chasten:ip"+
             "v6-user/bras-chasten:slot-id" {
     deviate "replace" {
       type "leafref" {
         path "/devm:devm/devm:lpu-boards/devm:lpu-board/devm:position";
       }
     }
   }
   deviation "/bras-chasten:bras-chasten/bras-chasten:ipv4-users/bras-chasten:ip"+
             "v4-user/bras-chasten:slot-id" {
     deviate "replace" {
       type "leafref" {
         path "/devm:devm/devm:lpu-boards/devm:lpu-board/devm:position";
       }
     }
   }
 }

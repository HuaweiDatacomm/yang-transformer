submodule openconfig-network-instance-l2 {
   belongs-to openconfig-network-instance {
     prefix "oc-netinst";
   }
   import openconfig-extensions {
     prefix "oc-ext";
   }
   organization
     "OpenConfig working group";
   contact
     "OpenConfig working group\nwww.openconfig.net";
   description
     "This module contains groupings which specifically relate to\nLayer 2 "+
     "network instance configuration and operational state\nparameters.";
   oc-ext:openconfig-version "0.12.0";
   revision "2019-04-16" {
     description
       "Move BGP RIB into the protocol/bgp container.";
     reference
       "0.12.0";
   }
   revision "2018-11-21" {
     description
       "Add OpenConfig module metadata extensions.";
     reference
       "0.11.1";
   }
   revision "2018-08-11" {
     description
       "Add vlan id as additional key in MAC table";
     reference
       "0.11.0";
   }
   revision "2018-06-22" {
     description
       "Fix typo in OSPF when statement";
     reference
       "0.10.2";
   }
   revision "2018-06-05" {
     description
       "Fix bugs in when statements";
     reference
       "0.10.1";
   }
   revision "2018-02-19" {
     description
       "Add PIM and IGMP to network instance";
     reference
       "0.10.0";
   }
   revision "2017-12-13" {
     description
       "Fix incorrect constraint on SR and MPLS containers";
     reference
       "0.9.0";
   }
   revision "2017-08-24" {
     description
       "Minor formatting fixes";
     reference
       "0.8.1";
   }
   revision "2017-02-28" {
     description
       "Add OSPFv2 to network instance";
     reference
       "0.8.0";
   }
   revision "2017-01-26" {
     description
       "Add policy forwarding to network instance";
     reference
       "0.7.0";
   }
   revision "2017-01-13" {
     description
       "Add AFT to the network instance";
     reference
       "0.6.0";
   }
   revision "2016-12-15" {
     description
       "Add segment routing to network instance";
     reference
       "0.5.0";
   }
   revision "2016-11-10" {
     description
       "Update model to include IS-IS.";
     reference
       "0.4.1";
   }
   revision "2016-10-12" {
     description
       "Update table connections";
     reference
       "0.4.0";
   }
   revision "2016-09-28" {
     description
       "Change L2 instance to submodule; add MAC table";
     reference
       "0.3.0";
   }
   revision "2016-08-11" {
     description
       "Resolve repeated container names in routing protocols";
     reference
       "0.2.3";
   }
   revision "2016-07-08" {
     description
       "Updated with refactored routing protocol models";
     reference
       "0.2.1";
   }
   revision "2016-03-29" {
     description
       "Initial revision";
     reference
       "0.2.0";
   }
   revision "2015-11-20" {
     description
       "Initial revision";
     reference
       "0.1.0";
   }
 }

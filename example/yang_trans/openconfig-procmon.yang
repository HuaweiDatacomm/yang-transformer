module openconfig-procmon {
   yang-version "1";
   namespace "http://openconfig.net/yang/system/procmon";
   prefix "oc-proc";
   import openconfig-extensions {
     prefix "oc-ext";
   }
   organization
     "OpenConfig working group";
   contact
     "OpenConfig working group\nwww.openconfig.net";
   description
     "This module provides data definitions for process health\nmonitoring of "+
     "one or more processes running on the system.";
   oc-ext:openconfig-version "0.3.0";
   revision "2017-09-18" {
     description
       "Updated to use OpenConfig types modules";
     reference
       "0.3.0";
   }
   revision "2017-07-06" {
     description
       "Move to oc-inet types, add IETF attribution, add RADIUS\ncounters, "+
       "changed password leaf names to indicate hashed";
     reference
       "0.2.0";
   }
   revision "2017-01-29" {
     description
       "Initial public release";
     reference
       "0.1.0";
   }
 }

/*
Copyright (C) 2020 Huawei Technologies Co., Ltd. All rights reserved.
*/

 module huawei-l2vpn-extension-deviations-OC-NE-X8X16 {
   namespace "urn:huawei:yang:huawei-l2vpn-extension-deviations-OC-NE-X8X16";
   prefix "l2vpn-extension-devs-OC-NE-X8X16";
   import huawei-qos {
     prefix "qos";
   }
   import huawei-l2vpn {
     prefix "l2vpn";
   }
   import huawei-l2vpn-extension {
     prefix "l2vpn-extension";
   }
   organization
     "Huawei Technologies Co., Ltd.";
   contact
     "Huawei Industrial Base\nBantian, Longgang\nShenzhen 518129\nPeople's "+
     "Republic of China\nWebsite: http://www.huawei.com\nEmail: support@huawei.c"+
     "om";
   description
     "L2VPN extension.";
   revision "2020-04-22" {
     description
       "Initial revision.";
     reference
       "Huawei private.";
   }
   deviation "/l2vpn:l2vpn/l2vpn:instances/l2vpn:instance/l2vpn:vpls/l2vpn-exten"+
             "sion:qos-parameter/l2vpn-extension:profile-name" {
     deviate "add" {
       must "(. and /qos:qos/qos:queue-scheduler-template/qos:profiles/qos:profi"+
            "le[qos:name=current()]/qos:mode != '8cos-enhance') or not(.)";
     }
   }
   deviation "/l2vpn:l2vpn/l2vpn:instances/l2vpn:instance/l2vpn:vpls/l2vpn:ldp-s"+
             "ignaling/l2vpn:pws/l2vpn:pw/l2vpn-extension:qos-parameter/l2vpn-ex"+
             "tension:profile-name" {
     deviate "add" {
       must "(. and /qos:qos/qos:queue-scheduler-template/qos:profiles/qos:profi"+
            "le[qos:name=current()]/qos:mode != '8cos-enhance') or not(.)";
     }
   }
   deviation "/l2vpn:l2vpn/l2vpn:instances/l2vpn:instance/l2vpn:vpws-ldp/l2vpn:p"+
             "ws/l2vpn:pw/l2vpn-extension:qos-parameter/l2vpn-extension:profile-"+
             "name" {
     deviate "add" {
       must "(. and /qos:qos/qos:queue-scheduler-template/qos:profiles/qos:profi"+
            "le[qos:name=current()]/qos:mode != '8cos-enhance') or not(.)";
     }
   }
   deviation "/l2vpn:l2vpn/l2vpn:instances/l2vpn:instance/l2vpn:vpws-switch/l2vp"+
             "n:pws/l2vpn:pw/l2vpn-extension:qos-parameter/l2vpn-extension:profi"+
             "le-name" {
     deviate "add" {
       must "(. and /qos:qos/qos:queue-scheduler-template/qos:profiles/qos:profi"+
            "le[qos:name=current()]/qos:mode != '8cos-enhance') or not(.)";
     }
   }
   deviation "/l2vpn:l2vpn/l2vpn:common/l2vpn:pw-templates/l2vpn:pw-template/l2v"+
             "pn-extension:qos-parameter/l2vpn-extension:profile-name" {
     deviate "add" {
       must "(. and /qos:qos/qos:queue-scheduler-template/qos:profiles/qos:profi"+
            "le[qos:name=current()]/qos:mode != '8cos-enhance') or not(.)";
     }
   }
 }

/*
Copyright (C) 2021 Huawei Technologies Co., Ltd. All rights reserved.
*/

 module huawei-ntp-deviations-OC-NE-X8X16 {
   namespace "urn:huawei:yang:huawei-ntp-deviations-OC-NE-X8X16";
   prefix "ntp-devs-OC-NE-X8X16";
   import huawei-ntp {
     prefix "ntp";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-ntp module.";
   revision "2021-05-07" {
     description
       "Initial revision.";
     reference
       "Huawei private.";
   }
   deviation "/ntp:ntp/ntp:system-config/ntp:is-auth-password-check" {
     deviate "replace" {
       default "false";
     }
   }
   deviation "/ntp:ntp/ntp:access-controls/ntp:access-control" {
     deviate "add" {
       must "acl4-identity or acl6-identity";
     }
   }
 }

module ietf-yang-library {
   namespace "urn:ietf:params:xml:ns:yang:ietf-yang-library";
   prefix "yanglib";
   import ietf-yang-types {
     prefix "yang";
   }
   import ietf-inet-types {
     prefix "inet";
   }
   organization
     "IETF NETCONF (Network Configuration) Working Group";
   contact
     "WG Web:   <https://datatracker.ietf.org/wg/netconf/>\nWG List:  <mailto:ne"+
     "tconf@ietf.org>\n\nWG Chair: Mehmet Ersue\n          <mailto:mehmet.ersue@"+
     "nsn.com>\n\nWG Chair: Mahesh Jethanandani\n          <mailto:mjethanandani"+
     "@gmail.com>\n\nEditor:   Andy Bierman\n          <mailto:andy@yumaworks.co"+
     "m>\n\nEditor:   Martin Bjorklund\n          <mailto:mbj@tail-f.com>\n\nEdi"+
     "tor:   Kent Watsen\n          <mailto:kwatsen@juniper.net>";
   description
     "This module contains monitoring information about the YANG\nmodules and "+
     "submodules that are used within a YANG-based\nserver.\n\nCopyright (c) "+
     "2016 IETF Trust and the persons identified as\nauthors of the code.  All "+
     "rights reserved.\n\nRedistribution and use in source and binary forms, "+
     "with or\nwithout modification, is permitted pursuant to, and subject\nto "+
     "the license terms contained in, the Simplified BSD License\nset forth in "+
     "Section 4.c of the IETF Trust's Legal Provisions\nRelating to IETF "+
     "Documents\n(http://trustee.ietf.org/license-info).\n\nThis version of this"+
     " YANG module is part of RFC 7895; see\nthe RFC itself for full legal "+
     "notices.";
   revision "2016-06-21" {
     description
       "Initial revision.";
     reference
       "RFC 7895: YANG Module Library.";
   }
   typedef revision-identifier {
     type "string" {
       pattern "\\d{4}-\\d{2}-\\d{2}";
     }
     description
       "Represents a specific date in YYYY-MM-DD format.";
   }
   container modules-state {
     config "false";
     description
       "Contains YANG module monitoring information.";
     leaf module-set-id {
       type "string";
       mandatory "true";
       description
         "Contains a server-specific identifier representing\nthe current set of"+
         " modules and submodules.  The\nserver MUST change the value of this "+
         "leaf if the\ninformation represented by the 'module' list instances\nh"+
         "as changed.";
     }
     list module {
       key "name revision";
       description
         "Each entry represents one revision of one module\ncurrently supported "+
         "by the server.";
       leaf name {
         type "yang:yang-identifier";
         description
           "The YANG module or submodule name.";
       }
       leaf revision {
         type "union" {
           type "revision-identifier";
           type "string" {
             length "0";
           }
         }
         description
           "The YANG module or submodule revision date.\nA zero-length string is"+
           " used if no revision statement\nis present in the YANG module or "+
           "submodule.";
       }
       leaf schema {
         type "inet:uri";
         description
           "Contains a URL that represents the YANG schema\nresource for this "+
           "module or submodule.\n\nThis leaf will only be present if there is a"+
           " URL\navailable for retrieval of the schema for this entry.";
       }
       leaf namespace {
         type "inet:uri";
         mandatory "true";
         description
           "The XML namespace identifier for this module.";
       }
       leaf-list feature {
         type "yang:yang-identifier";
         description
           "List of YANG feature names from this module that are\nsupported by "+
           "the server, regardless of whether they are\ndefined in the module or"+
           " any included submodule.";
       }
       list deviation {
         key "name revision";
         description
           "List of YANG deviation module names and revisions\nused by this "+
           "server to modify the conformance of\nthe module associated with this"+
           " entry.  Note that\nthe same module can be used for deviations "+
           "for\nmultiple modules, so the same entry MAY appear\nwithin multiple"+
           " 'module' entries.\n\nThe deviation module MUST be present in the "+
           "'module'\nlist, with the same name and revision values.\nThe "+
           "'conformance-type' value will be 'implement' for\nthe deviation "+
           "module.";
         leaf name {
           type "yang:yang-identifier";
           description
             "The YANG module or submodule name.";
         }
         leaf revision {
           type "union" {
             type "revision-identifier";
             type "string" {
               length "0";
             }
           }
           description
             "The YANG module or submodule revision date.\nA zero-length string "+
             "is used if no revision statement\nis present in the YANG module or"+
             " submodule.";
         }
       }
       leaf conformance-type {
         type "enumeration" {
           enum "implement" {
             description
               "Indicates that the server implements one or more\nprotocol-acces"+
               "sible objects defined in the YANG module\nidentified in this "+
               "entry.  This includes deviation\nstatements defined in the "+
               "module.\n\nFor YANG version 1.1 modules, there is at most "+
               "one\nmodule entry with conformance type 'implement' for "+
               "a\nparticular module name, since YANG 1.1 requires that,\nat "+
               "most, one revision of a module is implemented.\n\nFor YANG "+
               "version 1 modules, there SHOULD NOT be more\nthan one module "+
               "entry for a particular module name.";
           }
           enum "import" {
             description
               "Indicates that the server imports reusable definitions\nfrom the"+
               " specified revision of the module but does\nnot implement any "+
               "protocol-accessible objects from\nthis revision.\n\nMultiple "+
               "module entries for the same module name MAY\nexist.  This can "+
               "occur if multiple modules import the\nsame module but specify "+
               "different revision dates in\nthe import statements.";
           }
         }
         mandatory "true";
         description
           "Indicates the type of conformance the server is claiming\nfor the "+
           "YANG module identified by this entry.";
       }
       list submodule {
         key "name revision";
         description
           "Each entry represents one submodule within the\nparent module.";
         leaf name {
           type "yang:yang-identifier";
           description
             "The YANG module or submodule name.";
         }
         leaf revision {
           type "union" {
             type "revision-identifier";
             type "string" {
               length "0";
             }
           }
           description
             "The YANG module or submodule revision date.\nA zero-length string "+
             "is used if no revision statement\nis present in the YANG module or"+
             " submodule.";
         }
         leaf schema {
           type "inet:uri";
           description
             "Contains a URL that represents the YANG schema\nresource for this "+
             "module or submodule.\n\nThis leaf will only be present if there is"+
             " a URL\navailable for retrieval of the schema for this entry.";
         }
       }
     }
   }
   notification yang-library-change {
     description
       "Generated when the set of modules and submodules supported\nby the "+
       "server has changed.";
     leaf module-set-id {
       type "leafref" {
         path "/yanglib:modules-state/yanglib:module-set-id";
       }
       mandatory "true";
       description
         "Contains the module-set-id value representing the\nset of modules and "+
         "submodules supported at the server at\nthe time the notification is "+
         "generated.";
     }
   }
 }

/*
Copyright (C) 2019-2021 Huawei Technologies Co., Ltd. All rights reserved.
*/

 module huawei-mplstpoam-deviations-OC-NE-X8X16 {
   yang-version "1";
   namespace "urn:huawei:yang:huawei-mplstpoam-deviations-OC-NE-X8X16";
   prefix "mplstpoam-devs-OC-NE-X8X16";
   import huawei-mplstpoam {
     prefix "mplstpoam";
   }
   organization
     "Huawei Technologies Co., Ltd.";
   contact
     "Huawei Industrial Base\nBantian, Longgang\nShenzhen 518129\nPeople's "+
     "Republic of China\nWebsite: http://www.huawei.com\nEmail: support@huawei.c"+
     "om";
   description
     "Multiprotocol Label Switching-Transport Profile (MPLS-TP), operations, "+
     "administration and maintenance (OAM), mainly provides functions: fault "+
     "management, performance monitoring, and protection switching.";
   revision "2021-01-13" {
     description
       "Solve some errors.";
     reference
       "Huawei private.";
   }
   revision "2019-10-18" {
     description
       "Initial revision.";
     reference
       "Huawei private.";
   }
   typedef gal-pw-deviations {
     type "enumeration" {
       enum "label-13" {
         value "1";
         description
           "The Gal is 13.";
       }
       enum "label-14" {
         value "2";
         description
           "The Gal is 14.";
       }
       enum "disable" {
         value "3";
         description
           "The GAL type is disable.";
       }
     }
     description
       "Gal PW type.";
   }
   deviation "/mplstpoam:mplstpoam/mplstpoam:megs/mplstpoam:meg/mplstpoam:pw/mpl"+
             "stpoam:pw-vll/mplstpoam:gal-mode" {
     deviate "replace" {
       type "mplstpoam-devs-OC-NE-X8X16:gal-pw-deviations";
     }
   }
   deviation "/mplstpoam:mplstpoam/mplstpoam:megs/mplstpoam:meg/mplstpoam:pw/mpl"+
             "stpoam:pw-vpls/mplstpoam:gal-mode" {
     deviate "replace" {
       type "mplstpoam-devs-OC-NE-X8X16:gal-pw-deviations";
     }
   }
 }

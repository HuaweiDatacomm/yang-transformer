/*
Copyright (C) 2019 Huawei Technologies Co., Ltd. All rights reserved.
*/

 module huawei-driver-deviations-OC-NE-X8X16 {
   namespace "urn:huawei:yang:huawei-driver-deviations-OC-NE-X8X16";
   prefix "driver-devs-OC-NE-X8X16";
   import huawei-driver {
     prefix "driver";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-driver module.";
   revision "2019-11-06" {
     description
       "Initial revision.";
     reference
       "Huawei private.";
   }
   typedef fan-workmode-deviations {
     type "enumeration" {
       enum "auto" {
         value "1";
         description
           "Automatic.";
       }
       enum "manual" {
         value "2";
         description
           "Percent.";
       }
       enum "silent" {
         value "4";
         description
           "Silent.";
       }
       enum "full" {
         value "5";
         description
           "Full.";
       }
       enum "minimum-percent" {
         value "9";
         description
           "Minimum-percent.";
       }
     }
     description
       "Information of enum type fan-workmode.";
   }
   typedef pwr-supply-temp-type-deviations {
     type "enumeration" {
       enum "templow" {
         value "40";
         description
           "40.";
       }
       enum "temphigh" {
         value "55";
         description
           "55.";
       }
     }
     description
       "Information of enum type pwr-supply-temp-type.";
   }
   typedef trap-type-deviations {
     type "enumeration" {
       enum "base-trap" {
         value "1";
         description
           "Base-trap.";
       }
       enum "entity-trap" {
         value "4";
         description
           "Entity-trap.";
       }
     }
     description
       "Information of enum type trap-type.";
   }
   typedef energy-mode-type-deviations {
     type "enumeration" {
       enum "basic" {
         value "0";
         description
           "Basic.";
       }
       enum "standard" {
         value "1";
         description
           "Standard.";
       }
       enum "deep" {
         value "2";
         description
           "Deep.";
       }
       enum "optimal" {
         value "3";
         description
           "Optimal.";
       }
     }
     description
       "Information of enum type energy-mode-type.";
   }
   deviation "/driver:driver/driver:global-attribute/driver:least-sfu-number" {
     deviate "replace" {
       type "uint32" {
         range "1..4";
       }
     }
   }
   deviation "/driver:driver/driver:global-attribute/driver:system-trap" {
     deviate "replace" {
       type "driver-devs-OC-NE-X8X16:trap-type-deviations";
     }
   }
   deviation "/driver:driver/driver:temperatures/driver:temperature" {
     deviate "add" {
       must "(minor and major and fatal) or (not(minor) and not(major) and "+
            "not(fatal))";
     }
   }
   deviation "/driver:driver/driver:voltageinfos/driver:voltageinfo" {
     deviate "add" {
       must "(major-voltage-threshold-low and major-voltage-threshold-high and "+
            "fatal-voltage-threshold-low and fatal-voltage-threshold-high) or "+
            "(not(major-voltage-threshold-low) and not(major-voltage-threshold-h"+
            "igh) and not(fatal-voltage-threshold-low) and not(fatal-voltage-thr"+
            "eshold-high))";
     }
   }
   deviation "/devm:devm/devm:chassiss/devm:chassis/driver:fan-attribute/driver:"+
             "workmode" {
     deviate "replace" {
       type "driver-devs-OC-NE-X8X16:fan-workmode-deviations";
     }
   }
   deviation "/devm:devm/devm:chassiss/devm:chassis/driver:power-supply-attribut"+
             "e/driver:power-supply-temp" {
     deviate "replace" {
       type "driver-devs-OC-NE-X8X16:pwr-supply-temp-type-deviations";
     }
   }
   deviation "/devm:devm/devm:chassiss/devm:chassis/driver:power-supply-attribut"+
             "e" {
     deviate "add" {
       must "not (power-supply-mode='assign' and not (power-supply-input))";
     }
   }
   deviation "/driver:driver/driver:global-attribute/driver:energy-mode" {
     deviate "replace" {
       type "driver-devs-OC-NE-X8X16:energy-mode-type-deviations";
     }
   }
 }

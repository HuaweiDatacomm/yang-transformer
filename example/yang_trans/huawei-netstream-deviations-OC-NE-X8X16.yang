/*
Copyright (C) 2019 Huawei Technologies Co., Ltd. All rights reserved.
*/

 module huawei-netstream-deviations-OC-NE-X8X16 {
   namespace "urn:huawei:yang:huawei-netstream-deviations-OC-NE-X8X16";
   prefix "netstream-devs-OC-NE-X8X16";
   import huawei-netstream {
     prefix "netstream";
   }
   import huawei-extension {
     prefix "ext";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-netstream module.";
   revision "2019-11-06" {
     description
       "Initial revision.";
     reference
       "Huawei private.";
   }
   ext:deviation-ext "/netstream:netstream/netstream:flow-instances/netstream:fl"+
                     "ow-instance/netstream:export-version" {
     ext:deviate-ext "add" {
       ext:dynamic-default {
         ext:default-value "5" {
           when "../flow-type='ip-flow'";
           description
             "The default value is 5 of version when flow type is IPv4.";
         }
       }
     }
   }
   deviation "/ifm:ifm/ifm:interfaces/ifm:interface/netstream:netstream/netstrea"+
             "m:sampler-enables/netstream:sampler-enable" {
     deviate "add" {
       must "../../../ifm:type='Ethernet' or\n../../../ifm:type='GigabitEthernet"+
            "' or\n../../../ifm:type='Eth-Trunk' or\n../../../ifm:type='100GE' "+
            "or\n../../../ifm:type='400GE' or\n../../../ifm:type='40GE' "+
            "or\n../../../ifm:type='50GE' or\n../../../ifm:type='50|100GE' "+
            "or\n../../../ifm:type='25GE' or\n../../../ifm:type='ATM' or\n../../"+
            "../ifm:type='FlexE' or\n../../../ifm:type='Serial' or\n../../../ifm"+
            ":type='Ip-Trunk' or\n../../../ifm:type='Mp-group' or\n../../../ifm:"+
            "type='Pos' or\n../../../ifm:type='Vbdif' or\n../../../ifm:type='Vla"+
            "nif' or\n(../../../ifm:type='Global-VE' and ../../../ifm:class='sub"+
            "-interface') or\n(../../../ifm:type='Virtual-Ethernet' and "+
            "../../../ifm:class='sub-interface')";
     }
   }
   deviation "/ifm:ifm/ifm:interfaces/ifm:interface/netstream:netstream/netstrea"+
             "m:sampler-rates/netstream:sampler-rate" {
     deviate "add" {
       must "../../../ifm:type='Ethernet' or\n../../../ifm:type='GigabitEthernet"+
            "' or\n../../../ifm:type='Eth-Trunk' or\n../../../ifm:type='100GE' "+
            "or\n../../../ifm:type='400GE' or\n../../../ifm:type='40GE' "+
            "or\n../../../ifm:type='50GE' or\n../../../ifm:type='50|100GE' "+
            "or\n../../../ifm:type='25GE' or\n../../../ifm:type='ATM' or\n../../"+
            "../ifm:type='FlexE' or\n../../../ifm:type='Serial' or\n../../../ifm"+
            ":type='Ip-Trunk' or\n../../../ifm:type='Mp-group' or\n../../../ifm:"+
            "type='Pos' or\n../../../ifm:type='Vbdif' or\n../../../ifm:type='Vla"+
            "nif' or\n(../../../ifm:type='Global-VE' and ../../../ifm:class='sub"+
            "-interface') or\n(../../../ifm:type='Virtual-Ethernet' and "+
            "../../../ifm:class='sub-interface')";
     }
   }
 }

/*
Copyright (C) 2020 Huawei Technologies Co., Ltd. All rights reserved.
*/

 module huawei-bier-fwd {
   namespace "urn:huawei:yang:huawei-bier-fwd";
   prefix "bier-fwd";
   import huawei-bier {
     prefix "bier";
   }
   import huawei-extension {
     prefix "ext";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "Bier forward.";
   revision "2020-02-13" {
     description
       "Init revision.";
     reference
       "Huawei private.";
   }
   ext:task-name "bier";
   container bier-fwd {
     description
       "Global configuration of bier-fwd.";
     container select-boards {
       description
         "Configure boards selected for bier.";
       leaf-list slot {
         type "leafref" {
           path "/devm:devm/devm:lpu-boards/devm:lpu-board/devm:position";
         }
         max-elements "20";
         description
           "Configure slot ID.";
       }
     }
   }
   augment "/bier:bier" {
     description
       "Configure global attributes to the BIER.";
     container forward {
       description
         "Configure global attributes to the BIER.";
       container reserve-interface-enhancement {
         description
           "Configure reserve-interface enhancement.";
         leaf enable {
           type "boolean";
           default "false";
           description
             "Enable/disable reserve-interface enhancement.";
         }
       }
     }
   }
   augment "/bier:bier/bier:sub-domains/bier:sub-domain" {
     description
       "Configure pipe mode ttl value.";
     container pipe-mode-ttl {
       description
         "Configure pipe mode ttl value.";
       leaf ttl-value {
         type "uint8" {
           range "1..255";
         }
         default "255";
         description
           "Bier pipe mode ttl value.";
       }
     }
     container load-balance-enhance-factor {
       when "../bier:address-family = 'ipv6-unicast'";
       description
         "Configure load-balance enhance factor.";
       leaf factor-value {
         type "uint8" {
           range "1..64";
         }
         must "(../bier-fwd:factor-value * ../../bier:load-balance-num) <= 64";
         description
           "Configure load-balance enhance factor.";
       }
     }
   }
 }

/*
Copyright (C) 2019-2021 Huawei Technologies Co., Ltd. All rights reserved.
*/

 module huawei-bgp-srpolicy {
   yang-version "1";
   namespace "urn:huawei:yang:huawei-bgp-srpolicy";
   prefix "bgp-srpolicy";
   import huawei-extension {
     prefix "ext";
   }
   import huawei-network-instance {
     prefix "ni";
   }
   import huawei-bgp {
     prefix "bgp";
   }
   import huawei-xpl {
     prefix "xpl";
   }
   import huawei-routing-policy {
     prefix "rtp";
   }
   import huawei-bgp-routing-table {
     prefix "bgp-rt";
   }
   import ietf-inet-types {
     prefix "inet";
   }
   import huawei-ifm {
     prefix "ifm";
   }
   import huawei-pub-type {
     prefix "pub-type";
   }
   organization
     "Huawei Technologies Co., Ltd.";
   contact
     "Huawei Industrial Base\nBantian, Longgang\nShenzhen 518129\nPeople's "+
     "Republic of China\nWebsite: http://www.huawei.com\nEmail: support@huawei.c"+
     "om";
   description
     "Inter-AS routing protocol that exchanges Network Layer Reachability "+
     "Information (NLRI) with other BGP systems.";
   revision "2021-08-28" {
     description
       "The YANG descriptions are modified according to new standards.";
     reference
       "Huawei private.";
   }
   revision "2019-03-22" {
     description
       "Initial revision.";
     reference
       "Huawei private.";
   }
   augment "/ni:network-instance/ni:instances/ni:instance/bgp:bgp/bgp:base-proce"+
           "ss/bgp:afs/bgp:af" {
     description
       "BGP IPv4-srpolicy address family configuration.";
     container ipv4-srpolicy {
       when "../bgp:type='ipv4srpolicy'";
       description
         "Configure IPv4-family srpolicy options.";
       container common {
         description
           "Configure IPv4-family srpolicy common options.";
         leaf routerid-neglect {
           type "boolean";
           default "false";
           description
             "Enable/disable BGP to ignore router IDs when selecting the optimal"+
             " route. Comparing router IDs is the last resort in route "+
             "selection. This means that if one optimal route must be selected "+
             "and no other parameters can be used to break the tie, router IDs "+
             "can be used. If this option is selected, the first received route "+
             "will be selected as the optimal route, and BGP will ignore the "+
             "router ID and peer address in route selection.";
         }
         leaf reflect-change-path {
           type "boolean";
           default "false";
           description
             "Enable/disable an RR to use an export policy to change route "+
             "AS_Path.";
         }
         leaf reflect-between-client {
           type "boolean";
           default "true";
           description
             "Enable/disable route reflection between clients. If clients of a "+
             "route reflector (RR) are fully meshed, you can disable route "+
             "reflection among clients to reduce the cost.";
         }
         choice reflector-type {
           description
             "Set IPv4 address or id.";
           case address {
             description
               "IPv4 address.";
             leaf reflector-cluster-ipv4 {
               type "inet:ipv4-address-no-zone";
               description
                 "Set a cluster ID. The value is expressed in the format of an "+
                 "IPv4 address. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
           case id {
             description
               "Set value.";
             leaf reflector-cluster-id {
               type "uint32" {
                 range "1..4294967295";
               }
               description
                 "Set a cluster ID. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
         }
         leaf router-id-filter {
           type "boolean";
           default "true";
           description
             "Enable/disable router ID filtering.";
         }
         leaf default-local-preference {
           type "uint32" {
             range "0..4294967295";
           }
           default "100";
           description
             "The local preference of BGP routes.";
         }
         leaf bestroute-as-path-ignore {
           type "boolean";
           default "false";
           description
             "Enable/disable BGP to ignore the AS_Path attribute when selecting "+
             "the optimal route. By default, BGP uses the AS_Path attribute as "+
             "one of route selection rules, and a route with a shorter AS_Path "+
             "is preferred. After bestroute-as-path-ignore is selected, BGP does"+
             " not compare the AS_Path length.";
         }
         leaf nexthop-select-depend-type {
           type "bgp:select-depend-ip-type";
           default "depend-ip";
           description
             "Specify the route iteration mode: IP or tunnel. In tunnel mode, "+
             "the labeled BGP IPv4 route can participate in route selection only"+
             " after its next hop is iterated to an LSP. In IP \nmode, the "+
             "labeled BGP IPv4 route can participate in route selection only "+
             "after its next hop is iterated to an IP address. By default, the "+
             "labeled BGP IPv4 route can participate in route selection \nif its"+
             " next hop can be iterated to an IP address, regardless of whether "+
             "the LSP of the next hop exists. This allows the RR that is not "+
             "enabled with MPLS to forward labeled routes. In non-RR \nnetworkin"+
             "g or RR networking where the BGP next hop is changed, BGP needs to"+
             " check whether there is an LSP destined for the next hop. If such "+
             "an LSP is not found, BGP needs to establish an LSP in \nadvance. "+
             "If the default setting is adopted, a labeled BGP IPv4 unicast "+
             "route may be selected prior to LSP establishment. As a result, "+
             "services are incorrectly switched before LSP establishment and "+
             "\nservice stability is affected. Therefore, allow route selection "+
             "only after the labeled BGP IPv4 route is iterated to an LSP.";
         }
         leaf advertise-ebgp {
           type "boolean";
           default "false";
           description
             "Enable/disable advertise to EBGP peer.";
         }
       }
     }
   }
   augment "/ni:network-instance/ni:instances/ni:instance/bgp:bgp/bgp:base-proce"+
           "ss/bgp:peers/bgp:peer/bgp:afs/bgp:af" {
     description
       "BGP peer IPv4-srpolicy address family configuration.";
     container ipv4-srpolicy {
       when "../bgp:type='ipv4srpolicy'";
       description
         "Configure IPv4-family srpolicy options.";
       leaf reflect-client {
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf advertise-ext-community {
         type "boolean";
         default "false";
         description
           "Enable/disable advertise the extended community attribute to a peer "+
           "or peer group.";
       }
       leaf allow-as-loop {
         type "uint32" {
           range "1..10";
         }
         description
           "Allow repetitive local AS numbers. By default, repetitive local AS "+
           "numbers are not allowed.";
       }
       leaf advertise-community {
         type "boolean";
         default "false";
         description
           "Enable/disable advertise the community attribute to a peer or a peer"+
           " group.";
       }
       leaf graceful-restart-static-timer {
         type "uint32" {
           range "3600..2147483647";
         }
         units "s";
         description
           "Specifies the maximum time during which a peer waits for a BGP "+
           "session reestablishment.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-large-community {
         type "bgp:peer-enable-config-type";
         default "default";
         description
           "Enable large-community attribute advertisement. The Link-state "+
           "address family and the RPD address family do not support this "+
           "element.";
       }
       leaf import-as-path-filter {
         type "leafref" {
           path "/rtp:routing-policy/rtp:as-path-filters/rtp:as-path-filter/rtp:"+
                "name";
         }
         description
           "Apply an AS_Path-based filtering policy to the routes received from "+
           "a specified peer. The policy can be identified with a name or "+
           "number, and the number ranges from 1 to 256. By default, no such "+
           "policy is specified. Therefore, all BGP routes can be accepted.";
       }
       leaf export-as-path-filter {
         type "leafref" {
           path "/rtp:routing-policy/rtp:as-path-filters/rtp:as-path-filter/rtp:"+
                "name";
         }
         description
           "Apply an AS_Path-based filtering policy to the routes to be "+
           "advertised to a specified peer. The policy can be identified with a "+
           "name or number, and the number ranges from 1 to 256. By default, no "+
           "such policy is specified. Therefore, all BGP routes can be "+
           "advertised.";
       }
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
   }
   augment "/bgp:bgp/bgp:base-process/bgp-rt:bgp-route" {
     description
       "BGP IPv4-srpolicy address family routes information.";
     container ipv4-srpolicy {
       config "false";
       description
         "Statistics of IPv4-srpolicy routes.";
       container routes {
         config "false";
         description
           "List of IPv4-srpolicy routing tables.";
         list route {
           key "vpn-name prefix from";
           description
             "Statistics of IPv4-srpolicy routing table.";
           leaf vpn-name {
             type "leafref" {
               path "/ni:network-instance/ni:instances/ni:instance/ni:name";
             }
             description
               "VPN name of a BGP instance.";
           }
           leaf prefix {
             type "string" {
               length "1..300";
             }
             description
               "SR-policy route prefix.";
           }
           leaf from {
             type "inet:ip-address-no-zone";
             description
               "Source peer that sends a route.";
           }
           leaf local-priority {
             type "uint32";
             description
               "Local priority.";
           }
           leaf preferred-value {
             type "uint32";
             description
               "Preferred value of a protocol.";
           }
           leaf preference {
             type "uint8";
             description
               "Preference of a route.";
           }
           leaf origin {
             type "bgp-rt:bgp-origin-type";
             description
               "Origin of a route.";
           }
           leaf med {
             type "uint32";
             description
               "Route MED in the attribute node.";
           }
           leaf flag-string {
             type "string" {
               length "1..100";
             }
             description
               "Route flag that contains a string of characters.";
           }
           leaf time {
             type "uint32";
             units "s";
             description
               "Time stamp of a route.";
           }
           leaf originator {
             type "inet:ip-address-no-zone";
             description
               "Router ID of the route initiator.";
           }
           leaf remote-router-id {
             type "inet:ipv4-address-no-zone";
             description
               "Router ID of a peer.";
           }
           leaf interface-name {
             type "leafref" {
               path "/ifm:ifm/ifm:interfaces/ifm:interface/ifm:name";
             }
             description
               "Name of the outbound interface of a route.";
           }
           leaf relay-nexthop {
             type "inet:ip-address-no-zone";
             description
               "Next hop to which a route is iterated.";
           }
           leaf worse-reason {
             type "string" {
               length "1..50";
             }
             description
               "Reason why a route is not selected.";
           }
         }
       }
       container statistic {
         description
           "Statistics of BGP routes information of sr-policy address family.";
         leaf total-number {
           type "uint32";
           description
             "Total number of routes.";
         }
       }
     }
   }
   ext:task-name "bgp";
 }

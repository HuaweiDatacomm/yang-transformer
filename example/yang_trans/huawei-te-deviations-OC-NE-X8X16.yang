/*
Copyright (C) 2019 Huawei Technologies Co., Ltd. All rights reserved.
*/

 module huawei-te-deviations-OC-NE-X8X16 {
   namespace "urn:huawei:yang:huawei-te-deviations-OC-NE-X8X16";
   prefix "te-devs-OC-NE-X8X16";
   import huawei-te {
     prefix "te";
   }
   organization
     "Huawei Technologies Co., Ltd.";
   contact
     "Huawei Industrial Base\nBantian, Longgang\nShenzhen 518129\nPeople's "+
     "Republic of China\nWebsite: http://www.huawei.com\nEmail: support@huawei.c"+
     "om";
   description
     "Specifies the multi-protocol label switching protocol.";
   revision "2019-03-27" {
     description
       "Init revision.";
     reference
       "Huawei private.";
   }
   typedef er-hop-mode-deviations {
     type "enumeration" {
       enum "ipv4-ipv6-address" {
         value "1";
         description
           "IPv4 or IPv6 address.";
       }
       enum "sid-label" {
         value "2";
         description
           "SID label.";
       }
     }
     description
       "ERHop Mode.";
   }
   deviation "/te:te/te:explicit-paths/te:explicit-path/te:hops/te:hop/te:mode" {
     deviate "replace" {
       type "te-devs-OC-NE-X8X16:er-hop-mode-deviations";
     }
   }
   deviation "/te:te/te:explicit-paths/te:explicit-path/te:hops/te:hop" {
     deviate "add" {
       must "(mode = 'ipv4-ipv6-address') or ((mode = 'sid-label') and "+
            "(count(../hop) < 11))";
     }
   }
 }

/*
Copyright (C) 2020 Huawei Technologies Co., Ltd. All rights reserved.
*/

 module huawei-diagnostic-tools-deviations-OC-NE-X8X16 {
   namespace "urn:huawei:yang:huawei-diagnostic-tools-deviations-OC-NE-X8X16";
   prefix "diagnostic-tools-devs-OC-NE-X8X16";
   import huawei-diagnostic-tools {
     prefix "diagnostic-tools";
   }
   import huawei-y1731 {
     prefix "y1731";
   }
   import huawei-l2vpn {
     prefix "l2vpn";
   }
   import huawei-network-instance {
     prefix "ni";
   }
   import huawei-segment-routing {
     prefix "sr";
   }
   import huawei-srpolicy {
     prefix "srpolicy";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-diagnostic-tools "+
     "module.";
   revision "2020-08-28" {
     description
       "Initial revision.";
     reference
       "Huawei private.";
   }
   typedef pw-type-deviations {
     type "enumeration" {
       enum "atm-trans-cell" {
         value "3";
         description
           "ATM transparent cell transport.";
       }
       enum "vlan" {
         value "4";
         description
           "VLAN encapsulation.";
       }
       enum "ethernet" {
         value "5";
         description
           "Ethernet encapsulation.";
       }
       enum "hdlc" {
         value "6";
         description
           "HDLC encapsulation.";
       }
       enum "ppp" {
         value "7";
         description
           "PPP encapsulation.";
       }
       enum "atm-nto1-vcc" {
         value "9";
         description
           "ATM n-to-one VCC cell transport.";
       }
       enum "atm-nto1-vpc" {
         value "10";
         description
           "ATM n-to-one VPC cell transport.";
       }
       enum "ip-layer2" {
         value "11";
         description
           "IP-layer2 encapsulation.";
       }
       enum "atm-1to1-vcc" {
         value "12";
         description
           "ATM one-to-one VCC Cell Mode.";
       }
       enum "atm-1to1-vpc" {
         value "13";
         description
           "ATM one-to-one VPC Cell Mode.";
       }
       enum "cep" {
         value "16";
         description
           "CEP encapsulation.";
       }
       enum "satop-e1" {
         value "17";
         description
           "Structure-agnostic E1 over Packet.";
       }
       enum "cesopsn-basic" {
         value "21";
         description
           "CESoPSN basic mode.";
       }
       enum "ip-interworking" {
         value "64";
         description
           "MPLS L2VPN IP interworking.";
       }
     }
     description
       "Description of pw-type.";
   }
   deviation "/diagnostic-tools:pwe3-start-ping/diagnostic-tools:input/diagnosti"+
             "c-tools:detection-type/diagnostic-tools:vpws-bgp-vpn-instance/diag"+
             "nostic-tools:vpws-bgp-vpn-name" {
     deviate "replace" {
       type "leafref" {
         path "/l2vpn:l2vpn/l2vpn:common/l2vpn:vpws-bgp-vpns/l2vpn:vpws-bgp-vpn/"+
              "l2vpn:name";
       }
     }
   }
   deviation "/diagnostic-tools:pwe3-start-trace/diagnostic-tools:input/diagnost"+
             "ic-tools:detection-type/diagnostic-tools:vpws-bgp-vpn-instance/dia"+
             "gnostic-tools:vpws-bgp-vpn-name" {
     deviate "replace" {
       type "leafref" {
         path "/l2vpn:l2vpn/l2vpn:common/l2vpn:vpws-bgp-vpns/l2vpn:vpws-bgp-vpn/"+
              "l2vpn:name";
       }
     }
   }
   deviation "/diagnostic-tools:pwe3-start-ping/diagnostic-tools:input/diagnosti"+
             "c-tools:detection-type/diagnostic-tools:pw-id/diagnostic-tools:pw-"+
             "type" {
     deviate "replace" {
       type "diagnostic-tools-devs-OC-NE-X8X16:pw-type-deviations";
     }
   }
   deviation "/diagnostic-tools:start-lb-test/diagnostic-tools:input/diagnostic-"+
             "tools:md-name" {
     deviate "replace" {
       type "leafref" {
         path "/y1731:y1731/y1731:global-enable/y1731:mds/y1731:md/y1731:name";
       }
     }
   }
   deviation "/diagnostic-tools:start-lb-test/diagnostic-tools:input/diagnostic-"+
             "tools:ma-name" {
     deviate "replace" {
       type "leafref" {
         path "/y1731:y1731/y1731:global-enable/y1731:mds/y1731:md[y1731:name=cu"+
              "rrent()/../md-name]/y1731:mas/y1731:ma/y1731:name";
       }
     }
   }
   deviation "/diagnostic-tools:start-lb-test/diagnostic-tools:input/diagnostic-"+
             "tools:mep-id" {
     deviate "replace" {
       type "leafref" {
         path "/y1731:y1731/y1731:global-enable/y1731:mds/y1731:md[y1731:name=cu"+
              "rrent()/../md-name]/y1731:mas/y1731:ma[y1731:name=current()/../ma"+
              "-name]/y1731:meps/y1731:mep/y1731:id";
       }
     }
   }
   deviation "/diagnostic-tools:start-lb-test/diagnostic-tools:input/diagnostic-"+
             "tools:remote/diagnostic-tools:remote-mep-id/diagnostic-tools:rmep-"+
             "id" {
     deviate "replace" {
       type "leafref" {
         path "/y1731:y1731/y1731:global-enable/y1731:mds/y1731:md[y1731:name=cu"+
              "rrent()/../md-name]/y1731:mas/y1731:ma[y1731:name=current()/../ma"+
              "-name]/y1731:rmeps/y1731:rmep/y1731:id";
       }
     }
   }
   deviation "/diagnostic-tools:start-lt-test/diagnostic-tools:input/diagnostic-"+
             "tools:md-name" {
     deviate "replace" {
       type "leafref" {
         path "/y1731:y1731/y1731:global-enable/y1731:mds/y1731:md/y1731:name";
       }
     }
   }
   deviation "/diagnostic-tools:start-lt-test/diagnostic-tools:input/diagnostic-"+
             "tools:ma-name" {
     deviate "replace" {
       type "leafref" {
         path "/y1731:y1731/y1731:global-enable/y1731:mds/y1731:md[y1731:name=cu"+
              "rrent()/../md-name]/y1731:mas/y1731:ma/y1731:name";
       }
     }
   }
   deviation "/diagnostic-tools:start-lt-test/diagnostic-tools:input/diagnostic-"+
             "tools:mep-id" {
     deviate "replace" {
       type "leafref" {
         path "/y1731:y1731/y1731:global-enable/y1731:mds/y1731:md[y1731:name=cu"+
              "rrent()/../md-name]/y1731:mas/y1731:ma[y1731:name=current()/../ma"+
              "-name]/y1731:meps/y1731:mep/y1731:id";
       }
     }
   }
   deviation "/diagnostic-tools:start-lt-test/diagnostic-tools:input/diagnostic-"+
             "tools:remote/diagnostic-tools:remote-mep-id/diagnostic-tools:rmep-"+
             "id" {
     deviate "replace" {
       type "leafref" {
         path "/y1731:y1731/y1731:global-enable/y1731:mds/y1731:md[y1731:name=cu"+
              "rrent()/../md-name]/y1731:mas/y1731:ma[y1731:name=current()/../ma"+
              "-name]/y1731:rmeps/y1731:rmep/y1731:id";
       }
     }
   }
   deviation "/diagnostic-tools:pwe3-start-trace/diagnostic-tools:input/diagnost"+
             "ic-tools:detection-type/diagnostic-tools:pw-id/diagnostic-tools:pw"+
             "-type" {
     deviate "replace" {
       type "diagnostic-tools-devs-OC-NE-X8X16:pw-type-deviations";
     }
   }
   deviation "/diagnostic-tools:vpls-start-vsi-ping/diagnostic-tools:input/diagn"+
             "ostic-tools:vsi-name" {
     deviate "replace" {
       type "leafref" {
         path "/l2vpn:l2vpn/l2vpn:instances/l2vpn:instance/l2vpn:name";
       }
     }
   }
   deviation "/diagnostic-tools:start-lsp-ping/diagnostic-tools:input/diagnostic"+
             "-tools:lsp-protocol/diagnostic-tools:srte-policy/diagnostic-tools:"+
             "probe-type/diagnostic-tools:policy-name/diagnostic-tools:policy-na"+
             "me" {
     deviate "replace" {
       type "leafref" {
         path "/ni:network-instance/ni:instances/ni:instance/sr:segment-routing/"+
              "srpolicy:srpolicy/srpolicy:policys/srpolicy:policy/srpolicy:name";
       }
     }
   }
   deviation "/diagnostic-tools:start-lsp-trace/diagnostic-tools:input/diagnosti"+
             "c-tools:lsp-protocol/diagnostic-tools:srte-policy/diagnostic-tools"+
             ":probe-type/diagnostic-tools:policy-name/diagnostic-tools:policy-n"+
             "ame" {
     deviate "replace" {
       type "leafref" {
         path "/ni:network-instance/ni:instances/ni:instance/sr:segment-routing/"+
              "srpolicy:srpolicy/srpolicy:policys/srpolicy:policy/srpolicy:name";
       }
     }
   }
 }

/*
Copyright (C) 2020 Huawei Technologies Co., Ltd. All rights reserved.
*/

 submodule huawei-dhcp-snooping {
   yang-version "1";
   belongs-to huawei-dhcp {
     prefix "dhcp";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module contains a collection of YANG definitions for managing DHCP "+
     "snooping.";
   revision "2020-02-25" {
     description
       "Initial revision.";
     reference
       "Huawei private.";
   }
   typedef dhcp-snooping-port {
     type "enumeration" {
       enum "bootps" {
         value "0";
         description
           "Bootps(67).";
       }
       enum "bootpc" {
         value "1";
         description
           "Bootpc(68).";
       }
     }
     description
       "The type of DHCP snooping port.";
   }
   typedef snooping-file-authentication-mode {
     type "enumeration" {
       enum "check" {
         value "0";
         description
           "Check.";
       }
       enum "no-check" {
         value "1";
         description
           "No-check.";
       }
       enum "force-check" {
         value "2";
         description
           "Force-check.";
       }
     }
     description
       "The type of file authentication mode.";
   }
 }

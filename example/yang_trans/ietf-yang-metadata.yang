module ietf-yang-metadata {
   namespace "urn:ietf:params:xml:ns:yang:ietf-yang-metadata";
   prefix "md";
   organization
     "IETF NETMOD (NETCONF Data Modeling Language) Working Group";
   contact
     "WG Web:   <http://tools.ietf.org/wg/netmod/>\nWG List:  <mailto:netmod@iet"+
     "f.org>\n\nWG Chair: Lou Berger\n          <mailto:lberger@labn.net>\n\nWG "+
     "Chair: Juergen Schoenwaelder\n          <mailto:j.schoenwaelder@jacobs-uni"+
     "versity.de>\n\nWG Chair: Kent Watsen\n          <mailto:kwatsen@juniper.ne"+
     "t>\n\nEditor:   Ladislav Lhotka\n          <mailto:lhotka@nic.cz>";
   description
     "This YANG module defines an extension statement that allows for\n defining"+
     " metadata annotations.\n\n Copyright (c) 2016 IETF Trust and the persons "+
     "identified as\n authors of the code. All rights reserved.\n\n Redistributi"+
     "on and use in source and binary forms, with or\n without modification, is "+
     "permitted pursuant to, and subject to\n the license terms contained in, "+
     "the Simplified BSD License set\n forth in Section 4.c of the IETF Trust's "+
     "Legal Provisions\n Relating to IETF Documents\n (http://trustee.ietf.org/l"+
     "icense-info).\n\n This version of this YANG module is part of RFC XXXX\n "+
     "(http://tools.ietf.org/html/rfcXXXX); see the RFC itself for\n full legal "+
     "notices.";
   revision "2016-03-21" {
     description
       "Initial revision.";
     reference
       "RFC XXXX: Defining and Using Metadata with YANG";
   }
   extension annotation {
     argument name;
     description
       "This extension allows for defining metadata annotations in\nYANG "+
       "modules. The 'md:annotation' statement can appear only at\nthe top level"+
       " of a YANG module or submodule, i.e. it becomes a\nnew alternative in "+
       "the ABNF production rule for 'body-stmts'\n(sec. 14 in RFC 6020bis).\nTh"+
       "e argument of the 'md:annotation' statement defines the name\nof the "+
       "annotation. Syntactically it is a YANG identifier as\ndefined in RFC "+
       "6020bis, sec. 6.2.\n\nAn annotation defined with this extension "+
       "statement inherits\nthe namespace and other context from the YANG module"+
       " in which\nit is defined.\n\nData type of the annotation value is "+
       "specified in the same way\nas for a leaf data node using the 'type' "+
       "statement.\n\nSemantics of the annotation and other documentation can "+
       "be\nspecified using the following standard YANG substatements (all\nare "+
       "optional): 'description', 'if-feature', 'reference',\n'status', and "+
       "'units'.\n\nA server announces support for a particular annotation "+
       "by\nincluding the module in which the annotation is defined among\nthe "+
       "advertised YANG modules (e.g., in NETCONF hello message or\nyang-library"+
       "). The annotation then can be attached to any\ninstance of data node "+
       "defined in any YANG module that is\nadvertised by the server.\n\nXML and"+
       " JSON encoding of annotations is defined in\nRFC XXXX.";
   }
 }

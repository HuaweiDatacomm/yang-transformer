/*
Copyright (C) 2019 Huawei Technologies Co., Ltd. All rights reserved.
*/

 module huawei-srpolicy-deviations-OC-NE-X8X16 {
   namespace "urn:huawei:yang:huawei-srpolicy-deviations-OC-NE-X8X16";
   prefix "srpolicy-devs-OC-NE-X8X16";
   import huawei-srpolicy {
     prefix "srpolicy";
   }
   import huawei-segment-routing {
     prefix "sr";
   }
   import huawei-network-instance {
     prefix "ni";
   }
   import huawei-srv6 {
     prefix "srv6";
   }
   import huawei-net-slice {
     prefix "net-slice";
   }
   organization
     "Huawei Technologies Co., Ltd.";
   contact
     "Huawei Industrial Base\nBantian, Longgang\nShenzhen 518129\nPeople's "+
     "Republic of China\nWebsite: http://www.huawei.com\nEmail: support@huawei.c"+
     "om";
   description
     "Common srpolicy management, which includes the public configuration of "+
     "srpolicies.";
   revision "2019-03-22" {
     description
       "Initial revision.";
     reference
       "Huawei private.";
   }
   typedef bfd-enable-type-deviations {
     type "enumeration" {
       enum "disable" {
         value "0";
         description
           "Disable.";
       }
       enum "sbfd-enable" {
         value "1";
         description
           "SBFD enable.";
       }
     }
     description
       "BFD enable type.";
   }
   typedef policy-bfd-enable-type-deviations {
     type "enumeration" {
       enum "not-configured" {
         value "0";
         description
           "Not configured.";
       }
       enum "sbfd-enable" {
         value "1";
         description
           "SBFD enable.";
       }
       enum "disable" {
         value "2";
         description
           "Disable.";
       }
     }
     description
       "BFD enable type for SR Policy.";
   }
   deviation "/ni:network-instance/ni:instances/ni:instance/sr:segment-routing/s"+
             "rpolicy:srpolicy/srpolicy:policy-attributes/srpolicy:bfd/srpolicy:"+
             "min-tx" {
     deviate "replace" {
       type "uint32" {
         range "3..20000";
       }
     }
   }
   deviation "/ni:network-instance/ni:instances/ni:instance/sr:segment-routing/s"+
             "rpolicy:srpolicy/srpolicy:policy-attributes/srpolicy:bfd/srpolicy:"+
             "min-rx" {
     deviate "replace" {
       type "uint32" {
         range "3..20000";
       }
     }
   }
   deviation "/ni:network-instance/ni:instances/ni:instance/srv6:srv6/srpolicy:s"+
             "rpolicy/srpolicy:policy-attributes/srpolicy:bfd/srpolicy:min-tx" {
     deviate "replace" {
       type "uint32" {
         range "3..20000";
       }
     }
   }
   deviation "/ni:network-instance/ni:instances/ni:instance/srv6:srv6/srpolicy:s"+
             "rpolicy/srpolicy:policys/srpolicy:policy/srpolicy:candidate-paths/"+
             "srpolicy:candidate-path/srpolicy:network-slice-id" {
     deviate "replace" {
       type "leafref" {
         path "/net-slice:net-slice/net-slice:instances/net-slice:instance/net-s"+
              "lice:id";
       }
     }
   }
   deviation "/ni:network-instance/ni:instances/ni:instance/srv6:srv6/srpolicy:s"+
             "rpolicy/srpolicy:policy-attributes/srpolicy:bfd/srpolicy:backup-mi"+
             "n-tx" {
     deviate "replace" {
       type "uint32" {
         range "3..20000";
       }
     }
   }
   deviation "/ni:network-instance/ni:instances/ni:instance/srv6:srv6/srpolicy:s"+
             "rpolicy/srpolicy:policys/srpolicy:policy/srpolicy:bfd-min-tx" {
     deviate "replace" {
       type "uint32" {
         range "3..20000";
       }
     }
   }
   deviation "/ni:network-instance/ni:instances/ni:instance/srv6:srv6/srpolicy:s"+
             "rpolicy/srpolicy:policys/srpolicy:policy/srpolicy:bfd-backup-min-t"+
             "x" {
     deviate "replace" {
       type "uint32" {
         range "3..20000";
       }
     }
   }
   deviation "/ni:network-instance/ni:instances/ni:instance/sr:segment-routing/s"+
             "rpolicy:srpolicy/srpolicy:policy-attributes/srpolicy:bfd/srpolicy:"+
             "enable" {
     deviate "replace" {
       type "srpolicy-devs-OC-NE-X8X16:bfd-enable-type-deviations";
     }
   }
   deviation "/ni:network-instance/ni:instances/ni:instance/sr:segment-routing/s"+
             "rpolicy:srpolicy/srpolicy:policys/srpolicy:policy/srpolicy:bfd-ena"+
             "ble" {
     deviate "replace" {
       type "srpolicy-devs-OC-NE-X8X16:policy-bfd-enable-type-deviations";
     }
   }
 }

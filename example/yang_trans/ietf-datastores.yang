module ietf-datastores {
   yang-version "1.1";
   namespace "urn:ietf:params:xml:ns:yang:ietf-datastores";
   prefix "ds";
   organization
     "IETF Network Modeling (NETMOD) Working Group";
   contact
     "WG Web:   <https://datatracker.ietf.org/wg/netmod/>\n\nWG List:  "+
     "<mailto:netmod@ietf.org>\n\nAuthor:   Martin Bjorklund\n          "+
     "<mailto:mbj@tail-f.com>\n\nAuthor:   Juergen Schoenwaelder\n          "+
     "<mailto:j.schoenwaelder@jacobs-university.de>\n\nAuthor:   Phil Shafer\n  "+
     "        <mailto:phil@juniper.net>\n\nAuthor:   Kent Watsen\n          "+
     "<mailto:kwatsen@juniper.net>\n\nAuthor:   Rob Wilton\n          <rwilton@c"+
     "isco.com>";
   description
     "This YANG module defines a set of identities for identifying\ndatastores."+
     "\n\nCopyright (c) 2018 IETF Trust and the persons identified as\nauthors "+
     "of the code.  All rights reserved.\n\nRedistribution and use in source and"+
     " binary forms, with or\nwithout modification, is permitted pursuant to, "+
     "and subject to\nthe license terms contained in, the Simplified BSD License"+
     " set\nforth in Section 4.c of the IETF Trust's Legal Provisions\nRelating "+
     "to IETF Documents\n(https://trustee.ietf.org/license-info).\n\nThis "+
     "version of this YANG module is part of RFC 8342\n(https://www.rfc-editor.o"+
     "rg/info/rfc8342); see the RFC itself\nfor full legal notices.";
   revision "2018-02-14" {
     description
       "Initial revision.";
     reference
       "RFC 8342: Network Management Datastore Architecture (NMDA)";
   }
   identity datastore {
     description
       "Abstract base identity for datastore identities.";
   }
   identity conventional {
     base "datastore";
     description
       "Abstract base identity for conventional configuration\ndatastores.";
   }
   identity running {
     base "conventional";
     description
       "The running configuration datastore.";
   }
   identity candidate {
     base "conventional";
     description
       "The candidate configuration datastore.";
   }
   identity startup {
     base "conventional";
     description
       "The startup configuration datastore.";
   }
   identity intended {
     base "conventional";
     description
       "The intended configuration datastore.";
   }
   identity dynamic {
     base "datastore";
     description
       "Abstract base identity for dynamic configuration datastores.";
   }
   identity operational {
     base "datastore";
     description
       "The operational state datastore.";
   }
   typedef datastore-ref {
     type "identityref" {
       base "datastore";
     }
     description
       "A datastore identity reference.";
   }
 }

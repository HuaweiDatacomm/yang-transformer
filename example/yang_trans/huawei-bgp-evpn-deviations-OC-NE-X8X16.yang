/*
Copyright (C) 2019 Huawei Technologies Co., Ltd. All rights reserved.
*/

 module huawei-bgp-evpn-deviations-OC-NE-X8X16 {
   namespace "urn:huawei:yang:huawei-bgp-evpn-deviations-OC-NE-X8X16";
   prefix "bgp-evpn-devs-OC-NE-X8X16";
   import huawei-bgp {
     prefix "bgp";
   }
   import huawei-network-instance {
     prefix "ni";
   }
   import huawei-bgp-evpn {
     prefix "bgp-evpn";
   }
   organization
     "Huawei Technologies Co., Ltd.";
   contact
     "Huawei Industrial Base\nBantian, Longgang\nShenzhen 518129\nPeople's "+
     "Republic of China\nWebsite: http://www.huawei.com\nEmail: support@huawei.c"+
     "om";
   description
     "BGP EVPN configuration.";
   revision "2019-03-22" {
     description
       "Initial revision.";
     reference
       "Huawei private.";
   }
   typedef advertise-encap-type-deviations {
     type "enumeration" {
       enum "vxlan" {
         value "1";
         description
           "VXLAN.";
       }
       enum "mpls" {
         value "2";
         description
           "MPLS.";
       }
       enum "srv6" {
         value "4";
         description
           "SRv6.";
       }
     }
     description
       "Encapsulation type of packets.";
   }
   deviation "/ni:network-instance/ni:instances/ni:instance/bgp:bgp/bgp:base-pro"+
             "cess/bgp:peers/bgp:peer/bgp:afs/bgp:af/bgp-evpn:l2vpn-evpn/bgp-evp"+
             "n:advertise-encap-type" {
     deviate "replace" {
       type "bgp-evpn-devs-OC-NE-X8X16:advertise-encap-type-deviations";
     }
   }
   deviation "/ni:network-instance/ni:instances/ni:instance/bgp:bgp/bgp:base-pro"+
             "cess/bgp:peer-groups/bgp:peer-group/bgp:afs/bgp:af/bgp-evpn:l2vpn-"+
             "evpn/bgp-evpn:advertise-encap-type" {
     deviate "replace" {
       type "bgp-evpn-devs-OC-NE-X8X16:advertise-encap-type-deviations";
     }
   }
 }

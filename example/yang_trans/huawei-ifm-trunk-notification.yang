/*
Copyright (C) 2020 Huawei Technologies Co., Ltd. All rights reserved.
*/

 module huawei-ifm-trunk-notification {
   yang-version "1";
   namespace "urn:huawei:yang:huawei-ifm-trunk-notification";
   prefix "ifm-trunk-notification";
   import huawei-pub-type {
     prefix "pub-type";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of ifm-trunk.";
   revision "2020-08-12" {
     description
       "Initial revision.";
     reference
       "Huawei private.";
   }
   ext:task-name "trunk";
   notification all-member-down {
     description
       "The last member interface link status changes to down.";
     leaf trunk-index {
       type "uint32";
       mandatory "true";
       description
         "Trunk interface index.";
     }
     leaf trunk-name {
       type "pub-type:if-name";
       mandatory "true";
       description
         "Name of the Trunk interface.";
     }
   }
   notification all-member-down-resume {
     description
       "The first member interface link status changes to up.";
     leaf trunk-index {
       type "uint32";
       mandatory "true";
       description
         "Trunk interface index.";
     }
     leaf trunk-name {
       type "pub-type:if-name";
       mandatory "true";
       description
         "Name of the Trunk interface.";
     }
   }
   notification member-link-down {
     description
       "A trunk member interface went Down.";
     leaf port-index {
       type "uint32";
       mandatory "true";
       description
         "Index of a trunk member interface.";
     }
     leaf member-admin-status {
       type "uint32";
       mandatory "true";
       description
         "Administration status of a trunk member interface.";
     }
     leaf member-oper-status {
       type "uint32";
       mandatory "true";
       description
         "Operating status of a trunk member interface.";
     }
     leaf port-name {
       type "pub-type:if-name";
       mandatory "true";
       description
         "Name of a trunk member interface.";
     }
     leaf member-phy-status {
       type "uint32";
       mandatory "true";
       description
         "Physical status of a trunk member interface.";
     }
     leaf trunk-index {
       type "uint32";
       mandatory "true";
       description
         "Index of the trunk interface to which the member interface belongs.";
     }
     leaf trunk-name {
       type "pub-type:if-name";
       mandatory "true";
       description
         "Name of the trunk interface to which the member interface belongs.";
     }
   }
   notification member-link-up {
     description
       "A trunk member interface went Up.";
     leaf port-index {
       type "uint32";
       mandatory "true";
       description
         "Index of a trunk member interface.";
     }
     leaf member-admin-status {
       type "uint32";
       mandatory "true";
       description
         "Administration status of a trunk member interface.";
     }
     leaf member-oper-status {
       type "uint32";
       mandatory "true";
       description
         "Operating status of a trunk member interface.";
     }
     leaf port-name {
       type "pub-type:if-name";
       mandatory "true";
       description
         "Name of a trunk member interface.";
     }
     leaf member-phy-status {
       type "uint32";
       mandatory "true";
       description
         "Physical status of a trunk member interface.";
     }
     leaf trunk-index {
       type "uint32";
       description
         "Index of a trunk interface.";
     }
     leaf trunk-name {
       type "pub-type:if-name";
       mandatory "true";
       description
         "Name of the trunk interface to which the member interface belongs.";
     }
   }
   notification member-number-change {
     description
       "The number of active trunk member interfaces changed.";
     leaf trunk-name {
       type "pub-type:if-name";
       mandatory "true";
       description
         "Name of the trunk interface.";
     }
     leaf port-name {
       type "pub-type:if-name";
       mandatory "true";
       description
         "Name of the trunk member interface.";
     }
     leaf trunk-mem-number {
       type "uint32";
       mandatory "true";
       description
         "Number of active trunk member interfaces.";
     }
     leaf reason {
       type "string" {
         length "0..127";
       }
       mandatory "true";
       description
         "Reason.";
     }
   }
 }

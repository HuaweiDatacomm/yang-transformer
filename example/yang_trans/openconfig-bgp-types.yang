module openconfig-bgp-types {
   yang-version "1";
   namespace "http://openconfig.net/yang/bgp-types";
   prefix "oc-bgp-types";
   import openconfig-extensions {
     prefix "oc-ext";
   }
   include openconfig-bgp-errors;
   organization
     "OpenConfig working group";
   contact
     "OpenConfig working group\nnetopenconfig@googlegroups.com";
   description
     "This module contains general data definitions for use in BGP\npolicy. It "+
     "can be imported by modules that make use of BGP\nattributes";
   oc-ext:openconfig-version "5.0.2";
   revision "2018-11-21" {
     description
       "Add OpenConfig module metadata extensions.";
     reference
       "5.0.2";
   }
   revision "2018-08-20" {
     description
       "Correct description of AFI-SAFI enabled leaf.";
     reference
       "5.0.1";
   }
   revision "2018-04-11" {
     description
       "Correct naming of BGP maximum prefix warning percentage leaf.";
     reference
       "5.0.0";
   }
   revision "2018-03-20" {
     description
       "Added SR-TE policy SAFI";
     reference
       "4.1.0";
   }
   revision "2018-03-20" {
     description
       "Added color extended community";
     reference
       "4.0.2";
   }
   revision "2017-07-30" {
     description
       "Clarification of add-paths send-max leaf";
     reference
       "4.0.1";
   }
   revision "2017-07-10" {
     description
       "Add error notifications; moved add-paths config; add AS\nprepend policy "+
       "features; removed unneeded config leaves";
     reference
       "4.0.0";
   }
   revision "2017-02-02" {
     description
       "Bugfix to remove remaining global-level policy data";
     reference
       "3.0.1";
   }
   revision "2017-01-26" {
     description
       "Add dynamic neighbor support, migrate to OpenConfig types";
     reference
       "3.0.0";
   }
   revision "2016-06-21" {
     description
       "OpenConfig BGP refactor";
     reference
       "2.1.1";
   }
   oc-ext:regexp-posix;
   oc-ext:catalog-organization "openconfig";
   oc-ext:origin "openconfig";
   identity BGP_CAPABILITY {
     description
       "Base identity for a BGP capability";
   }
   identity MPBGP {
     base "BGP_CAPABILITY";
     description
       "Multi-protocol extensions to BGP";
     reference
       "RFC2858";
   }
   identity ROUTE_REFRESH {
     base "BGP_CAPABILITY";
     description
       "The BGP route-refresh functionality";
     reference
       "RFC2918";
   }
   identity ASN32 {
     base "BGP_CAPABILITY";
     description
       "4-byte (32-bit) AS number functionality";
     reference
       "RFC6793";
   }
   identity GRACEFUL_RESTART {
     base "BGP_CAPABILITY";
     description
       "Graceful restart functionality";
     reference
       "RFC4724";
   }
   identity ADD_PATHS {
     base "BGP_CAPABILITY";
     description
       "BGP add-paths";
     reference
       "draft-ietf-idr-add-paths";
   }
   identity AFI_SAFI_TYPE {
     description
       "Base identity type for AFI,SAFI tuples for BGP-4";
     reference
       "RFC4760 - multiprotocol extensions for BGP-4";
   }
   identity IPV4_UNICAST {
     base "AFI_SAFI_TYPE";
     description
       "IPv4 unicast (AFI,SAFI = 1,1)";
     reference
       "RFC4760";
   }
   identity IPV6_UNICAST {
     base "AFI_SAFI_TYPE";
     description
       "IPv6 unicast (AFI,SAFI = 2,1)";
     reference
       "RFC4760";
   }
   identity IPV4_LABELED_UNICAST {
     base "AFI_SAFI_TYPE";
     description
       "Labeled IPv4 unicast (AFI,SAFI = 1,4)";
     reference
       "RFC3107";
   }
   identity IPV6_LABELED_UNICAST {
     base "AFI_SAFI_TYPE";
     description
       "Labeled IPv6 unicast (AFI,SAFI = 2,4)";
     reference
       "RFC3107";
   }
   identity L3VPN_IPV4_UNICAST {
     base "AFI_SAFI_TYPE";
     description
       "Unicast IPv4 MPLS L3VPN (AFI,SAFI = 1,128)";
     reference
       "RFC4364";
   }
   identity L3VPN_IPV6_UNICAST {
     base "AFI_SAFI_TYPE";
     description
       "Unicast IPv6 MPLS L3VPN (AFI,SAFI = 2,128)";
     reference
       "RFC4659";
   }
   identity L3VPN_IPV4_MULTICAST {
     base "AFI_SAFI_TYPE";
     description
       "Multicast IPv4 MPLS L3VPN (AFI,SAFI = 1,129)";
     reference
       "RFC6514";
   }
   identity L3VPN_IPV6_MULTICAST {
     base "AFI_SAFI_TYPE";
     description
       "Multicast IPv6 MPLS L3VPN (AFI,SAFI = 2,129)";
     reference
       "RFC6514";
   }
   identity L2VPN_VPLS {
     base "AFI_SAFI_TYPE";
     description
       "BGP-signalled VPLS (AFI,SAFI = 25,65)";
     reference
       "RFC4761";
   }
   identity L2VPN_EVPN {
     base "AFI_SAFI_TYPE";
     description
       "BGP MPLS Based Ethernet VPN (AFI,SAFI = 25,70)";
   }
   identity SRTE_POLICY_IPV4 {
     base "AFI_SAFI_TYPE";
     description
       "Segment Routing Traffic Engineering (SRTE) Policy\nfor IPv4 (AFI,SAFI = "+
       "1,73)";
   }
   identity SRTE_POLICY_IPV6 {
     base "AFI_SAFI_TYPE";
     description
       "Segment Routing Traffic Engineering (SRTE) Policy\nfor IPv6 (AFI,SAFI = "+
       "2,73)";
   }
   identity BGP_WELL_KNOWN_STD_COMMUNITY {
     description
       "Reserved communities within the standard community space\ndefined by "+
       "RFC1997. These communities must fall within the\nrange 0x00000000 to "+
       "0xFFFFFFFF";
     reference
       "RFC1997";
   }
   identity NO_EXPORT {
     base "BGP_WELL_KNOWN_STD_COMMUNITY";
     description
       "Do not export NLRI received carrying this community outside\nthe bounds "+
       "of this autonomous system, or this confederation if\nthe local "+
       "autonomous system is a confederation member AS. This\ncommunity has a "+
       "value of 0xFFFFFF01.";
     reference
       "RFC1997";
   }
   identity NO_ADVERTISE {
     base "BGP_WELL_KNOWN_STD_COMMUNITY";
     description
       "All NLRI received carrying this community must not be\nadvertised to "+
       "other BGP peers. This community has a value of\n0xFFFFFF02.";
     reference
       "RFC1997";
   }
   identity NO_EXPORT_SUBCONFED {
     base "BGP_WELL_KNOWN_STD_COMMUNITY";
     description
       "All NLRI received carrying this community must not be\nadvertised to "+
       "external BGP peers - including over confederation\nsub-AS boundaries. "+
       "This community has a value of 0xFFFFFF03.";
     reference
       "RFC1997";
   }
   identity NOPEER {
     base "BGP_WELL_KNOWN_STD_COMMUNITY";
     description
       "An autonomous system receiving NLRI tagged with this community\nis "+
       "advised not to readvertise the NLRI to external bi-lateral\npeer "+
       "autonomous systems. An AS may also filter received NLRI\nfrom bilateral "+
       "peer sessions when they are tagged with this\ncommunity value";
     reference
       "RFC3765";
   }
   typedef peer-type {
     type "enumeration" {
       enum "INTERNAL" {
         description
           "Internal (iBGP) peer";
       }
       enum "EXTERNAL" {
         description
           "External (eBGP) peer";
       }
     }
     description
       "Labels a peer or peer group as explicitly internal or\nexternal";
   }
   identity REMOVE_PRIVATE_AS_OPTION {
     description
       "Base identity for options for removing private autonomous\nsystem "+
       "numbers from the AS_PATH attribute";
   }
   identity PRIVATE_AS_REMOVE_ALL {
     base "REMOVE_PRIVATE_AS_OPTION";
     description
       "Strip all private autonmous system numbers from the AS_PATH.\nThis "+
       "action is performed regardless of the other content of the\nAS_PATH "+
       "attribute, and for all instances of private AS numbers\nwithin that "+
       "attribute.";
   }
   identity PRIVATE_AS_REPLACE_ALL {
     base "REMOVE_PRIVATE_AS_OPTION";
     description
       "Replace all instances of private autonomous system numbers in\nthe "+
       "AS_PATH with the local BGP speaker's autonomous system\nnumber. This "+
       "action is performed regardless of the other\ncontent of the AS_PATH "+
       "attribute, and for all instances of\nprivate AS number within that "+
       "attribute.";
   }
 }

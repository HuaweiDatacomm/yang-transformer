/*
Copyright (C) 2019 Huawei Technologies Co., Ltd. All rights reserved.
*/

 module huawei-rip-deviations-OC-NE-X8X16 {
   namespace "urn:huawei:yang:huawei-rip-deviations-OC-NE-X8X16";
   prefix "rip-devs-OC-NE-X8X16";
   import huawei-rip {
     prefix "rip";
   }
   import huawei-network-instance {
     prefix "ni";
   }
   organization
     "Huawei Technologies Co., Ltd.";
   contact
     "Huawei Industrial Base\nBantian, Longgang\nShenzhen 518129\nPeople's "+
     "Republic of China\nWebsite: http://www.huawei.com\nEmail: support@huawei.c"+
     "om";
   description
     "RIP management.";
   revision "2019-04-04" {
     description
       "Initial revision.";
     reference
       "Huawei private.";
   }
   deviation "/ni:network-instance/ni:instances/ni:instance/rip:rip/rip:processs"+
             "/rip:process/rip:bfd/rip:min-rx" {
     deviate "replace" {
       type "uint32" {
         range "3..20000";
       }
     }
   }
   deviation "/ni:network-instance/ni:instances/ni:instance/rip:rip/rip:processs"+
             "/rip:process/rip:bfd/rip:min-tx" {
     deviate "replace" {
       type "uint32" {
         range "3..20000";
       }
     }
   }
   deviation "/ni:network-instance/ni:instances/ni:instance/rip:rip/rip:processs"+
             "/rip:process/rip:interfaces/rip:interface/rip:bfd/rip:min-rx" {
     deviate "replace" {
       type "uint32" {
         range "3..20000";
       }
     }
   }
   deviation "/ni:network-instance/ni:instances/ni:instance/rip:rip/rip:processs"+
             "/rip:process/rip:interfaces/rip:interface/rip:bfd/rip:min-tx" {
     deviate "replace" {
       type "uint32" {
         range "3..20000";
       }
     }
   }
 }

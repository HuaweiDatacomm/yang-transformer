module openconfig-pim-types {
   yang-version "1";
   namespace "http://openconfig.net/yang/pim/types";
   prefix "oc-pim-types";
   import openconfig-extensions {
     prefix "oc-ext";
   }
   organization
     "OpenConfig working group";
   contact
     "OpenConfig working group\nwww.openconfig.net";
   description
     "This module defines types related to the PIM protocol model.";
   oc-ext:openconfig-version "0.1.1";
   revision "2018-11-21" {
     description
       "Add OpenConfig module metadata extensions.";
     reference
       "0.1.1";
   }
   revision "2018-02-19" {
     description
       "Initial revision.";
     reference
       "0.1.0";
   }
   oc-ext:regexp-posix;
   oc-ext:catalog-organization "openconfig";
   oc-ext:origin "openconfig";
   identity PIM_MODE {
     description
       "Base identity for the operating modes of Protocol-Independent\nMulticast"+
       ".";
   }
   identity PIM_MODE_SPARSE {
     base "PIM_MODE";
     description
       "PIM sparse mode (PIM-SM).";
     reference
       "RFC7761";
   }
   identity PIM_MODE_DENSE {
     base "PIM_MODE";
     description
       "PIM dense mode (PIM-DM).";
     reference
       "RFC3973";
   }
 }

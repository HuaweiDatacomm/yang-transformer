/*
Copyright (C) 2021 Huawei Technologies Co., Ltd. All rights reserved.
*/

 module huawei-te-interface-deviations-OC-NE-X8X16 {
   namespace "urn:huawei:yang:huawei-te-interface-deviations-OC-NE-X8X16";
   prefix "te-interface-devs-OC-NE-X8X16";
   import huawei-network-instance {
     prefix "ni";
   }
   import huawei-ifm {
     prefix "ifm";
   }
   import huawei-te {
     prefix "te";
   }
   import huawei-te-interface {
     prefix "te-interface";
   }
   import huawei-tunnel-management {
     prefix "tnlm";
   }
   import huawei-gre {
     prefix "gre";
   }
   organization
     "Huawei Technologies Co., Ltd.";
   contact
     "Huawei Industrial Base\nBantian, Longgang\nShenzhen 518129\nPeople's "+
     "Republic of China\nWebsite: http://www.huawei.com\nEmail: support@huawei.c"+
     "om";
   description
     "Specifies the traffic engineering configuration.";
   revision "2021-02-10" {
     description
       "Init revision.";
     reference
       "Huawei private.";
   }
   deviation "/ni:network-instance/ni:instances/ni:instance/te:te/te-interface:i"+
             "nterfaces/te-interface:interface/te-interface:attribute/te-interfa"+
             "ce:bandwidth/te-interface:max-reserved" {
     deviate "add" {
       must "not(/ifm:ifm/ifm:interfaces/ifm:interface[ifm:name = current()/../."+
            "./../te-interface:name]/tnlm:tunnel-protocol/gre:gre-tunnel) or "+
            "(/ifm:ifm/ifm:interfaces/ifm:interface[ifm:name = current()/../../."+
            "./te-interface:name]/ifm:bandwidth and /ifm:ifm/ifm:interfaces/ifm:"+
            "interface[ifm:name = current()/../../../te-interface:name]/ifm:band"+
            "width*1000>=../max-reserved) or (/ifm:ifm/ifm:interfaces/ifm:interf"+
            "ace[ifm:name = current()/../../../te-interface:name]/ifm:bandwidth-"+
            "kbps and /ifm:ifm/ifm:interfaces/ifm:interface[ifm:name = "+
            "current()/../../../te-interface:name]/ifm:bandwidth-kbps>=../max-re"+
            "served) or (not(/ifm:ifm/ifm:interfaces/ifm:interface[ifm:name = "+
            "current()/../../../te-interface:name]/ifm:bandwidth) and not(/ifm:i"+
            "fm/ifm:interfaces/ifm:interface[ifm:name = current()/../../../te-in"+
            "terface:name]/ifm:bandwidth-kbps) and (65536>=../max-reserved*1000)"+
            ")";
     }
   }
   deviation "/ni:network-instance/ni:instances/ni:instance/te:te/te-interface:i"+
             "nterfaces/te-interface:interface/te-interface:attribute/te-interfa"+
             "ce:bandwidth/te-interface:dynamic-max-reserved-percent" {
     deviate "add" {
       must "not(/ifm:ifm/ifm:interfaces/ifm:interface[ifm:name = current()/../."+
            "./../te-interface:name]/tnlm:tunnel-protocol/gre:gre-tunnel) or "+
            "(../dynamic-max-reserved-percent>=1 and ../dynamic-max-reserved-per"+
            "cent<=100)";
     }
   }
   deviation "/ni:network-instance/ni:instances/ni:instance/te:te/te-interface:i"+
             "nterfaces/te-interface:interface" {
     deviate "add" {
       must "/ifm:ifm/ifm:interfaces/ifm:interface[ifm:name=current()/te-interfa"+
            "ce:name]/ifm:type!='Tunnel' or /ifm:ifm/ifm:interfaces/ifm:interfac"+
            "e[ifm:name=current()/te-interface:name]/tnlm:tunnel-protocol/gre:gr"+
            "e-tunnel";
     }
   }
 }

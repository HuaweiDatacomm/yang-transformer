/*
Copyright (C) 2019-2021 Huawei Technologies Co., Ltd. All rights reserved.
*/

 module huawei-trustem {
   namespace "urn:huawei:yang:huawei-trustem";
   prefix "trustem";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Indicate TPM (Trusted Platform Module) environment management.";
   revision "2021-05-08" {
     description
       "Fix description.";
     reference
       "Huawei private.";
   }
   revision "2021-02-23" {
     description
       "Add trust-startup-softwares.";
     reference
       "Huawei private.";
   }
   revision "2020-04-02" {
     description
       "YANG check.";
     reference
       "Huawei private.";
   }
   revision "2019-05-27" {
     description
       "Initial revision.";
     reference
       "Huawei private.";
   }
   ext:task-name "tpm";
   typedef status-type {
     type "enumeration" {
       enum "active" {
         value "1";
         description
           "Status active.";
       }
     }
     description
       "TPM status.";
   }
   container trustem {
     config "false";
     description
       "Indicate trust environment management.";
     container statuss {
       description
         "List of operational state of TPM status information.";
       list status {
         key "slot-id";
         description
           "Operational state of TPM status information.";
         leaf slot-id {
           type "string" {
             length "1..32";
           }
           description
             "Slot ID of a board.";
         }
         leaf version {
           type "string" {
             length "1..127";
           }
           description
             "TPM version.";
         }
         leaf manufacturer {
           type "string" {
             length "1..127";
           }
           description
             "TPM manufacturer.";
         }
         leaf status {
           type "status-type";
           description
             "TPM status.";
         }
       }
     }
     container trust-startup-softwares {
       config "false";
       description
         "List of software files information measured by TPM.";
       list trust-startup-software {
         key "name version file";
         description
           "Operational data of software file information measured by TPM.";
         leaf name {
           type "string" {
             length "1..63";
           }
           description
             "Software file description information.";
         }
         leaf version {
           type "string" {
             length "1..63";
           }
           description
             "Software file version.";
         }
         leaf file {
           type "string" {
             length "1..255";
           }
           description
             "Software file name on device.";
         }
         leaf checksum {
           type "string" {
             length "1..127";
           }
           description
             "Hash value of the file.";
         }
       }
     }
   }
 }

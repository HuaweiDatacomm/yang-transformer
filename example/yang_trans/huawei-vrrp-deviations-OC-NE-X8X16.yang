/*
Copyright (C) 2020 Huawei Technologies Co., Ltd. All rights reserved.
*/

 module huawei-vrrp-deviations-OC-NE-X8X16 {
   yang-version "1";
   namespace "urn:huawei:yang:huawei-vrrp-deviations-OC-NE-X8X16";
   prefix "vrrp-devs-OC-NE-X8X16";
   import huawei-vrrp {
     prefix "vrrp";
   }
   import huawei-ifm {
     prefix "ifm";
   }
   import huawei-ip {
     prefix "ip";
   }
   import huawei-efm {
     prefix "efm";
   }
   organization
     "Huawei Technologies Co., Ltd.";
   contact
     "Huawei Industrial Base\nBantian, Longgang\nShenzhen 518129\nPeople's "+
     "Republic of China\nWebsite: http://www.huawei.com\nEmail: support@huawei.c"+
     "om";
   description
     "Global VRRP configuration.";
   revision "2020-03-19" {
     description
       "Initial revision.";
     reference
       "Huawei private.";
   }
   deviation "/ifm:ifm/ifm:interfaces/ifm:interface/ip:ipv6/vrrp:vrrp6/vrrp:grou"+
             "p6s/vrrp:group6/vrrp:adver-interval" {
     deviate "add" {
       must "((../adver-interval)=100 or (../adver-interval)=200 or (../adver-in"+
            "terval)=500 or ((../adver-interval)>=1000 and (../adver-interval) "+
            "mod 10 = 0))";
     }
   }
   deviation "/ifm:ifm/ifm:interfaces/ifm:interface/ip:ipv4/vrrp:vrrp/vrrp:group"+
             "s/vrrp:group/vrrp:adver-interval" {
     deviate "add" {
       must "((../adver-interval)=100 or (../adver-interval)=200 or (../adver-in"+
            "terval)=500 or ((../adver-interval)>=1000 and (../adver-interval) "+
            "mod 1000 = 0))";
     }
   }
   deviation "/ifm:ifm/ifm:interfaces/ifm:interface/ip:ipv6/vrrp:vrrp6/vrrp:grou"+
             "p6s/vrrp:group6/vrrp:adver-interval" {
     deviate "replace" {
       type "uint32" {
         range "100..40950";
       }
     }
   }
   deviation "/ifm:ifm/ifm:interfaces/ifm:interface/ip:ipv6/vrrp:vrrp6/vrrp:grou"+
             "p6s/vrrp:group6" {
     deviate "add" {
       must "((count(track-bfds/track-bfd[bfd-type='normal'])<=8) and (count(tra"+
            "ck-bfds/track-bfd[bfd-type='link'])<=8) and (count(track-bfds/track"+
            "-bfd[bfd-type='peer'])<=1)) or not(track-bfds/track-bfd)";
     }
   }
   deviation "/ifm:ifm/ifm:interfaces/ifm:interface/ip:ipv6/vrrp:vrrp6/vrrp:grou"+
             "p6s/vrrp:group6/vrrp:preempt/vrrp:delay-time" {
     deviate "replace" {
       type "uint16" {
         range "0..10800";
       }
     }
   }
   deviation "/ifm:ifm/ifm:interfaces/ifm:interface/ip:ipv4/vrrp:vrrp/vrrp:group"+
             "s/vrrp:group/vrrp:track-3ahs/vrrp:track-3ah" {
     deviate "replace" {
       max-elements "1";
     }
   }
   deviation "/ifm:ifm/ifm:interfaces/ifm:interface/ip:ipv4/vrrp:vrrp/vrrp:group"+
             "s/vrrp:group/vrrp:track-3ahs/vrrp:track-3ah/vrrp:track-if-name" {
     deviate "add" {
       must "/ifm:ifm/ifm:interfaces/ifm:interface[ifm:name=current()]/efm:efm/e"+
            "fm:session/efm:state='enable'";
     }
   }
 }

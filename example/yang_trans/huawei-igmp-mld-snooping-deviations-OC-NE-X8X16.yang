/*
Copyright (C) 2019 Huawei Technologies Co., Ltd. All rights reserved.
*/

 module huawei-igmp-mld-snooping-deviations-OC-NE-X8X16 {
   yang-version "1";
   namespace "urn:huawei:yang:huawei-igmp-mld-snooping-deviations-OC-NE-X8X16";
   prefix "igmp-mld-snooping-devs-OC-NE-X8X16";
   import huawei-igmp-mld-snooping {
     prefix "ims";
   }
   import huawei-ifm {
     prefix "ifm";
   }
   import huawei-ethernet {
     prefix "ethernet";
   }
   import huawei-l2vpn {
     prefix "l2vpn";
   }
   organization
     "Huawei Technologies Co., Ltd.";
   contact
     "Huawei Industrial Base\nBantian, Longgang\nShenzhen 518129\nPeople's "+
     "Republic of China\nWebsite: http://www.huawei.com\nEmail: support@huawei.c"+
     "om";
   description
     "IGMP snooping.";
   revision "2019-03-30" {
     description
       "Init revision.";
     reference
       "Huawei private.";
   }
   deviation "/ifm:ifm/ifm:interfaces/ifm:interface/ims:igmp-snooping" {
     deviate "add" {
       must "not(ims:learning-disable-vlans or ims:static-router-port-vlans or "+
            "ims:limit-max-entry or ims:except-acl) or ../ethernet:ethernet/ethe"+
            "rnet:main-interface/ethernet:l2-attribute";
     }
   }
   deviation "/ifm:ifm/ifm:interfaces/ifm:interface/ims:mld-snooping" {
     deviate "add" {
       must "not(ims:learning-disable-vlans or ims:static-router-port-vlans) or "+
            "../ethernet:ethernet/ethernet:main-interface/ethernet:l2-attribute";
     }
   }
   deviation "/l2vpn:l2vpn/l2vpn:instances/l2vpn:instance/l2vpn:vpls/l2vpn:acs/l"+
             "2vpn:ac/ims:igmp-snooping/ims:limit-max-entry/ims:config-entry" {
     deviate "add" {
       must "not(/ifm:ifm/ifm:interfaces/ifm:interface[ifm:name=current()/../../"+
            "../l2vpn:interface-name]/ethernet:ethernet/ethernet:l3-sub-interfac"+
            "e/ethernet:dot1q-termination)";
       must "not(/ifm:ifm/ifm:interfaces/ifm:interface[ifm:name=current()/../../"+
            "../l2vpn:interface-name]/ethernet:ethernet/ethernet:l3-sub-interfac"+
            "e/ethernet:qinq-termination)";
       must "not(/ifm:ifm/ifm:interfaces/ifm:interface[ifm:name=current()/../../"+
            "../l2vpn:interface-name]/ethernet:ethernet/ethernet:l3-sub-interfac"+
            "e/ethernet:qinq-stacking)";
     }
   }
 }

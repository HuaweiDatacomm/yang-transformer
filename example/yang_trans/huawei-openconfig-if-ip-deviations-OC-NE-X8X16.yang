/*
Copyright (C) 2019 Huawei Technologies Co., Ltd. All rights reserved.
*/

 module huawei-openconfig-if-ip-deviations-OC-NE-X8X16 {
   yang-version "1";
   namespace "urn:huawei:yang:huawei-openconfig-if-ip-deviations-OC-NE-X8X16";
   prefix "of-if-ip-devs-OC-NE-X8X16";
   import openconfig-interfaces {
     prefix "oc-if";
   }
   import openconfig-if-ip {
     prefix "oc-ip";
   }
   organization
     "Huawei Technologies Co., Ltd.";
   contact
     "Huawei Industrial Base\nBantian, Longgang\nShenzhen 518129\nPeople's "+
     "Republic of China\nWebsite: http://www.huawei.com\nEmail: support@huawei.c"+
     "om";
   description
     "Openconfig IP (IPv4 and IPv6) interfaces management.";
   revision "2019-03-01" {
     description
       "Initial revision.";
     reference
       "Huawei private.";
   }
   deviation "/oc-if:interfaces/oc-if:interface/oc-if:subinterfaces/oc-if:subint"+
             "erface/oc-ip:ipv4/oc-ip:config/oc-ip:enabled" {
     deviate "add" {
       must "../enabled='true'";
     }
   }
   deviation "/oc-if:interfaces/oc-if:interface/oc-if:subinterfaces/oc-if:subint"+
             "erface/oc-ip:ipv4/oc-ip:addresses/oc-ip:address/oc-ip:config/oc-ip"+
             ":prefix-length" {
     deviate "add" {
       mandatory "true";
     }
   }
   deviation "/oc-if:interfaces/oc-if:interface/oc-if:subinterfaces/oc-if:subint"+
             "erface/oc-ip:ipv4/oc-ip:config/oc-ip:mtu" {
     deviate "replace" {
       type "uint16" {
         range "46..9600";
       }
     }
   }
   deviation "/oc-if:interfaces/oc-if:interface/oc-if:subinterfaces/oc-if:subint"+
             "erface/oc-ip:ipv4/oc-ip:state/oc-ip:mtu" {
     deviate "replace" {
       type "uint16" {
         range "46..9600";
       }
     }
   }
 }

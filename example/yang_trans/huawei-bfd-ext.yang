/*
Copyright (C) 2019 Huawei Technologies Co., Ltd. All rights reserved.
*/

 module huawei-bfd-ext {
   yang-version "1";
   namespace "urn:huawei:yang:huawei-bfd-ext";
   prefix "bfd-ext";
   import huawei-bfd {
     prefix "bfd";
   }
   import huawei-ifm {
     prefix "ifm";
   }
   import huawei-ifm-trunk {
     prefix "ifm-trunk";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Extended BFD functions.";
   revision "2019-10-27" {
     description
       "Initial revision.";
     reference
       "Huawei private.";
   }
   ext:task-name "bfd";
   augment "/ifm:ifm/ifm:interfaces/ifm:interface" {
     description
       "Configure BFD on the interface.";
     container bfd-ext {
       description
         "Configure extended BFD functions based on interfaces.";
       leaf transparent-tx-flag {
         type "empty";
         must "(not(/bfd:bfd/bfd:sessions/bfd:session[bfd:out-if-name-multicast-"+
              "ipv4 = current()/../../ifm:name])) and (not(/ifm:ifm/ifm:interfac"+
              "es/ifm:interface/ifm-trunk:trunk/ifm-trunk:members/ifm-trunk:memb"+
              "er[ifm-trunk:name = current()/../../ifm:name]))";
         description
           "The flag of default BFD transparent transmission.";
       }
     }
   }
 }

/*
Copyright (C) 2019 Huawei Technologies Co., Ltd. All rights reserved.
*/

 module huawei-openconfig-mpls-types-ext {
   namespace "urn:huawei:yang:huawei-openconfig-mpls-types-ext";
   prefix "hw-oc-mplst-ext";
   import openconfig-mpls-types {
     prefix "oc-mplst";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om\n     ";
   description
     "GRPC.";
   revision "2019-03-01" {
     description
       "Initial revision.";
     reference
       "Huawei private.";
   }
   ext:task-name "mpls-base";
   identity NONNULL {
     base "oc-mplst:NULL_LABEL_TYPE";
     description
       "Non-null label is used.";
   }
 }

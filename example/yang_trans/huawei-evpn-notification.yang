/*
Copyright (C) 2019 Huawei Technologies Co., Ltd. All rights reserved.
*/

 module huawei-evpn-notification {
   yang-version "1";
   namespace "urn:huawei:yang:huawei-evpn-notification";
   prefix "evpn-notification";
   import ietf-inet-types {
     prefix "inet";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of EVPN.";
   revision "2019-11-21" {
     description
       "Init revision.";
     reference
       "Huawei private.";
   }
   ext:task-name "evpnbgp";
   notification evpn-etree-mul-err {
     description
       "In an EVPN E-Tree scenario where a CE is dual-homed to PEs, the leaf "+
       "attributes of the PEs' AC interfaces bound to the EVPN instance were "+
       "different, causing a traffic loop.";
     leaf evpn-instance-name {
       type "string" {
         length "1..31";
       }
       description
         "EVPN instance name.";
     }
     leaf interface-name {
       type "string" {
         length "1..63";
       }
       description
         "Interface name.";
     }
   }
   notification evpn-srv6-modify-arg {
     description
       "The minimum length of the ARG is changed, split horizon function may "+
       "fail temporarily.";
     leaf last-arg-len {
       type "uint32";
       description
         "Last ARG length.";
     }
     leaf current-arg-len {
       type "uint32";
       description
         "Current ARG length.";
     }
   }
   notification evpn-discard-route {
     description
       "The EVPN instance discards the newly learned MAC and MAC/IP routes.";
     leaf route-type {
       type "string" {
         length "1..11";
       }
       description
         "The MAC or MAC/IP route type.";
     }
   }
   notification evpn-ringid-conflict-alm {
     description
       "The number of peers with the same ring-id exceeded the limit.";
     leaf ring-id {
       type "uint32";
       description
         "Ring ID configured for the ring network.";
     }
     leaf router-id {
       type "inet:ipv4-address-no-zone";
       description
         "Router ID of the device on which a ring ID is configured.";
     }
   }
   notification evpn-ringid-conflict-alm-clear {
     description
       "The number of peers with the same ring-id unexceeded the limit.";
     leaf ring-id {
       type "uint32";
       description
         "Ring ID configured for the ring network.";
     }
     leaf router-id {
       type "inet:ipv4-address-no-zone";
       description
         "Router ID of the device on which a ring ID is configured.";
     }
   }
 }

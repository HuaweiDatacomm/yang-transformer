/*
Copyright (C) 2021 Huawei Technologies Co., Ltd. All rights reserved.
*/

 module huawei-netconf-client-notif-deviations-OC-NE-X8X16 {
   yang-version "1";
   namespace "urn:huawei:yang:huawei-netconf-client-notif-deviations-OC-NE-X8X16"+
             "";
   prefix "netconf-client-notif-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Notification of netconf-client-notif-deviations-ne40e.";
   revision "2021-04-02" {
     description
       "Initial revision.";
     reference
       "Huawei private.";
   }
 }

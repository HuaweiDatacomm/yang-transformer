/*
Copyright (C) 2020 Huawei Technologies Co., Ltd. All rights reserved.
*/

 module huawei-port-group-deviations-OC-NE-X8X16 {
   namespace "urn:huawei:yang:huawei-port-group-deviations-OC-NE-X8X16";
   prefix "port-group-devs-OC-NE-X8X16";
   import huawei-ifm {
     prefix "ifm";
   }
   import huawei-port-group {
     prefix "port-group";
   }
   organization
     "Huawei Technologies Co., Ltd.";
   contact
     "Huawei Industrial Base\nBantian, Longgang\nShenzhen 518129\nPeople's "+
     "Republic of China\nWebsite: http://www.huawei.com\nEmail: support@huawei.c"+
     "om";
   description
     "Permanent port group information.";
   revision "2020-03-26" {
     description
       "Initial revision.";
     reference
       "Huawei private.";
   }
   deviation "/port-group:port-group/port-group:groups/port-group:group/port-gro"+
             "up:members/port-group:member/port-group:if-name" {
     deviate "add" {
       must "/ifm:ifm/ifm:interfaces/ifm:interface[ifm:name=current()]/ifm:type="+
            "'Ethernet' or /ifm:ifm/ifm:interfaces/ifm:interface[ifm:name=curren"+
            "t()]/ifm:type='GigabitEthernet' or /ifm:ifm/ifm:interfaces/ifm:inte"+
            "rface[ifm:name=current()]/ifm:type='100GE' or /ifm:ifm/ifm:interfac"+
            "es/ifm:interface[ifm:name=current()]/ifm:type='200GE' or /ifm:ifm/i"+
            "fm:interfaces/ifm:interface[ifm:name=current()]/ifm:type='40GE' or "+
            "/ifm:ifm/ifm:interfaces/ifm:interface[ifm:name=current()]/ifm:type="+
            "'10GE' or /ifm:ifm/ifm:interfaces/ifm:interface[ifm:name=current()]"+
            "/ifm:type='4x10GE' or /ifm:ifm/ifm:interfaces/ifm:interface[ifm:nam"+
            "e=current()]/ifm:type='10x10GE' or /ifm:ifm/ifm:interfaces/ifm:inte"+
            "rface[ifm:name=current()]/ifm:type='3x40GE' or /ifm:ifm/ifm:interfa"+
            "ces/ifm:interface[ifm:name=current()]/ifm:type='4x25GE' or "+
            "/ifm:ifm/ifm:interfaces/ifm:interface[ifm:name=current()]/ifm:type="+
            "'25GE' or /ifm:ifm/ifm:interfaces/ifm:interface[ifm:name=current()]"+
            "/ifm:type='XGigabitEthernet' or /ifm:ifm/ifm:interfaces/ifm:interfa"+
            "ce[ifm:name=current()]/ifm:type='GEBrief' or /ifm:ifm/ifm:interface"+
            "s/ifm:interface[ifm:name=current()]/ifm:type='FlexE' or /ifm:ifm/if"+
            "m:interfaces/ifm:interface[ifm:name=current()]/ifm:type='400GE' or "+
            "/ifm:ifm/ifm:interfaces/ifm:interface[ifm:name=current()]/ifm:type="+
            "'50GE' or /ifm:ifm/ifm:interfaces/ifm:interface[ifm:name=current()]"+
            "/ifm:type='50|100GE' or /ifm:ifm/ifm:interfaces/ifm:interface[ifm:n"+
            "ame=current()]/ifm:type='FlexE-200GE' or /ifm:ifm/ifm:interfaces/if"+
            "m:interface[ifm:name=current()]/ifm:type='FlexE-50G' or /ifm:ifm/if"+
            "m:interfaces/ifm:interface[ifm:name=current()]/ifm:type='FlexE-100G"+
            "' or /ifm:ifm/ifm:interfaces/ifm:interface[ifm:name=current()]/ifm:"+
            "type='FlexE-50|100G' or /ifm:ifm/ifm:interfaces/ifm:interface[ifm:n"+
            "ame=current()]/ifm:type='HP-GE' or /ifm:ifm/ifm:interfaces/ifm:inte"+
            "rface[ifm:name=current()]/ifm:type='Pos' or /ifm:ifm/ifm:interfaces"+
            "/ifm:interface[ifm:name=current()]/ifm:type='FlexE-400G' or "+
            "/ifm:ifm/ifm:interfaces/ifm:interface[ifm:name=current()]/ifm:type="+
            "'FlexE-10G'";
     }
   }
 }

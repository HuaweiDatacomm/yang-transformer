module openconfig-policy-forwarding {
   yang-version "1";
   namespace "http://openconfig.net/yang/policy-forwarding";
   prefix "oc-pf";
   import openconfig-extensions {
     prefix "oc-ext";
   }
   include openconfig-pf-forwarding-policies;
   include openconfig-pf-path-groups;
   include openconfig-pf-interfaces;
   organization
     "OpenConfig working group";
   contact
     "OpenConfig working group\nwww.openconfig.net";
   description
     "This module defines configuration and operational state data\nrelating to "+
     "policy-based forwarding. Policy-based forwarding is\nutilised when a "+
     "system chooses how to forward packets (including\napplying data-plane "+
     "operations such as encapsulation or\ndecapsulation) based on policies "+
     "other than destination L2 or L3\nheader. Typically, systems may implement:"+
     "\n\n - IP policy-based routing, where routing may be done based on the\n  "+
     " source plus destination of an IP packet; information within the\n   L4 "+
     "header; or some combination of both.\n - Encapsulation or decapsulation "+
     "based on certain policy\n   information - for example, matching particular"+
     " IP destinations\n   and decapsulating GRE headers.\n - Class-based "+
     "selection of egress routes - such as class-based\n   selection of an "+
     "egress MPLS path.\n\nThe policies that are defined in this model are "+
     "applied to a\nparticular ingress context of a network element (e.g., "+
     "interface)\nand are defined to apply following other interface policy such"+
     " as\nQoS classification and access control lists.\n\nThis module "+
     "defines:\n\n - policy-forwarding\n|\n|--- policies\n|    |-- policy\n|    "+
     "    |-- [match criteria]    How packets are defined to\n|        |        "+
     "               match policy.\n|        |-- [forwarding-action] How packets"+
     " matching should\n|                                 be forwarded.\n|--- "+
     "interfaces\n|    |-- interfaces\n|        | -- apply-forwarding-policy  "+
     "Forwarding policy to\n|                                      used on the "+
     "interface.\n|--- path-selection-groups\n     |-- path-selection-group     "+
     "A group of forwarding resources\n                                  that "+
     "are grouped for purposes\n                                  of next-hop "+
     "selection.\n\nA forwarding-policy specifies the match criteria that it "+
     "intends\nto use to determine the packets that it reroutes - this "+
     "may\nconsist of a number of criteria, such as DSCP. The action of "+
     "the\npolicy results in a forwarding action being applied to matching\npack"+
     "ets. For example, decapsulating the packet from a GRE header.\nIn order to"+
     " enact the policy based on particular interfaces - the\nforwarding-policy "+
     "is applied to an interface via referencing it\nwithin an 'apply-forwarding"+
     "-policy' statement associated with an\ninterface.\n\nIn some cases (e.g., "+
     "Class-Based Tunnel Selection) the forwarding\naction does not resolve to a"+
     " single egress action, and rather\nnormal forwarding rules are to be "+
     "applied but considering a subset\nof forwarding resources. In these cases,"+
     " a path-selection-group\ncan be created, referencing the subset of "+
     "forwarding paths that\nshould be used for the egress selection. In the "+
     "case that a subset\nof MPLS LSPs are eligible for, say, DSCP 46 marked "+
     "packets, a\npath-selection-group is created, referencing the subset of "+
     "LSPs.\nThe forwarding action of the corresponding policy is set to\nPATH_G"+
     "ROUP and references the configured group of LSPs.";
   oc-ext:openconfig-version "0.2.1";
   revision "2018-11-21" {
     description
       "Add OpenConfig module metadata extensions.";
     reference
       "0.2.1";
   }
   revision "2017-06-21" {
     description
       "Amend policy forwarding model based on ACL changes.";
     reference
       "0.2.0";
   }
   revision "2017-02-28" {
     description
       "Initial public release of policy forwarding.";
     reference
       "0.1.0";
   }
   revision "2016-11-08" {
     description
       "Initial revision.";
     reference
       "0.0.1";
   }
   oc-ext:regexp-posix;
   oc-ext:catalog-organization "openconfig";
   oc-ext:origin "openconfig";
 }

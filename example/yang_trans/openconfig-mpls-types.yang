module openconfig-mpls-types {
   yang-version "1";
   namespace "http://openconfig.net/yang/mpls-types";
   prefix "oc-mplst";
   import openconfig-extensions {
     prefix "oc-ext";
   }
   organization
     "OpenConfig working group";
   contact
     "OpenConfig working group\nnetopenconfig@googlegroups.com";
   description
     "General types for MPLS / TE data model";
   oc-ext:openconfig-version "3.1.0";
   revision "2019-03-26" {
     description
       "Add Pseudowire encapsulation.";
     reference
       "3.1.0";
   }
   revision "2018-11-21" {
     description
       "Add OpenConfig module metadata extensions.";
     reference
       "3.0.1";
   }
   revision "2018-07-02" {
     description
       "Add new RSVP-TE statistics, remove associated-rsvp-session\nleaf. Remove"+
       " use of date-and-time.";
     reference
       "3.0.0";
   }
   revision "2018-06-16" {
     description
       "Included attributes for base LDP configuration.";
     reference
       "2.6.0";
   }
   revision "2018-06-13" {
     description
       "Add ttl-propagation to global MPLS config";
     reference
       "2.5.0";
   }
   revision "2018-06-05" {
     description
       "Fixed bugs in when statements on RSVP-TE attributes";
     reference
       "2.4.2";
   }
   revision "2017-08-24" {
     description
       "Minor formatting fixes.";
     reference
       "2.4.1";
   }
   revision "2017-06-21" {
     description
       "Add TC bits typedef.";
     reference
       "2.4.0";
   }
   revision "2017-03-22" {
     description
       "Add RSVP calculated-absolute-subscription-bw";
     reference
       "2.3.0";
   }
   revision "2017-01-26" {
     description
       "Add RSVP Tspec, clarify units for RSVP, remove unused LDP";
     reference
       "2.2.0";
   }
   revision "2016-12-15" {
     description
       "Add additional MPLS parameters";
     reference
       "2.1.0";
   }
   revision "2016-09-01" {
     description
       "Revisions based on implementation feedback";
     reference
       "2.0.0";
   }
   revision "2016-08-08" {
     description
       "Public release of MPLS models";
     reference
       "1.0.1";
   }
   identity PATH_COMPUTATION_METHOD {
     description
       "base identity for supported path computation\nmechanisms";
   }
   identity LOCALLY_COMPUTED {
     base "PATH_COMPUTATION_METHOD";
     description
       "indicates a constrained-path LSP in which the\npath is computed by the "+
       "local LER";
   }
   identity EXTERNALLY_QUERIED {
     base "PATH_COMPUTATION_METHOD";
     description
       "Constrained-path LSP in which the path is\nobtained by querying an "+
       "external source, such as a PCE server.\nIn the case that an LSP is "+
       "defined to be externally queried, it may\nalso have associated explicit "+
       "definitions (which are provided to the\nexternal source to aid "+
       "computation); and the path that is returned by\nthe external source is "+
       "not required to provide a wholly resolved\npath back to the originating "+
       "system - that is to say, some local\ncomputation may also be required";
   }
   identity EXPLICITLY_DEFINED {
     base "PATH_COMPUTATION_METHOD";
     description
       "constrained-path LSP in which the path is\nexplicitly specified as a "+
       "collection of strict or/and loose\nhops";
   }
   identity PATH_SETUP_PROTOCOL {
     description
       "base identity for supported MPLS signaling\nprotocols";
   }
   identity PATH_SETUP_RSVP {
     base "PATH_SETUP_PROTOCOL";
     description
       "RSVP-TE signaling protocol";
   }
   identity PATH_SETUP_SR {
     base "PATH_SETUP_PROTOCOL";
     description
       "Segment routing";
   }
   identity PATH_SETUP_LDP {
     base "PATH_SETUP_PROTOCOL";
     description
       "LDP - RFC 5036";
   }
   identity PROTECTION_TYPE {
     description
       "base identity for protection type";
   }
   identity UNPROTECTED {
     base "PROTECTION_TYPE";
     description
       "no protection is desired";
   }
   identity LINK_PROTECTION_REQUIRED {
     base "PROTECTION_TYPE";
     description
       "link protection is desired";
   }
   identity LINK_NODE_PROTECTION_REQUESTED {
     base "PROTECTION_TYPE";
     description
       "node and link protection are both desired";
   }
   identity LSP_ROLE {
     description
       "Base identity for describing the role of\nlabel switched path at the "+
       "current node";
   }
   identity INGRESS {
     base "LSP_ROLE";
     description
       "Label switched path is an ingress (headend)\nLSP";
   }
   identity EGRESS {
     base "LSP_ROLE";
     description
       "Label switched path is an egress (tailend)\nLSP";
   }
   identity TRANSIT {
     base "LSP_ROLE";
     description
       "Label switched path is a transit LSP";
   }
   identity TUNNEL_TYPE {
     description
       "Base identity from which specific tunnel types are\nderived.";
   }
   identity P2P {
     base "TUNNEL_TYPE";
     description
       "TE point-to-point tunnel type.";
   }
   identity P2MP {
     base "TUNNEL_TYPE";
     description
       "TE point-to-multipoint tunnel type.";
   }
   identity LSP_OPER_STATUS {
     description
       "Base identity for LSP operational status";
   }
   identity DOWN {
     base "LSP_OPER_STATUS";
     description
       "LSP is operationally down or out of service";
   }
   identity UP {
     base "LSP_OPER_STATUS";
     description
       "LSP is operationally active and available\nfor traffic.";
   }
   identity TUNNEL_ADMIN_STATUS {
     description
       "Base identity for tunnel administrative status";
   }
   identity ADMIN_DOWN {
     base "TUNNEL_ADMIN_STATUS";
     description
       "LSP is administratively down";
   }
   identity ADMIN_UP {
     base "TUNNEL_ADMIN_STATUS";
     description
       "LSP is administratively up";
   }
   identity NULL_LABEL_TYPE {
     description
       "Base identity from which specific null-label types are\nderived.";
   }
   identity EXPLICIT {
     base "NULL_LABEL_TYPE";
     description
       "Explicit null label is used.";
   }
   identity IMPLICIT {
     base "NULL_LABEL_TYPE";
     description
       "Implicit null label is used.";
   }
   identity LSP_METRIC_TYPE {
     description
       "Base identity for types of LSP metric specification";
   }
   identity LSP_METRIC_RELATIVE {
     base "LSP_METRIC_TYPE";
     description
       "The metric specified for the LSPs to which this identity refers\nis "+
       "specified as a relative value to the IGP metric cost to the\nLSP's "+
       "tail-end.";
   }
   identity LSP_METRIC_ABSOLUTE {
     base "LSP_METRIC_TYPE";
     description
       "The metric specified for the LSPs to which this identity refers\nis "+
       "specified as an absolute value";
   }
   identity LSP_METRIC_INHERITED {
     base "LSP_METRIC_TYPE";
     description
       "The metric for for the LSPs to which this identity refers is\nnot "+
       "specified explicitly - but rather inherited from the IGP\ncost directly";
   }
   identity PSEUDOWIRE_ENCAPSULATION {
     description
       "Sets the PDU type of the PSEUDOWIRE Example in RFC4448. This value\nshou"+
       "ld be enumerated from the IANA Pseudowire types registry";
   }
   identity PWE_ETHERNET_TAGGED_MODE {
     base "PSEUDOWIRE_ENCAPSULATION";
     description
       "Ethernet Tagged Mode RFC4448";
     reference
       "IANA PWE3 0x0004";
   }
   identity PWE_ETHERNET_RAW_MODE {
     base "PSEUDOWIRE_ENCAPSULATION";
     description
       "Ethernet Raw Mode RFC4448";
     reference
       "IANA PWE3 0x0005";
   }
 }

/*
Copyright (C) 2021 Huawei Technologies Co., Ltd. All rights reserved.
*/

 module huawei-cgn-deviations-OC-NE-X8X16 {
   namespace "urn:huawei:yang:huawei-cgn-deviations-OC-NE-X8X16";
   prefix "cgn-devs-OC-NE-X8X16";
   import huawei-cgn {
     prefix "cgn";
   }
   import huawei-license {
     prefix "lcs";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-cgn module.";
   revision "2021-09-15" {
     description
       "Initial revision.";
     reference
       "Huawei private.";
   }
   deviation "/lcs:license/cgn:active-nat-sessions/cgn:active-nat-session/cgn:en"+
             "gine" {
     deviate "add" {
       must "((../engine='NA') and (not(../card='NA'))) or ((not(../engine='NA')"+
            ") and (../card='NA'))";
     }
   }
   deviation "/lcs:license/cgn:active-nat-sessions/cgn:active-nat-session/cgn:ca"+
             "rd" {
     deviate "add" {
       must "((../engine='NA') and (not(../card='NA'))) or ((not(../engine='NA')"+
            ") and (../card='NA'))";
     }
   }
 }

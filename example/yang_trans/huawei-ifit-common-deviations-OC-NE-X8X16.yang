/*
Copyright (C) 2020 Huawei Technologies Co., Ltd. All rights reserved.
*/

 module huawei-ifit-common-deviations-OC-NE-X8X16 {
   namespace "urn:huawei:yang:huawei-ifit-common-deviations-OC-NE-X8X16";
   prefix "ifit-common-devs-OC-NE-X8X16";
   import huawei-ifit {
     prefix "ifit";
   }
   import huawei-ifit-common {
     prefix "ifit-common";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module contains a collection of YANG definitions IFIT feature.";
   revision "2020-04-02" {
     description
       "Initial revision.";
     reference
       "Huawei private.";
   }
   deviation "/ifit:ifit/ifit-common:ifit-common/ifit-common:whitelist-groups/if"+
             "it-common:whitelist-group/ifit-common:whitelist-rules/ifit-common:"+
             "whitelist-rule/ifit-common:address-type/ifit-common:ipv6-condition"+
             "/ifit-common:source-ipv6-mask" {
     deviate "replace" {
       type "uint8" {
         range "32..96";
       }
     }
   }
   deviation "/ifit:ifit/ifit-common:ifit-common/ifit-common:whitelist-groups/if"+
             "it-common:whitelist-group/ifit-common:whitelist-rules/ifit-common:"+
             "whitelist-rule/ifit-common:address-type/ifit-common:ipv6-condition"+
             "/ifit-common:destination-ipv6-mask" {
     deviate "replace" {
       type "uint8" {
         range "32..128";
       }
     }
   }
   ext:deviation-ext "/ifit:ifit/ifit-common:ifit-common/ifit-common:whitelist-g"+
                     "roups/ifit-common:whitelist-group/ifit-common:whitelist-ru"+
                     "les/ifit-common:whitelist-rule/ifit-common:address-type/if"+
                     "it-common:ipv6-condition/ifit-common:source-ipv6-mask" {
     ext:deviate-ext "replace" {
       ext:dynamic-default {
         ext:default-value "96" {
           when "../source-ipv6-address";
         }
       }
     }
   }
 }

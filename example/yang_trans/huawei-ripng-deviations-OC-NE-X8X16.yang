/*
Copyright (C) 2021 Huawei Technologies Co., Ltd. All rights reserved.
*/

 module huawei-ripng-deviations-OC-NE-X8X16 {
   namespace "urn:huawei:yang:huawei-ripng-deviations-OC-NE-X8X16";
   prefix "ripng-devs-OC-NE-X8X16";
   import huawei-ripng {
     prefix "ripng";
   }
   import huawei-ifm {
     prefix "ifm";
   }
   import huawei-if-ip {
     prefix "if-ip";
   }
   import huawei-ip {
     prefix "ip";
   }
   import huawei-network-instance {
     prefix "ni";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-ripng module.";
   revision "2021-05-07" {
     description
       "Initial revision.";
     reference
       "Huawei private.";
   }
   deviation "/ni:network-instance/ni:instances/ni:instance/ripng:ripng/ripng:pr"+
             "ocesss/ripng:process/ripng:interfaces/ripng:interface/ripng:name" {
     deviate "add" {
       must "../../../../../../ni:name=/ifm:ifm/ifm:interfaces/ifm:interface[ifm"+
            ":name=current()]/ifm:vrf-name and (/ifm:ifm/ifm:interfaces/ifm:inte"+
            "rface[ifm:name=current()]/ip:ipv6 or /ni:network-instance/ni:instan"+
            "ces/ni:instance/if-ip:ipv6-ifs/if-ip:ipv6-if[if-ip:name=current()])"+
            "";
     }
   }
 }

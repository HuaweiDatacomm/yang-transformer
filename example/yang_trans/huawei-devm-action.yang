/*
Copyright (C) 2019-2020 Huawei Technologies Co., Ltd. All rights reserved.
*/

 submodule huawei-devm-action {
   belongs-to huawei-devm {
     prefix "devm";
   }
   import huawei-pub-type {
     prefix "pub-type";
   }
   import huawei-extension {
     prefix "ext";
   }
   include huawei-devm-type;
   organization
     "Huawei Technologies Co., Ltd.";
   contact
     "Huawei Industrial Base\nBantian, Longgang\nShenzhen 518129\nPeople's "+
     "Republic of China\nWebsite: http://www.huawei.com\nEmail: support@huawei.c"+
     "om";
   description
     "The submodule of devm : devm_action.";
   revision "2020-08-07" {
     description
       "Add clear-active-hardware-alarm and clear-history-hardware-alarm.";
     reference
       "Huawei private.";
   }
   revision "2020-04-10" {
     description
       "Modify description warnings.";
     reference
       "Huawei private.";
   }
   revision "2019-09-09" {
     description
       "Change description.";
     reference
       "Huawei private.";
   }
   revision "2019-04-03" {
     description
       "Initial revision.";
     reference
       "Huawei private.";
   }
   rpc reset-board {
     description
       "Reset board.";
     input {
       leaf board-position {
         type "string" {
           length "1..32";
         }
         mandatory "true";
         description
           "Board position.";
       }
     }
   }
   rpc reset-mpu-board {
     description
       "Reset MPU.";
     ext:node-ref "/devm/mpu-boards/mpu-board";
     input {
       leaf board-position {
         type "string" {
           length "1..32";
         }
         mandatory "true";
         description
           "Board position.";
       }
     }
   }
   rpc reset-lpu-board {
     description
       "Reset LPU.";
     ext:node-ref "/devm/lpu-boards/lpu-board";
     input {
       leaf board-position {
         type "string" {
           length "1..32";
         }
         mandatory "true";
         description
           "Board position.";
       }
     }
   }
   rpc reset-sfu-board {
     description
       "Reset SFU.";
     ext:node-ref "/devm/sfu-boards/sfu-board";
     input {
       leaf board-position {
         type "string" {
           length "1..32";
         }
         mandatory "true";
         description
           "Board position.";
       }
     }
   }
   rpc reset-card {
     description
       "Reset Card.";
     ext:node-ref "/devm/cards/card";
     input {
       leaf card-position {
         type "string" {
           length "1..32";
         }
         mandatory "true";
         description
           "Card position.";
       }
     }
   }
   rpc reboot {
     description
       "Reboot.";
     input {
       leaf save-flag {
         type "boolean";
         default "true";
         description
           "Flag indicating whether to save the configuration. True: save; "+
           "False: not save.";
       }
     }
   }
   rpc clear-inactive-config {
     description
       "Clear Inactive Configuration.";
     input {
       leaf entity-class {
         type "offline-class-type";
         mandatory "true";
         description
           "Class.";
       }
       leaf position {
         type "string" {
           length "1..32";
         }
         mandatory "true";
         description
           "Position.";
       }
     }
   }
   rpc schedule-reboot-at-time {
     description
       "Schedule reboot at time.";
     input {
       leaf schedule-date {
         type "pub-type:date";
         mandatory "true";
         description
           "Date.";
       }
       leaf schedule-datetime {
         type "pub-type:time-hhmm";
         mandatory "true";
         description
           "Time.";
       }
       leaf save-flag {
         type "boolean";
         default "true";
         description
           "Flag indicating whether save config.";
       }
     }
   }
   rpc schedule-reboot-delay-time {
     description
       "Schedule reboot delay time.";
     input {
       leaf delay-time {
         type "string" {
           length "1..6";
         }
         mandatory "true";
         description
           "Delay time, total minutes or hours:minutes (mm or hh:mm), the max "+
           "value is 720 hours.";
       }
       leaf save-flag {
         type "boolean";
         default "true";
         description
           "Flag indicating whether save config.";
       }
     }
   }
   rpc undo-schedule-reboot {
     description
       "Undo Schedule reboot.";
   }
   rpc clear-active-hardware-alarm {
     description
       "Clear active hardware alarm.";
     input {
       choice clear-mode {
         default "all";
         description
           "The mode to clear alarm.";
         case all {
           description
             "Clear all alarm.";
           leaf all {
             type "empty";
             description
               "Clear all alarm.";
           }
         }
         case position {
           description
             "Clear alarm by hardware entity position.";
           leaf position {
             type "string" {
               length "1..32";
             }
             mandatory "true";
             description
               "Hardware entity position.";
           }
         }
         case sequence {
           description
             "Clear alarm by sequence.";
           leaf sequence {
             type "uint32" {
               range "1..4294967295";
             }
             mandatory "true";
             description
               "The sequence of all active alarm.";
           }
         }
       }
     }
   }
   rpc clear-history-hardware-alarm {
     description
       "Clear history hardware alarm.";
     input {
       choice clear-mode {
         default "all";
         description
           "The mode to clear alarm.";
         case all {
           description
             "Clear all alarm.";
           leaf all {
             type "empty";
             description
               "Clear all alarm.";
           }
         }
         case position {
           description
             "Clear alarm by hardware entity position.";
           leaf position {
             type "string" {
               length "1..32";
             }
             mandatory "true";
             description
               "Hardware entity position.";
           }
         }
       }
     }
   }
 }

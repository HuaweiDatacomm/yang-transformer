/*
Copyright (C) 2021 Huawei Technologies Co., Ltd. All rights reserved.
*/

 module huawei-snmp-deviations-OC-NE-X8X16 {
   namespace "urn:huawei:yang:huawei-snmp-deviations-OC-NE-X8X16";
   prefix "snmp-devs-OC-NE-X8X16";
   import huawei-snmp {
     prefix "snmp";
   }
   import huawei-aaa {
     prefix "aaa";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-snmp module.";
   revision "2021-05-07" {
     description
       "Initial revision.";
     reference
       "Huawei private.";
   }
   deviation "/snmp:snmp/snmp:local-users/snmp:local-user/snmp:name" {
     deviate "add" {
       must "/aaa:aaa/aaa:lam/aaa:users/aaa:user[aaa:name = current()]/aaa:servi"+
            "ce-snmp = 'true'";
     }
   }
 }

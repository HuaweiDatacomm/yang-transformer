/*
Copyright (C) 2020 Huawei Technologies Co., Ltd. All rights reserved.
*/

 module huawei-etrunk-deviations-OC-NE-X8X16 {
   yang-version "1";
   namespace "urn:huawei:yang:huawei-etrunk-deviations-OC-NE-X8X16";
   prefix "etrunk-devs-OC-NE-X8X16";
   import huawei-etrunk {
     prefix "etrunk";
   }
   organization
     "Huawei Technologies Co., Ltd.";
   contact
     "Huawei Industrial Base\nBantian, Longgang\nShenzhen 518129\nPeople's "+
     "Republic of China\nWebsite: http://www.huawei.com\nEmail: support@huawei.c"+
     "om";
   description
     "Enhanced Trunk (E-Trunk) is a mechanism that controls and implements link "+
     "aggregation among multiple devices. E-Trunk implements device-level not "+
     "board-level link reliability.";
   revision "2020-02-19" {
     description
       "Init revision.";
     reference
       "Huawei private.";
   }
   deviation "/etrunk:etrunk/etrunk:instances/etrunk:instance/etrunk:security-ke"+
             "y-type" {
     deviate "add" {
       must "../security-key and ../security-key-type";
     }
   }
   deviation "/etrunk:etrunk/etrunk:instances/etrunk:instance/etrunk:security-ke"+
             "y" {
     deviate "add" {
       must "../security-key and ../security-key-type";
     }
   }
   deviation "/etrunk:etrunk/etrunk:instances/etrunk:instance/etrunk:id" {
     deviate "replace" {
       type "uint16" {
         range "1..512";
       }
     }
   }
 }

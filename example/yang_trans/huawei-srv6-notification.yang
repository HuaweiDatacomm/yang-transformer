/*
Copyright (C) 2020 Huawei Technologies Co., Ltd. All rights reserved.
*/

 module huawei-srv6-notification {
   yang-version "1";
   namespace "urn:huawei:yang:huawei-srv6-notification";
   prefix "srv6-notification";
   import ietf-inet-types {
     prefix "inet";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Notification of segment routing IPv6.";
   revision "2020-03-03" {
     description
       "Init revision.";
     reference
       "Huawei private.";
   }
   ext:task-name "segr";
   notification local-sid-route-conflict {
     description
       "Conflict between an SRv6 local SID and a route.";
     leaf local-sid {
       type "inet:ipv6-address-no-zone";
       description
         "Local SID.";
     }
     leaf prefix-length {
       type "uint32";
       description
         "Mask length of local SID.";
     }
   }
   notification local-sid-route-conflict-resume {
     description
       "The conflict between the SRv6 local SID and route was removed.";
     leaf local-sid {
       type "inet:ipv6-address-no-zone";
       description
         "Local SID.";
     }
     leaf prefix-length {
       type "uint32";
       description
         "Mask length of local SID.";
     }
   }
 }

/*
Copyright (C) 2019 Huawei Technologies Co., Ltd. All rights reserved.
*/

 module huawei-srv6-deviations-OC-NE-X8X16 {
   namespace "urn:huawei:yang:huawei-srv6-deviations-OC-NE-X8X16";
   prefix "srv6-devs-OC-NE-X8X16";
   import huawei-network-instance {
     prefix "ni";
   }
   import huawei-srv6 {
     prefix "srv6";
   }
   organization
     "Huawei Technologies Co., Ltd.";
   contact
     "Huawei Industrial Base\nBantian, Longgang\nShenzhen 518129\nPeople's "+
     "Republic of China\nWebsite: http://www.huawei.com\nEmail: support@huawei.c"+
     "om";
   description
     "Common srv6 management, which includes the public configuration of srv6.";
   revision "2019-03-22" {
     description
       "Initial revision.";
     reference
       "Huawei private.";
   }
   typedef protocol-type-deviations {
     type "enumeration" {
       enum "evpn" {
         value "1";
         description
           "EVPN.";
       }
     }
     description
       "Protocol Type.";
   }
   deviation "/ni:network-instance/ni:instances/ni:instance/srv6:srv6/srv6:locat"+
             "ors/srv6:locator/srv6:opcodes/srv6:end-dx4s/srv6:end-dx4/srv6:prot"+
             "ocol" {
     deviate "replace" {
       type "srv6-devs-OC-NE-X8X16:protocol-type-deviations";
     }
   }
   deviation "/ni:network-instance/ni:instances/ni:instance/srv6:srv6/srv6:locat"+
             "ors/srv6:locator/srv6:opcodes/srv6:end-dx6s/srv6:end-dx6/srv6:prot"+
             "ocol" {
     deviate "replace" {
       type "srv6-devs-OC-NE-X8X16:protocol-type-deviations";
     }
   }
 }

/*
Copyright (C) 2020 Huawei Technologies Co., Ltd. All rights reserved.
*/

 module huawei-openconfig-network-instance-deviations-OC-NE-X8X16 {
   yang-version "1";
   namespace "urn:huawei:yang:huawei-openconfig-network-instance-deviations-OC-N"+
             "E-X8X16";
   prefix "oc-netinst-devs-OC-NE-X8X16";
   import openconfig-network-instance {
     prefix "oc-netinst";
   }
   import openconfig-network-instance-types {
     prefix "oc-ni-types";
   }
   import openconfig-types {
     prefix "oc-types";
   }
   import openconfig-policy-types {
     prefix "oc-pol-types";
   }
   import openconfig-bgp-types {
     prefix "oc-bgp-types";
   }
   import ietf-inet-types {
     prefix "inet";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "An OpenConfig description of a network-instance. This may be\na Layer 3 "+
     "forwarding construct such as a virtual routing and\nforwarding (VRF) "+
     "instance, or a Layer 2 instance such as a\nvirtual switch instance (VSI). "+
     "Mixed Layer 2 and Layer 3\ninstances are also supported.";
   revision "2020-10-23" {
     description
       "Initial revision.";
     reference
       "openconfig network instance.";
   }
   typedef route-distinguisher-deviations {
     type "union" {
       type "string" {
         pattern "(65[0-5][0-3][0-5]|[1-5][1-5][0-9][0-9][0-9]|[1-9]?[1-9]?[0-9]"+
                 "[0-9]|[1-9]):(4[0-2][0-9][0-4][0-9][0-6][0-7][0-2][0-9][0-5]|["+
                 "0-3][0-9]{9}|[1-9][0-9]{1,8}|[1-9])";
       }
       type "string" {
         pattern "(([0-9]|[1-9][0-9]|1[0-9][0-9]|2[0-4][0-9]|25[0-5])\\.){3}(["+
                 "0-9]|[1-9][0-9]|1[0-9][0-9]|2[0-4][0-9]|25[0-5]):(65[0-5][0-3]"+
                 "[0-5]|[1-5][1-5][0-9][0-9][0-9]|[1-9]?[1-9]?[0-9][0-9]|[1-9])";
       }
       type "string" {
         pattern "(4[0-2][0-9][0-4][0-9][0-6][0-7][0-2][0-9][0-5]|[0-3][0-9]{9}|"+
                 "[1-9][0-9]{1,8}|[1-9]):(65[0-5][0-3][0-5]|[1-5]{2}[0-9]{3}|[1-"+
                 "9]{0,2}[0-9][0-9]|[1-9])";
       }
     }
     description
       "A route distinguisher value";
     reference
       "RFC4364";
   }
   typedef ipv4-prefix-deviations {
     type "string" {
       pattern "(([0-9]|[1-9][0-9]|1[0-9][0-9]|2[0-4][0-9]|25[0-5])\\.){3}([0-"+
               "9]|[1-9][0-9]|1[0-9][0-9]|2[0-4][0-9]|25[0-5])/(([0-9])|([1-2][0"+
               "-9])|(3[0-2]))";
     }
     description
       "An IPv4 prefix represented in dotted quad notation followed by\na slash "+
       "and a CIDR mask (0 <= mask <= 32).";
   }
   typedef ipv6-prefix-deviations {
     type "string" {
       pattern "(([0-9a-fA-F]{1,4}:){7}[0-9a-fA-F]{1,4}|([0-9a-fA-F]{1,4}:){1,7}"+
               ":|([0-9a-fA-F]{1,4}:){1,6}:[0-9a-fA-F]{1,4}|([0-9a-fA-F]{1,4}:){"+
               "1,5}(:[0-9a-fA-F]{1,4}){1,2}|([0-9a-fA-F]{1,4}:){1,4}(:[0-9a-fA-"+
               "F]{1,4}){1,3}|([0-9a-fA-F]{1,4}:){1,3}(:[0-9a-fA-F]{1,4}){1,4}|("+
               "[0-9a-fA-F]{1,4}:){1,2}(:[0-9a-fA-F]{1,4}){1,5}|[0-9a-fA-F]{1,4}"+
               ":((:[0-9a-fA-F]{1,4}){1,6})|:((:[0-9a-fA-F]{1,4}){1,7}|:))/(12[0"+
               "-8]|1[0-1][0-9]|[1-9][0-9]|[0-9])";
     }
     description
       "An IPv6 prefix represented in full, shortened, or mixed\nshortened "+
       "format followed by a slash and CIDR mask\n(0 <= mask <= 128).";
   }
   typedef ip-prefix-deviations {
     type "union" {
       type "ipv4-prefix-deviations";
       type "ipv6-prefix-deviations";
     }
     description
       "An IPv4 or IPv6 prefix.";
   }
   typedef ipv4-address-deviations {
     type "string" {
       pattern "(([0-9]|[1-9][0-9]|1[0-9][0-9]|2[0-4][0-9]|25[0-5])\\.){3}([0-"+
               "9]|[1-9][0-9]|1[0-9][0-9]|2[0-4][0-9]|25[0-5])";
     }
     description
       "An IPv4 address in dotted quad notation using the default\nzone.";
   }
   typedef ipv6-address-deviations {
     type "string" {
       pattern "(([0-9a-fA-F]{1,4}:){7}[0-9a-fA-F]{1,4}|([0-9a-fA-F]{1,4}:){1,7}"+
               ":|([0-9a-fA-F]{1,4}:){1,6}:[0-9a-fA-F]{1,4}|([0-9a-fA-F]{1,4}:){"+
               "1,5}(:[0-9a-fA-F]{1,4}){1,2}|([0-9a-fA-F]{1,4}:){1,4}(:[0-9a-fA-"+
               "F]{1,4}){1,3}|([0-9a-fA-F]{1,4}:){1,3}(:[0-9a-fA-F]{1,4}){1,4}|("+
               "[0-9a-fA-F]{1,4}:){1,2}(:[0-9a-fA-F]{1,4}){1,5}|[0-9a-fA-F]{1,4}"+
               ":((:[0-9a-fA-F]{1,4}){1,6})|:((:[0-9a-fA-F]{1,4}){1,7}|:))";
     }
     description
       "An IPv6 address represented as either a full address; shortened\nor "+
       "mixed-shortened formats, using the default zone.";
   }
   typedef ip-address-deviations {
     type "union" {
       type "ipv4-address-deviations";
       type "ipv6-address-deviations";
     }
     description
       "An IPv4 or IPv6 address with no prefix specified.";
   }
   typedef bandwidth-kbps-deviations {
     type "uint64" {
       range "0..4000000000";
     }
     units "kbit/s";
     description
       "Bandwidth values expressed in kilobits per second.";
   }
   deviation "/oc-netinst:network-instances/oc-netinst:network-instance/oc-netin"+
             "st:mpls/oc-netinst:signaling-protocols/oc-netinst:ldp/oc-netinst:g"+
             "lobal/oc-netinst:config/oc-netinst:lsr-id" {
     deviate "replace" {
       type "oc-netinst-devs-OC-NE-X8X16:ip-address-deviations";
     }
   }
   deviation "/oc-netinst:network-instances/oc-netinst:network-instance/oc-netin"+
             "st:mpls/oc-netinst:signaling-protocols/oc-netinst:ldp/oc-netinst:t"+
             "argeted/oc-netinst:address-families/oc-netinst:address-family/oc-n"+
             "etinst:targets/oc-netinst:target/oc-netinst:config/oc-netinst:remo"+
             "te-address" {
     deviate "replace" {
       type "oc-netinst-devs-OC-NE-X8X16:ip-address-deviations";
     }
   }
   deviation "/oc-netinst:network-instances/oc-netinst:network-instance/oc-netin"+
             "st:mpls/oc-netinst:signaling-protocols/oc-netinst:ldp/oc-netinst:t"+
             "argeted/oc-netinst:address-families/oc-netinst:address-family/oc-n"+
             "etinst:targets/oc-netinst:target/oc-netinst:config/oc-netinst:loca"+
             "l-address" {
     deviate "replace" {
       type "oc-netinst-devs-OC-NE-X8X16:ip-address-deviations";
     }
   }
   deviation "/oc-netinst:network-instances/oc-netinst:network-instance/oc-netin"+
             "st:mpls/oc-netinst:signaling-protocols/oc-netinst:ldp/oc-netinst:t"+
             "argeted/oc-netinst:address-families/oc-netinst:address-family/oc-n"+
             "etinst:targets/oc-netinst:target/oc-netinst:config/oc-netinst:enab"+
             "led" {
     deviate "delete" {
       default "false";
     }
     deviate "add" {
       must "../enabled='true'";
       mandatory "true";
     }
   }
   deviation "/oc-netinst:network-instances/oc-netinst:network-instance/oc-netin"+
             "st:mpls/oc-netinst:lsps/oc-netinst:constrained-path/oc-netinst:tun"+
             "nels/oc-netinst:tunnel/oc-netinst:p2p-tunnel-attributes/oc-netinst"+
             ":config/oc-netinst:destination" {
     deviate "replace" {
       type "oc-netinst-devs-OC-NE-X8X16:ipv4-address-deviations";
     }
   }
   deviation "/oc-netinst:network-instances/oc-netinst:network-instance/oc-netin"+
             "st:mpls/oc-netinst:lsps/oc-netinst:constrained-path/oc-netinst:tun"+
             "nels/oc-netinst:tunnel/oc-netinst:config/oc-netinst:source" {
     deviate "replace" {
       type "oc-netinst-devs-OC-NE-X8X16:ip-address-deviations";
     }
   }
   deviation "/oc-netinst:network-instances/oc-netinst:network-instance/oc-netin"+
             "st:mpls/oc-netinst:lsps/oc-netinst:constrained-path/oc-netinst:tun"+
             "nels/oc-netinst:tunnel/oc-netinst:bandwidth/oc-netinst:config/oc-n"+
             "etinst:set-bandwidth" {
     deviate "add" {
       default "0";
     }
     deviate "replace" {
       type "oc-netinst-devs-OC-NE-X8X16:bandwidth-kbps-deviations";
     }
   }
   deviation "/oc-netinst:network-instances/oc-netinst:network-instance/oc-netin"+
             "st:mpls/oc-netinst:lsps/oc-netinst:constrained-path/oc-netinst:tun"+
             "nels/oc-netinst:tunnel/oc-netinst:config/oc-netinst:shortcut-eligi"+
             "ble" {
     deviate "replace" {
       default "false";
     }
   }
   deviation "/oc-netinst:network-instances/oc-netinst:network-instance/oc-netin"+
             "st:mpls/oc-netinst:lsps/oc-netinst:constrained-path/oc-netinst:tun"+
             "nels/oc-netinst:tunnel/oc-netinst:config/oc-netinst:type" {
     deviate "add" {
       mandatory "true";
     }
   }
   deviation "/oc-netinst:network-instances/oc-netinst:network-instance/oc-netin"+
             "st:mpls/oc-netinst:lsps/oc-netinst:constrained-path/oc-netinst:tun"+
             "nels/oc-netinst:tunnel/oc-netinst:config/oc-netinst:signaling-prot"+
             "ocol" {
     deviate "add" {
       mandatory "true";
     }
   }
   deviation "/oc-netinst:network-instances/oc-netinst:network-instance/oc-netin"+
             "st:mpls/oc-netinst:global/oc-netinst:interface-attributes/oc-netin"+
             "st:interface/oc-netinst:config/oc-netinst:mpls-enabled" {
     deviate "delete" {
       default "false";
     }
     deviate "add" {
       must "../mpls-enabled='true'";
       mandatory "true";
     }
   }
   deviation "/oc-netinst:network-instances/oc-netinst:network-instance/oc-netin"+
             "st:mpls/oc-netinst:lsps/oc-netinst:constrained-path/oc-netinst:tun"+
             "nels/oc-netinst:tunnel/oc-netinst:p2p-tunnel-attributes/oc-netinst"+
             ":p2p-primary-path/oc-netinst:p2p-primary-path/oc-netinst:config/oc"+
             "-netinst:path-computation-server" {
     deviate "replace" {
       type "oc-netinst-devs-OC-NE-X8X16:ip-address-deviations";
     }
   }
   deviation "/oc-netinst:network-instances/oc-netinst:network-instance/oc-netin"+
             "st:mpls/oc-netinst:lsps/oc-netinst:constrained-path/oc-netinst:tun"+
             "nels/oc-netinst:tunnel/oc-netinst:p2p-tunnel-attributes/oc-netinst"+
             ":p2p-primary-path/oc-netinst:p2p-primary-path/oc-netinst:config/oc"+
             "-netinst:use-cspf" {
     deviate "add" {
       default "true";
     }
   }
   deviation "/oc-netinst:network-instances/oc-netinst:network-instance/oc-netin"+
             "st:mpls/oc-netinst:te-interface-attributes/oc-netinst:interface/oc"+
             "-netinst:config/oc-netinst:interface-id" {
     deviate "replace" {
       type "leafref" {
         path "../../../../global/interface-attributes/interface/interface-id";
       }
     }
   }
   deviation "/oc-netinst:network-instances/oc-netinst:network-instance/oc-netin"+
             "st:mpls/oc-netinst:signaling-protocols/oc-netinst:rsvp-te/oc-netin"+
             "st:interface-attributes/oc-netinst:interface/oc-netinst:config/oc-"+
             "netinst:interface-id" {
     deviate "replace" {
       type "leafref" {
         path "../../../../../../te-interface-attributes/interface/interface-id";
       }
     }
   }
   deviation "/oc-netinst:network-instances/oc-netinst:network-instance/oc-netin"+
             "st:config/oc-netinst:route-distinguisher" {
     deviate "replace" {
       type "oc-netinst-devs-OC-NE-X8X16:route-distinguisher-deviations";
     }
     deviate "add" {
       must "../type='oc-ni-types:L3VRF'";
     }
   }
   deviation "/oc-netinst:network-instances/oc-netinst:network-instance/oc-netin"+
             "st:protocols/oc-netinst:protocol/oc-netinst:bgp/oc-netinst:global/"+
             "oc-netinst:config/oc-netinst:router-id" {
     deviate "replace" {
       type "inet:ipv4-address-no-zone";
     }
   }
   deviation "/oc-netinst:network-instances/oc-netinst:network-instance/oc-netin"+
             "st:connection-points/oc-netinst:connection-point/oc-netinst:config"+
             "/oc-netinst:connection-point-id" {
     deviate "replace" {
       type "string" {
         length "1..15";
       }
     }
   }
   deviation "/oc-netinst:network-instances/oc-netinst:network-instance/oc-netin"+
             "st:connection-points/oc-netinst:connection-point/oc-netinst:endpoi"+
             "nts/oc-netinst:endpoint/oc-netinst:config/oc-netinst:endpoint-id" {
     deviate "replace" {
       type "string" {
         length "1..15";
       }
     }
   }
   deviation "/oc-netinst:network-instances/oc-netinst:network-instance/oc-netin"+
             "st:connection-points/oc-netinst:connection-point/oc-netinst:endpoi"+
             "nts/oc-netinst:endpoint/oc-netinst:config/oc-netinst:type" {
     deviate "add" {
       must ".='oc-ni-types:REMOTE'";
       mandatory "true";
     }
   }
   deviation "/oc-netinst:network-instances/oc-netinst:network-instance/oc-netin"+
             "st:connection-points/oc-netinst:connection-point/oc-netinst:endpoi"+
             "nts/oc-netinst:endpoint/oc-netinst:config/oc-netinst:precedence" {
     deviate "replace" {
       type "uint16" {
         range "1..32";
       }
     }
     deviate "add" {
       mandatory "true";
     }
   }
   deviation "/oc-netinst:network-instances/oc-netinst:network-instance/oc-netin"+
             "st:connection-points/oc-netinst:connection-point/oc-netinst:endpoi"+
             "nts/oc-netinst:endpoint" {
     deviate "add" {
       unique "config/precedence";
       max-elements "2";
     }
   }
   deviation "/oc-netinst:network-instances/oc-netinst:network-instance/oc-netin"+
             "st:connection-points/oc-netinst:connection-point/oc-netinst:endpoi"+
             "nts/oc-netinst:endpoint/oc-netinst:remote/oc-netinst:config/oc-net"+
             "inst:remote-system" {
     deviate "replace" {
       type "oc-netinst-devs-OC-NE-X8X16:ipv4-address-deviations";
     }
     deviate "add" {
       mandatory "true";
     }
   }
   deviation "/oc-netinst:network-instances/oc-netinst:network-instance/oc-netin"+
             "st:connection-points/oc-netinst:connection-point/oc-netinst:endpoi"+
             "nts/oc-netinst:endpoint/oc-netinst:remote/oc-netinst:config/oc-net"+
             "inst:virtual-circuit-identifier" {
     deviate "add" {
       mandatory "true";
     }
     deviate "replace" {
       type "uint32" {
         range "1..4294967295";
       }
     }
   }
   deviation "/oc-netinst:network-instances/oc-netinst:network-instance/oc-netin"+
             "st:config/oc-netinst:enabled" {
     deviate "add" {
       must "../type='oc-ni-types:L2VSI' or (not(../type='oc-ni-types:L2VSI') "+
            "and .='true')";
       default "true";
     }
   }
   deviation "/oc-netinst:network-instances/oc-netinst:network-instance/oc-netin"+
             "st:encapsulation/oc-netinst:config/oc-netinst:encapsulation-type" {
     deviate "add" {
       must ".='oc-ni-types:MPLS'";
     }
   }
   deviation "/oc-netinst:network-instances/oc-netinst:network-instance/oc-netin"+
             "st:inter-instance-policies/oc-netinst:apply-policy/oc-netinst:conf"+
             "ig/oc-netinst:import-policy" {
     deviate "add" {
       max-elements "1";
     }
   }
   deviation "/oc-netinst:network-instances/oc-netinst:network-instance/oc-netin"+
             "st:inter-instance-policies/oc-netinst:apply-policy/oc-netinst:conf"+
             "ig/oc-netinst:export-policy" {
     deviate "add" {
       max-elements "1";
     }
   }
   deviation "/oc-netinst:network-instances/oc-netinst:network-instance" {
     deviate "add" {
       must "((./config/type='oc-ni-types:L2P2P' and (count(./interfaces/interfa"+
            "ce)=1) and (count(./connection-points/connection-point)=1) and "+
            "./connection-points/connection-point/endpoints/endpoint/config/prec"+
            "edence<=2 and ./connection-points/connection-point/endpoints/endpoi"+
            "nt/config[precedence=1]) or\n./config/type!='oc-ni-types:L2P2P')";
     }
   }
   deviation "/oc-netinst:network-instances/oc-netinst:network-instance/oc-netin"+
             "st:config/oc-netinst:name" {
     deviate "replace" {
       type "string" {
         length "1..31";
       }
     }
     deviate "add" {
       must "(../name='_public_' and ../type='oc-ni-types:DEFAULT_INSTANCE') or "+
            "(../name!='_public_' and ../type!='oc-ni-types:DEFAULT_INSTANCE')";
     }
   }
   deviation "/oc-netinst:network-instances/oc-netinst:network-instance/oc-netin"+
             "st:config/oc-netinst:description" {
     deviate "replace" {
       type "string" {
         length "1..242";
       }
     }
     deviate "add" {
       must "../type='oc-ni-types:L3VRF' or ((../type='oc-ni-types:L2P2P' or "+
            "../type='oc-ni-types:L2VSI') and (string-length(../description) <= "+
            "128))";
     }
   }
   deviation "/oc-netinst:network-instances/oc-netinst:network-instance/oc-netin"+
             "st:config/oc-netinst:enabled-address-families" {
     deviate "add" {
       must "../type='oc-ni-types:L3VRF'";
     }
   }
   deviation "/oc-netinst:network-instances/oc-netinst:network-instance/oc-netin"+
             "st:encapsulation/oc-netinst:config/oc-netinst:label-allocation-mod"+
             "e" {
     deviate "add" {
       must "../../../config/route-distinguisher and ../../../config/type='oc-ni"+
            "-types:L3VRF'";
     }
   }
   deviation "/oc-netinst:network-instances/oc-netinst:network-instance/oc-netin"+
             "st:encapsulation" {
     deviate "add" {
       must "../config/type='oc-ni-types:L3VRF' or ../config/type='oc-ni-types:L"+
            "2P2P' or ../config/type='oc-ni-types:L2VSI'";
     }
   }
   deviation "/oc-netinst:network-instances/oc-netinst:network-instance/oc-netin"+
             "st:inter-instance-policies" {
     deviate "add" {
       must "../config/type='oc-ni-types:L3VRF' or ../config/type='oc-ni-types:D"+
            "EFAULT_INSTANCE'";
     }
   }
   deviation "/oc-netinst:network-instances/oc-netinst:network-instance/oc-netin"+
             "st:table-connections" {
     deviate "add" {
       must "../config/type='oc-ni-types:L3VRF' or ../config/type='oc-ni-types:D"+
            "EFAULT_INSTANCE'";
     }
   }
   deviation "/oc-netinst:network-instances/oc-netinst:network-instance/oc-netin"+
             "st:connection-points" {
     deviate "add" {
       must "../config/type='oc-ni-types:L2P2P' or ../config/type='oc-ni-types:L"+
            "2VSI'";
     }
   }
   deviation "/oc-netinst:network-instances/oc-netinst:network-instance/oc-netin"+
             "st:protocols" {
     deviate "add" {
       must "../config/type='oc-ni-types:L3VRF' or ../config/type='oc-ni-types:D"+
            "EFAULT_INSTANCE'";
     }
   }
   deviation "/oc-netinst:network-instances/oc-netinst:network-instance/oc-netin"+
             "st:inter-instance-policies/oc-netinst:apply-policy/oc-netinst:conf"+
             "ig/oc-netinst:import-policy" {
     deviate "add" {
       must "../../../../config/route-distinguisher";
     }
   }
   deviation "/oc-netinst:network-instances/oc-netinst:network-instance/oc-netin"+
             "st:inter-instance-policies/oc-netinst:apply-policy/oc-netinst:conf"+
             "ig/oc-netinst:export-policy" {
     deviate "add" {
       must "../../../../config/route-distinguisher";
     }
   }
   deviation "/oc-netinst:network-instances/oc-netinst:network-instance/oc-netin"+
             "st:config/oc-netinst:type" {
     deviate "add" {
       must "../type='oc-ni-types:DEFAULT_INSTANCE' or ../type='oc-ni-types:L3VR"+
            "F' or ../type='oc-ni-types:L2P2P' or ../type='oc-ni-types:L2VSI'";
       mandatory "true";
     }
   }
   deviation "/oc-netinst:network-instances/oc-netinst:network-instance/oc-netin"+
             "st:protocols/oc-netinst:protocol/oc-netinst:bgp/oc-netinst:global/"+
             "oc-netinst:afi-safis/oc-netinst:afi-safi/oc-netinst:config/oc-neti"+
             "nst:afi-safi-name" {
     deviate "add" {
       must "../afi-safi-name='oc-bgp-types:IPV4_UNICAST' or ../afi-safi-name='o"+
            "c-bgp-types:IPV6_UNICAST' or ../afi-safi-name='oc-bgp-types:IPV4_LA"+
            "BELED_UNICAST' or ../afi-safi-name='oc-bgp-types:L3VPN_IPV4_UNICAST"+
            "' or ../afi-safi-name='oc-bgp-types:L3VPN_IPV6_UNICAST' or "+
            "../afi-safi-name='oc-bgp-types:L2VPN_VPLS' or ../afi-safi-name='oc-"+
            "bgp-types:L2VPN_EVPN' or ../afi-safi-name='oc-bgp-types:SRTE_POLICY"+
            "_IPV4' or ../afi-safi-name='oc-bgp-types:SRTE_POLICY_IPV6'";
       must "../../../../../../../../name='_public_' or (../../../../../../../.."+
            "/name!='_public_' and (((../afi-safi-name='oc-bgp-types:IPV4_UNICAS"+
            "T' or ../afi-safi-name='oc-bgp-types:IPV4_LABELED_UNICAST') and "+
            "../../../../../../../../config/enabled-address-families[.='oc-types"+
            ":IPV4'])  or (../afi-safi-name='oc-bgp-types:IPV6_UNICAST' and "+
            "../../../../../../../../config/enabled-address-families[.='oc-types"+
            ":IPV6'])))";
     }
   }
   deviation "/oc-netinst:network-instances/oc-netinst:network-instance/oc-netin"+
             "st:protocols/oc-netinst:protocol/oc-netinst:bgp/oc-netinst:neighbo"+
             "rs/oc-netinst:neighbor/oc-netinst:afi-safis/oc-netinst:afi-safi/oc"+
             "-netinst:config/oc-netinst:afi-safi-name" {
     deviate "add" {
       must "../../../../../../global/afi-safis/afi-safi[afi-safi-name = "+
            "current()]";
     }
   }
   deviation "/oc-netinst:network-instances/oc-netinst:network-instance/oc-netin"+
             "st:protocols/oc-netinst:protocol/oc-netinst:bgp/oc-netinst:neighbo"+
             "rs/oc-netinst:neighbor/oc-netinst:afi-safis/oc-netinst:afi-safi/oc"+
             "-netinst:apply-policy/oc-netinst:config/oc-netinst:import-policy" {
     deviate "add" {
       max-elements "1";
     }
   }
   deviation "/oc-netinst:network-instances/oc-netinst:network-instance/oc-netin"+
             "st:protocols/oc-netinst:protocol/oc-netinst:bgp/oc-netinst:neighbo"+
             "rs/oc-netinst:neighbor/oc-netinst:afi-safis/oc-netinst:afi-safi/oc"+
             "-netinst:apply-policy/oc-netinst:config/oc-netinst:export-policy" {
     deviate "add" {
       max-elements "1";
     }
   }
   deviation "/oc-netinst:network-instances/oc-netinst:network-instance/oc-netin"+
             "st:protocols/oc-netinst:protocol/oc-netinst:bgp/oc-netinst:neighbo"+
             "rs/oc-netinst:neighbor/oc-netinst:config/oc-netinst:peer-as" {
     deviate "add" {
       mandatory "true";
     }
   }
   deviation "/oc-netinst:network-instances/oc-netinst:network-instance/oc-netin"+
             "st:protocols/oc-netinst:protocol/oc-netinst:bgp/oc-netinst:neighbo"+
             "rs/oc-netinst:neighbor/oc-netinst:config/oc-netinst:description" {
     deviate "replace" {
       type "string" {
         length "1..255";
       }
     }
   }
   deviation "/oc-netinst:network-instances/oc-netinst:network-instance/oc-netin"+
             "st:protocols/oc-netinst:protocol/oc-netinst:bgp/oc-netinst:neighbo"+
             "rs/oc-netinst:neighbor/oc-netinst:ebgp-multihop/oc-netinst:config/"+
             "oc-netinst:multihop-ttl" {
     deviate "replace" {
       type "uint8" {
         range "1..255";
       }
     }
   }
   deviation "/oc-netinst:network-instances/oc-netinst:network-instance/oc-netin"+
             "st:table-connections/oc-netinst:table-connection/oc-netinst:config"+
             "/oc-netinst:import-policy" {
     deviate "add" {
       max-elements "1";
     }
   }
   deviation "/oc-netinst:network-instances/oc-netinst:network-instance/oc-netin"+
             "st:table-connections/oc-netinst:table-connection/oc-netinst:config"+
             "/oc-netinst:src-protocol" {
     deviate "replace" {
       type "leafref" {
         path "../../../../protocols/protocol/config/identifier";
       }
     }
   }
   deviation "/oc-netinst:network-instances/oc-netinst:network-instance/oc-netin"+
             "st:table-connections/oc-netinst:table-connection/oc-netinst:config"+
             "/oc-netinst:src-protocol" {
     deviate "add" {
       must "not (../src-protocol=../dst-protocol) and (../src-protocol='oc-pol-"+
            "types:STATIC' or ../src-protocol='oc-pol-types:DIRECTLY_CONNECTED' "+
            "or (../src-protocol='oc-pol-types:OSPF' and ../address-family='oc-t"+
            "ypes:IPV4'))";
     }
   }
   deviation "/oc-netinst:network-instances/oc-netinst:network-instance/oc-netin"+
             "st:table-connections/oc-netinst:table-connection/oc-netinst:config"+
             "/oc-netinst:address-family" {
     deviate "replace" {
       type "identityref" {
         base "oc-types:ADDRESS_FAMILY";
       }
     }
   }
   deviation "/oc-netinst:network-instances/oc-netinst:network-instance/oc-netin"+
             "st:table-connections/oc-netinst:table-connection/oc-netinst:config"+
             "/oc-netinst:address-family" {
     deviate "add" {
       must "../address-family='oc-types:IPV4' or ../address-family='oc-types:IP"+
            "V6'";
     }
   }
   deviation "/oc-netinst:network-instances/oc-netinst:network-instance/oc-netin"+
             "st:table-connections/oc-netinst:table-connection/oc-netinst:config"+
             "/oc-netinst:dst-protocol" {
     deviate "replace" {
       type "leafref" {
         path "../../../../protocols/protocol/config/identifier";
       }
     }
   }
   deviation "/oc-netinst:network-instances/oc-netinst:network-instance/oc-netin"+
             "st:table-connections/oc-netinst:table-connection/oc-netinst:config"+
             "/oc-netinst:dst-protocol" {
     deviate "add" {
       must "../dst-protocol='oc-pol-types:BGP' and ((../address-family='oc-type"+
            "s:IPV4' and ../../../../protocols/protocol[identifier='oc-pol-types"+
            ":BGP']/bgp/global/afi-safis/afi-safi[afi-safi-name='oc-bgp-types:IP"+
            "V4_UNICAST']) or (../address-family='oc-types:IPV6' and ../../../.."+
            "/protocols/protocol[identifier='oc-pol-types:BGP']/bgp/global/afi-s"+
            "afis/afi-safi[afi-safi-name='oc-bgp-types:IPV6_UNICAST']))";
     }
   }
   deviation "/oc-netinst:network-instances/oc-netinst:network-instance/oc-netin"+
             "st:fdb" {
     deviate "add" {
       must "../config/type='oc-ni-types:L2VSI'";
     }
   }
   deviation "/oc-netinst:network-instances/oc-netinst:network-instance/oc-netin"+
             "st:fdb/oc-netinst:config/oc-netinst:mac-learning" {
     deviate "add" {
       default "true";
     }
   }
   deviation "/oc-netinst:network-instances/oc-netinst:network-instance/oc-netin"+
             "st:fdb/oc-netinst:config/oc-netinst:mac-aging-time" {
     deviate "replace" {
       type "uint32" {
         range "0|60..1000000";
       }
     }
   }
   deviation "/oc-netinst:network-instances/oc-netinst:network-instance/oc-netin"+
             "st:fdb/oc-netinst:config/oc-netinst:maximum-entries" {
     deviate "replace" {
       type "uint32" {
         range "1..2048000";
       }
     }
   }
   deviation "/oc-netinst:network-instances/oc-netinst:network-instance/oc-netin"+
             "st:protocols/oc-netinst:protocol/oc-netinst:static-routes/oc-netin"+
             "st:static/oc-netinst:next-hops/oc-netinst:next-hop" {
     deviate "add" {
       min-elements "1";
     }
   }
   deviation "/oc-netinst:network-instances/oc-netinst:network-instance/oc-netin"+
             "st:protocols/oc-netinst:protocol/oc-netinst:static-routes/oc-netin"+
             "st:static/oc-netinst:next-hops/oc-netinst:next-hop/oc-netinst:conf"+
             "ig/oc-netinst:index" {
     deviate "replace" {
       type "string" {
         length "1..103";
       }
     }
   }
   deviation "/oc-netinst:network-instances/oc-netinst:network-instance/oc-netin"+
             "st:protocols/oc-netinst:protocol/oc-netinst:static-routes/oc-netin"+
             "st:static/oc-netinst:next-hops/oc-netinst:next-hop/oc-netinst:stat"+
             "e/oc-netinst:index" {
     deviate "replace" {
       type "string" {
         length "1..103";
       }
     }
   }
   deviation "/oc-netinst:network-instances/oc-netinst:network-instance/oc-netin"+
             "st:protocols/oc-netinst:protocol/oc-netinst:static-routes/oc-netin"+
             "st:static/oc-netinst:next-hops/oc-netinst:next-hop/oc-netinst:inte"+
             "rface-ref/oc-netinst:config/oc-netinst:interface" {
     deviate "replace" {
       type "string" {
         length "0..63";
       }
     }
   }
   deviation "/oc-netinst:network-instances/oc-netinst:network-instance/oc-netin"+
             "st:protocols/oc-netinst:protocol/oc-netinst:static-routes/oc-netin"+
             "st:static/oc-netinst:next-hops/oc-netinst:next-hop/oc-netinst:inte"+
             "rface-ref/oc-netinst:config/oc-netinst:subinterface" {
     deviate "add" {
       must "../interface";
     }
   }
   deviation "/oc-netinst:network-instances/oc-netinst:network-instance/oc-netin"+
             "st:protocols/oc-netinst:protocol/oc-netinst:static-routes/oc-netin"+
             "st:static/oc-netinst:next-hops/oc-netinst:next-hop/oc-netinst:inte"+
             "rface-ref/oc-netinst:state/oc-netinst:interface" {
     deviate "replace" {
       type "string" {
         length "0..63";
       }
     }
   }
   deviation "/oc-netinst:network-instances/oc-netinst:network-instance/oc-netin"+
             "st:protocols/oc-netinst:protocol/oc-netinst:static-routes/oc-netin"+
             "st:static/oc-netinst:next-hops/oc-netinst:next-hop/oc-netinst:inte"+
             "rface-ref/oc-netinst:state/oc-netinst:subinterface" {
     deviate "add" {
       must "../interface";
     }
   }
   deviation "/oc-netinst:network-instances/oc-netinst:network-instance/oc-netin"+
             "st:protocols/oc-netinst:protocol/oc-netinst:static-routes/oc-netin"+
             "st:static/oc-netinst:config/oc-netinst:prefix" {
     deviate "replace" {
       type "oc-netinst-devs-OC-NE-X8X16:ip-prefix-deviations";
     }
   }
   deviation "/oc-netinst:network-instances/oc-netinst:network-instance/oc-netin"+
             "st:protocols/oc-netinst:protocol/oc-netinst:static-routes/oc-netin"+
             "st:static/oc-netinst:next-hops/oc-netinst:next-hop/oc-netinst:conf"+
             "ig/oc-netinst:next-hop" {
     deviate "replace" {
       type "oc-netinst-devs-OC-NE-X8X16:ip-address-deviations";
     }
   }
   deviation "/oc-netinst:network-instances/oc-netinst:network-instance/oc-netin"+
             "st:protocols/oc-netinst:protocol/oc-netinst:bgp/oc-netinst:neighbo"+
             "rs/oc-netinst:neighbor/oc-netinst:config/oc-netinst:neighbor-addre"+
             "ss" {
     deviate "replace" {
       type "oc-netinst-devs-OC-NE-X8X16:ip-address-deviations";
     }
   }
   deviation "/oc-netinst:network-instances/oc-netinst:network-instance/oc-netin"+
             "st:protocols/oc-netinst:protocol/oc-netinst:static-routes/oc-netin"+
             "st:static/oc-netinst:next-hops/oc-netinst:next-hop/oc-netinst:conf"+
             "ig/oc-netinst:metric" {
     deviate "replace" {
       type "uint32" {
         range "1..4294967295";
       }
     }
   }
   deviation "/oc-netinst:network-instances/oc-netinst:network-instance/oc-netin"+
             "st:protocols/oc-netinst:protocol/oc-netinst:static-routes/oc-netin"+
             "st:static/oc-netinst:next-hops/oc-netinst:next-hop/oc-netinst:stat"+
             "e/oc-netinst:metric" {
     deviate "replace" {
       type "uint32" {
         range "1..4294967295";
       }
     }
   }
   deviation "/oc-netinst:network-instances/oc-netinst:network-instance/oc-netin"+
             "st:protocols/oc-netinst:protocol/oc-netinst:config/oc-netinst:iden"+
             "tifier" {
     deviate "add" {
       must "(../identifier='oc-pol-types:BGP' and /network-instances/network-in"+
            "stance[name='_public_']/protocols/protocol[identifier='oc-pol-types"+
            ":BGP']) or (../identifier='oc-pol-types:STATIC' or ../identifier='o"+
            "c-pol-types:DIRECTLY_CONNECTED' or ../identifier='oc-pol-types:OSPF"+
            "')";
     }
   }
   deviation "/oc-netinst:network-instances/oc-netinst:network-instance/oc-netin"+
             "st:protocols/oc-netinst:protocol/oc-netinst:config/oc-netinst:name"+
             "" {
     deviate "add" {
       must "((../identifier='oc-pol-types:STATIC' or ../identifier='oc-pol-type"+
            "s:DIRECTLY_CONNECTED' or ../identifier='oc-pol-types:BGP') and "+
            "../name='default') or (../identifier='oc-pol-types:OSPF')";
     }
   }
   deviation "/oc-netinst:network-instances/oc-netinst:network-instance/oc-netin"+
             "st:interfaces/oc-netinst:interface/oc-netinst:config/oc-netinst:su"+
             "binterface" {
     deviate "add" {
       must "../interface";
     }
   }
   deviation "/oc-netinst:network-instances/oc-netinst:network-instance/oc-netin"+
             "st:protocols/oc-netinst:protocol/oc-netinst:ospfv2/oc-netinst:area"+
             "s/oc-netinst:area/oc-netinst:interfaces/oc-netinst:interface/oc-ne"+
             "tinst:config/oc-netinst:passive" {
     deviate "add" {
       default "true";
     }
   }
   deviation "/oc-netinst:network-instances/oc-netinst:network-instance/oc-netin"+
             "st:protocols/oc-netinst:protocol/oc-netinst:bgp/oc-netinst:global/"+
             "oc-netinst:graceful-restart/oc-netinst:config" {
     deviate "add" {
       must "../../../../../../name='_public_'";
     }
   }
   deviation "/oc-netinst:network-instances/oc-netinst:network-instance/oc-netin"+
             "st:protocols/oc-netinst:protocol/oc-netinst:bgp/oc-netinst:global/"+
             "oc-netinst:graceful-restart/oc-netinst:config/oc-netinst:enabled" {
     deviate "add" {
       default "false";
     }
   }
   ext:deviation-ext "/oc-netinst:network-instances/oc-netinst:network-instance/"+
                     "oc-netinst:mpls/oc-netinst:lsps/oc-netinst:constrained-pat"+
                     "h/oc-netinst:tunnels/oc-netinst:tunnel/oc-netinst:p2p-tunn"+
                     "el-attributes/oc-netinst:p2p-primary-path/oc-netinst:p2p-p"+
                     "rimary-path" {
     ext:deviate-ext "add" {
       ext:generated-by "system" {
         description
           "The p2p primary path is generated automatically.";
       }
       ext:operation-exclude "create|delete" {
         description
           "The node does not support the create and delete operations.";
       }
     }
   }
   ext:deviation-ext "/oc-netinst:network-instances/oc-netinst:network-instance/"+
                     "oc-netinst:connection-points/oc-netinst:connection-point/o"+
                     "c-netinst:endpoints/oc-netinst:endpoint/oc-netinst:remote/"+
                     "oc-netinst:config/oc-netinst:remote-system" {
     ext:deviate-ext "add" {
       ext:operation-exclude "update" {
         description
           "The node cannot be modified, when node is already configured.";
       }
     }
   }
   ext:deviation-ext "/oc-netinst:network-instances/oc-netinst:network-instance/"+
                     "oc-netinst:connection-points/oc-netinst:connection-point/o"+
                     "c-netinst:endpoints/oc-netinst:endpoint/oc-netinst:remote/"+
                     "oc-netinst:config/oc-netinst:virtual-circuit-identifier" {
     ext:deviate-ext "add" {
       ext:operation-exclude "update" {
         description
           "The node cannot be modified, when node is already configured.";
       }
     }
   }
   ext:deviation-ext "/oc-netinst:network-instances/oc-netinst:network-instance" {
     ext:deviate-ext "add" {
       ext:generated-by "system" {
         ext:filter "name = '_public_'";
         description
           "The public instances is generated automatically.";
       }
     }
   }
   ext:deviation-ext "/oc-netinst:network-instances/oc-netinst:network-instance/"+
                     "oc-netinst:config/oc-netinst:type" {
     ext:deviate-ext "add" {
       ext:operation-exclude "update" {
         description
           "The node cannot be modified, when node is already configured.";
       }
     }
   }
   ext:deviation-ext "/oc-netinst:network-instances/oc-netinst:network-instance/"+
                     "oc-netinst:encapsulation/oc-netinst:config/oc-netinst:labe"+
                     "l-allocation-mode" {
     ext:deviate-ext "add" {
       ext:dynamic-default {
         ext:default-value "oc-ni-types:INSTANCE_LABEL" {
           when "../../../config/route-distinguisher and ../../../config/type='o"+
                "c-ni-types:L3VRF'";
         }
       }
     }
   }
   ext:deviation-ext "/oc-netinst:network-instances/oc-netinst:network-instance/"+
                     "oc-netinst:encapsulation" {
     ext:deviate-ext "replace" {
       when "../config/type='oc-ni-types:L3VRF' or ../config/type='oc-ni-types:L"+
            "2P2P' or ../config/type='oc-ni-types:L2VSI'";
     }
   }
   ext:deviation-ext "/oc-netinst:network-instances/oc-netinst:network-instance/"+
                     "oc-netinst:inter-instance-policies" {
     ext:deviate-ext "add" {
       when "../config/type='oc-ni-types:L3VRF' or ../config/type='oc-ni-types:D"+
            "EFAULT_INSTANCE'";
     }
   }
   ext:deviation-ext "/oc-netinst:network-instances/oc-netinst:network-instance/"+
                     "oc-netinst:table-connections" {
     ext:deviate-ext "add" {
       when "../config/type='oc-ni-types:L3VRF' or ../config/type='oc-ni-types:D"+
            "EFAULT_INSTANCE'";
     }
   }
   ext:deviation-ext "/oc-netinst:network-instances/oc-netinst:network-instance/"+
                     "oc-netinst:connection-points" {
     ext:deviate-ext "add" {
       when "../config/type='oc-ni-types:L2P2P' or ../config/type='oc-ni-types:L"+
            "2VSI'";
     }
   }
   ext:deviation-ext "/oc-netinst:network-instances/oc-netinst:network-instance/"+
                     "oc-netinst:protocols" {
     ext:deviate-ext "add" {
       when "../config/type='oc-ni-types:L3VRF' or ../config/type='oc-ni-types:D"+
            "EFAULT_INSTANCE'";
     }
   }
   ext:deviation-ext "/oc-netinst:network-instances/oc-netinst:network-instance/"+
                     "oc-netinst:protocols/oc-netinst:protocol/oc-netinst:bgp/oc"+
                     "-netinst:global/oc-netinst:afi-safis/oc-netinst:afi-safi" {
     ext:deviate-ext "add" {
       ext:generated-by "system" {
         when "../../../../../../oc-netinst:name = '_public_'";
         ext:filter "afi-safi-name = 'oc-bgp-types:IPV4_UNICAST'";
         description
           "The public instances is generated automatically when BGP protocol is"+
           " created.";
       }
     }
   }
   ext:deviation-ext "/oc-netinst:network-instances/oc-netinst:network-instance/"+
                     "oc-netinst:protocols/oc-netinst:protocol/oc-netinst:bgp/oc"+
                     "-netinst:neighbors/oc-netinst:neighbor/oc-netinst:config/o"+
                     "c-netinst:peer-as" {
     ext:deviate-ext "add" {
       ext:operation-exclude "update" {
         description
           "The node cannot be modified, when node is already configured.";
       }
     }
   }
   ext:deviation-ext "/oc-netinst:network-instances/oc-netinst:network-instance/"+
                     "oc-netinst:protocols/oc-netinst:protocol/oc-netinst:bgp/oc"+
                     "-netinst:neighbors/oc-netinst:neighbor/oc-netinst:ebgp-mul"+
                     "tihop/oc-netinst:config/oc-netinst:multihop-ttl" {
     ext:deviate-ext "add" {
       ext:dynamic-default {
         ext:default-value "1";
       }
     }
   }
   ext:deviation-ext "/oc-netinst:network-instances/oc-netinst:network-instance/"+
                     "oc-netinst:fdb" {
     ext:deviate-ext "add" {
       when "../config/type='oc-ni-types:L2VSI'";
     }
   }
   ext:deviation-ext "/oc-netinst:network-instances/oc-netinst:network-instance/"+
                     "oc-netinst:protocols/oc-netinst:protocol" {
     ext:deviate-ext "add" {
       ext:generated-by "system" {
         ext:filter "(identifier='oc-pol-types:STATIC' and name='default') or "+
                    "(identifier='oc-pol-types:DIRECTLY_CONNECTED' and "+
                    "name='default')";
         description
           "The STATIC and DIRECTLY_CONNECTED are generated automatically.";
       }
     }
   }
 }

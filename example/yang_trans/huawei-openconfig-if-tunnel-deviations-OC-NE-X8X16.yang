/*
Copyright (C) 2020 Huawei Technologies Co., Ltd. All rights reserved.
*/

 module huawei-openconfig-if-tunnel-deviations-OC-NE-X8X16 {
   yang-version "1";
   namespace "urn:huawei:yang:huawei-openconfig-if-tunnel-deviations-OC-NE-X8X16"+
             "";
   prefix "oc-if-tunnel-devs-OC-NE-X8X16";
   import openconfig-interfaces {
     prefix "oc-if";
   }
   import openconfig-if-tunnel {
     prefix "oc-tun";
   }
   import huawei-extension {
     prefix "ext";
   }
   import iana-if-type {
     prefix "ianaift";
   }
   organization
     "Huawei Technologies Co., Ltd.";
   contact
     "Huawei Industrial Base\nBantian, Longgang\nShenzhen 518129\nPeople's "+
     "Republic of China\nWebsite: http://www.huawei.com\nEmail: support@huawei.c"+
     "om";
   description
     "This model adds extensions to the OpenConfig interfaces\nmodel to "+
     "configure tunnel interfaces on a network\ndevice.";
   revision "2020-10-20" {
     description
       "Initial revision.";
     reference
       "Huawei private.";
   }
   deviation "/oc-if:interfaces/oc-if:interface/oc-tun:tunnel/oc-tun:ipv4/oc-tun"+
             ":config/oc-tun:mtu" {
     deviate "replace" {
       type "uint16" {
         range "46..64000";
       }
     }
   }
   deviation "/oc-if:interfaces/oc-if:interface/oc-tun:tunnel/oc-tun:ipv4/oc-tun"+
             ":state/oc-tun:mtu" {
     deviate "replace" {
       type "uint16" {
         range "46..64000";
       }
     }
   }
   deviation "/oc-if:interfaces/oc-if:interface/oc-tun:tunnel/oc-tun:ipv4/oc-tun"+
             ":config/oc-tun:enabled" {
     deviate "add" {
       must "../enabled='true'";
     }
   }
   deviation "/oc-if:interfaces/oc-if:interface/oc-tun:tunnel/oc-tun:ipv4/oc-tun"+
             ":addresses/oc-tun:address/oc-tun:config/oc-tun:prefix-length" {
     deviate "add" {
       mandatory "true";
     }
   }
   ext:deviation-ext "/oc-if:interfaces/oc-if:interface/oc-tun:tunnel" {
     ext:deviate-ext "add" {
       when "../oc-if:config/oc-if:type='ianaift:tunnel'";
     }
   }
 }

/*
Copyright (C) 2020 Huawei Technologies Co., Ltd. All rights reserved.
*/

 module huawei-ietf-network-instance-deviations-OC-NE-X8X16 {
   yang-version "1.1";
   namespace "urn:huawei:yang:huawei-ietf-network-instance-deviations-OC-NE-X8X1"+
             "6";
   prefix "ni-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Deviations for ietf-network-instance model.";
   revision "2020-10-10" {
     description
       "Initial revision.";
     reference
       "Huawei private.";
   }
 }

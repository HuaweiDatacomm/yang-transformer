/*
Copyright (C) 2020-2021 Huawei Technologies Co., Ltd. All rights reserved.
*/

 module huawei-oam-bfd-interface {
   namespace "urn:huawei:yang:huawei-oam-bfd-interface";
   prefix "oam-bfd-interface";
   import huawei-extension {
     prefix "ext";
   }
   import huawei-oammgr {
     prefix "oammgr";
   }
   import huawei-bfd {
     prefix "bfd";
   }
   import huawei-ifm {
     prefix "ifm";
   }
   import huawei-bfd-static-mpls-te {
     prefix "bfd-static-mpls-te";
   }
   import huawei-bfd-static-vpls {
     prefix "bfd-static-vpls";
   }
   import huawei-bfd-static-vpws {
     prefix "bfd-static-vpws";
   }
   organization
     "Huawei Technologies Co., Ltd.";
   contact
     "Huawei Industrial Base\nBantian, Longgang\nShenzhen 518129\nPeople's "+
     "Republic of China\nWebsite: http://www.huawei.com\nEmail: support@huawei.c"+
     "om";
   description
     "Configure the operation, administration and maintenance (OAM) association "+
     "function.";
   revision "2021-03-19" {
     description
       "Reconstruct leaf.";
     reference
       "Huawei private.";
   }
   revision "2020-12-12" {
     description
       "Initial revision.";
     reference
       "Huawei private.";
   }
   ext:task-name "bfd";
   augment "/oammgr:oammgr" {
     description
       "Configure the operation, administration and maintenance (OAM) associatio"+
       "n function.";
     container bfd-bind-interfaces {
       description
         "List of associations between BFD and an interface.";
       list bfd-bind-interface {
         key "if-name";
         description
           "Configure an instance of an association between BFD and an "+
           "interface.";
         leaf if-name {
           type "leafref" {
             path "/ifm:ifm/ifm:interfaces/ifm:interface/ifm:name";
           }
           description
             "Configure the name of interface.";
         }
         leaf reboot-impact {
           type "boolean";
           default "false";
           description
             "Enable/disable a BFD session to associate the interface status "+
             "after device reboot.";
         }
         choice name-or-id {
           mandatory "true";
           description
             "List of BFD session configurations.";
           case name {
             description
               "List of name of BFD session.";
             leaf bfd-sess-name {
               type "leafref" {
                 path "/bfd:bfd/bfd:sessions/bfd:session/bfd:name";
               }
               description
                 "Configure the name of a BFD session.";
               must "count(/oammgr:oammgr/oam-bfd-interface:bfd-bind-interfaces/"+
                    "oam-bfd-interface:bfd-bind-interface[oam-bfd-interface:bfd-"+
                    "sess-name=current()]) <= 1 and count(/oammgr:oammgr/oam-bfd"+
                    "-interface:bfd-bind-interfaces/oam-bfd-interface:bfd-bind-i"+
                    "nterface[oam-bfd-interface:bfd-session-id=(/bfd:bfd/bfd:ses"+
                    "sions/bfd:session[bfd:name=current()]/bfd:local-discriminat"+
                    "or-multicast-ipv4)]) = 0 and count(/oammgr:oammgr/oam-bfd-i"+
                    "nterface:bfd-bind-interfaces/oam-bfd-interface:bfd-bind-int"+
                    "erface[oam-bfd-interface:bfd-session-id=(/bfd:bfd/bfd:sessi"+
                    "ons/bfd:session[bfd:name=current()]/bfd:local-discriminator"+
                    ")]) = 0 and count(/oammgr:oammgr/oam-bfd-interface:bfd-bind"+
                    "-interfaces/oam-bfd-interface:bfd-bind-interface[oam-bfd-in"+
                    "terface:bfd-session-id=(/bfd:bfd/bfd:sessions/bfd:session[b"+
                    "fd:name=current()]/bfd:local-discriminator-static-ipv6)]) ="+
                    " 0 and count(/oammgr:oammgr/oam-bfd-interface:bfd-bind-inte"+
                    "rfaces/oam-bfd-interface:bfd-bind-interface[oam-bfd-interfa"+
                    "ce:bfd-session-id=(/bfd:bfd/bfd:sessions/bfd:session[bfd:na"+
                    "me=current()]/bfd:local-discriminator-static-ldp-lsp)]) = 0"+
                    " and count(/oammgr:oammgr/oam-bfd-interface:bfd-bind-interf"+
                    "aces/oam-bfd-interface:bfd-bind-interface[oam-bfd-interface"+
                    ":bfd-session-id=(/bfd:bfd/bfd:sessions/bfd:session[bfd:name"+
                    "=current()]/bfd-static-mpls-te:local-discriminator-static-t"+
                    "e-lsp)]) = 0 and count(/oammgr:oammgr/oam-bfd-interface:bfd"+
                    "-bind-interfaces/oam-bfd-interface:bfd-bind-interface[oam-b"+
                    "fd-interface:bfd-session-id=(/bfd:bfd/bfd:sessions/bfd:sess"+
                    "ion[bfd:name=current()]/bfd-static-mpls-te:local-discrimina"+
                    "tor-static-te-tunnel)]) = 0 and (not((/bfd:bfd/bfd:sessions"+
                    "/bfd:session[bfd:name=current()]/bfd:bundle-mode-auto-ipv4 "+
                    "and /bfd:bfd/bfd:sessions/bfd:session[bfd:name=current()]/b"+
                    "fd:bundle-mode-auto-ipv4 !='none') or (/bfd:bfd/bfd:session"+
                    "s/bfd:session[bfd:name=current()]/bfd:bundle-mode-auto-ipv6"+
                    " and /bfd:bfd/bfd:sessions/bfd:session[bfd:name=current()]/"+
                    "bfd:bundle-mode-auto-ipv6 !='none') or (/bfd:bfd/bfd:sessio"+
                    "ns/bfd:session[bfd:name=current()]/bfd-static-vpls:vsi-name"+
                    "-static-vsi-pw) or (/bfd:bfd/bfd:sessions/bfd:session[bfd:n"+
                    "ame=current()]/bfd-static-vpws:out-if-name-static-vll-pw)))"+
                    "";
             }
           }
           case id {
             description
               "List of local discriminator of BFD session.";
             leaf bfd-session-id {
               type "uint32" {
                 range "1..16384";
               }
               description
                 "Configure the local discriminator of a BFD session.";
               must "count(/oammgr:oammgr/oam-bfd-interface:bfd-bind-interfaces/"+
                    "oam-bfd-interface:bfd-bind-interface[oam-bfd-interface:bfd-"+
                    "session-id=current()]) <= 1 and count(/oammgr:oammgr/oam-bf"+
                    "d-interface:bfd-bind-interfaces/oam-bfd-interface:bfd-bind-"+
                    "interface[oam-bfd-interface:bfd-sess-name=(/bfd:bfd/bfd:ses"+
                    "sions/bfd:session[bfd:local-discriminator-multicast-ipv4=cu"+
                    "rrent()]/bfd:name)]) = 0 and count(/oammgr:oammgr/oam-bfd-i"+
                    "nterface:bfd-bind-interfaces/oam-bfd-interface:bfd-bind-int"+
                    "erface[oam-bfd-interface:bfd-sess-name=(/bfd:bfd/bfd:sessio"+
                    "ns/bfd:session[bfd:local-discriminator=current()]/bfd:name)"+
                    "]) = 0 and count(/oammgr:oammgr/oam-bfd-interface:bfd-bind-"+
                    "interfaces/oam-bfd-interface:bfd-bind-interface[oam-bfd-int"+
                    "erface:bfd-sess-name=(/bfd:bfd/bfd:sessions/bfd:session[bfd"+
                    ":local-discriminator-static-ipv6=current()]/bfd:name)]) = 0"+
                    " and count(/oammgr:oammgr/oam-bfd-interface:bfd-bind-interf"+
                    "aces/oam-bfd-interface:bfd-bind-interface[oam-bfd-interface"+
                    ":bfd-sess-name=(/bfd:bfd/bfd:sessions/bfd:session[bfd:local"+
                    "-discriminator-static-ldp-lsp=current()]/bfd:name)]) = 0 "+
                    "and count(/oammgr:oammgr/oam-bfd-interface:bfd-bind-interfa"+
                    "ces/oam-bfd-interface:bfd-bind-interface[oam-bfd-interface:"+
                    "bfd-sess-name=(/bfd:bfd/bfd:sessions/bfd:session[bfd-static"+
                    "-mpls-te:local-discriminator-static-te-lsp=current()]/bfd:n"+
                    "ame)]) = 0 and count(/oammgr:oammgr/oam-bfd-interface:bfd-b"+
                    "ind-interfaces/oam-bfd-interface:bfd-bind-interface[oam-bfd"+
                    "-interface:bfd-sess-name=(/bfd:bfd/bfd:sessions/bfd:session"+
                    "[bfd-static-mpls-te:local-discriminator-static-te-tunnel=cu"+
                    "rrent()]/bfd:name)]) = 0 and (/bfd:bfd/bfd:sessions/bfd:ses"+
                    "sion[bfd:local-discriminator-multicast-ipv4=current()] or "+
                    "/bfd:bfd/bfd:sessions/bfd:session[bfd:local-discriminator=c"+
                    "urrent()] or /bfd:bfd/bfd:sessions/bfd:session[bfd:local-di"+
                    "scriminator-static-ipv6=current()] or /bfd:bfd/bfd:sessions"+
                    "/bfd:session[bfd:local-discriminator-static-ldp-lsp=current"+
                    "()] or /bfd:bfd/bfd:sessions/bfd:session[bfd-static-mpls-te"+
                    ":local-discriminator-static-te-lsp=current()] or /bfd:bfd/b"+
                    "fd:sessions/bfd:session[bfd-static-mpls-te:local-discrimina"+
                    "tor-static-te-tunnel=current()])";
             }
           }
         }
       }
     }
   }
 }

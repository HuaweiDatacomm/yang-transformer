/*
Copyright (C) 2021 Huawei Technologies Co., Ltd. All rights reserved.
*/

 module huawei-vlan-fwd-deviations-OC-NE-X8X16 {
   namespace "urn:huawei:yang:huawei-vlan-fwd-deviations-OC-NE-X8X16";
   prefix "vlan-fwd-devs-OC-NE-X8X16";
   import huawei-vlan-fwd {
     prefix "vlan-fwd";
   }
   import huawei-ethernet {
     prefix "ethernet";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-vlan-fwd module.";
   revision "2021-05-07" {
     description
       "Initial revision.";
     reference
       "Huawei private.";
   }
   deviation "/ifm:ifm/ifm:interfaces/ifm:interface/ethernet:ethernet/ethernet:m"+
             "ain-interface/ethernet:l2-attribute/vlan-fwd:vlan-isolate-attribut"+
             "e/vlan-fwd:isolate-vlanlist" {
     deviate "add" {
       must "(../../ethernet:trunk-vlans) or (../../ethernet:pvid) or not(../iso"+
            "late-vlanlist)";
     }
   }
 }

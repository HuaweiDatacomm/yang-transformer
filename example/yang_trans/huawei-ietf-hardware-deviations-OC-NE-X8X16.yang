/*
Copyright (C) 2020 Huawei Technologies Co., Ltd. All rights reserved.
*/

 module huawei-ietf-hardware-deviations-OC-NE-X8X16 {
   namespace "urn:huawei:yang:huawei-ietf-hardware-deviations-OC-NE-X8X16";
   prefix "hardware-devs-OC-NE-X8X16";
   import ietf-hardware {
     prefix "hw";
   }
   organization
     "Huawei Technologies Co., Ltd.";
   contact
     "Huawei Industrial Base\nBantian, Longgang\nShenzhen 518129\nPeople's "+
     "Republic of China\nWebsite: http://www.huawei.com\nEmail: support@huawei.c"+
     "om";
   description
     "Configuration deviations of the driver file.";
   revision "2020-04-13" {
     description
       "Initial revision.";
     reference
       "Huawei private.";
   }
   deviation "/hw:hardware/hw:component" {
     deviate "replace" {
       config "false";
     }
   }
   deviation "/hw:hardware/hw:component/hw:name" {
     deviate "replace" {
       config "false";
     }
   }
   deviation "/hw:hardware/hw:component/hw:state" {
     deviate "replace" {
       config "false";
     }
   }
 }

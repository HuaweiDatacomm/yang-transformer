submodule openconfig-rib-bgp-attributes {
   belongs-to openconfig-rib-bgp {
     prefix "oc-rib-bgp";
   }
   import openconfig-extensions {
     prefix "oc-ext";
   }
   organization
     "OpenConfig working group";
   contact
     "OpenConfig working group\nwww.openconfig.net";
   description
     "This submodule contains common data definitions for BGP\nattributes for "+
     "use in BGP RIB tables.";
   oc-ext:openconfig-version "0.6.0";
   revision "2019-04-25" {
     description
       "Update last-modified timestamp to be expressed as nanoseconds\nsince the"+
       " Unix epoch.";
     reference
       "0.6.0";
   }
   revision "2019-04-16" {
     description
       "Rename the top-level BGP RIB container's name\nto RIB.";
     reference
       "0.5.0";
   }
   revision "2019-02-27" {
     description
       "Remove top-level BGP RIB container, and update list\nnames to be "+
       "compatible with path compression.";
     reference
       "0.4.0";
   }
   revision "2018-11-21" {
     description
       "Add OpenConfig module metadata extensions.";
     reference
       "0.3.1";
   }
   revision "2016-10-17" {
     description
       "OpenConfig BGP RIB refactor";
     reference
       "0.3.0";
   }
 }

/*
Copyright (C) 2019-2020 Huawei Technologies Co., Ltd. All rights reserved.
*/

 submodule huawei-segment-routing-type {
   belongs-to huawei-segment-routing {
     prefix "sr";
   }
   organization
     "Huawei Technologies Co., Ltd.";
   contact
     "Huawei Industrial Base\nBantian, Longgang\nShenzhen 518129\nPeople's "+
     "Republic of China\nWebsite: http://www.huawei.com\nEmail: support@huawei.c"+
     "om";
   description
     "Segment routing type defined file.";
   revision "2020-02-04" {
     description
       "Modify the description.";
     reference
       "Huawei private.";
   }
   revision "2019-04-04" {
     description
       "Initial revision.";
     reference
       "Huawei private.";
   }
   typedef bfd-type {
     type "enumeration" {
       enum "seamless-bfd" {
         value "1";
         description
           "The BFD type is seamless BFD.";
       }
       enum "bfd" {
         value "2";
         description
           "The BFD type is BFD.";
       }
     }
     description
       "Segment routing bfd session type.";
   }
   typedef segr-lsp-type {
     type "enumeration" {
       enum "ingress" {
         value "1";
         description
           "Ingress.";
       }
       enum "transit" {
         value "2";
         description
           "Transit.";
       }
       enum "ingress-transit" {
         value "3";
         description
           "Ingress and transit.";
       }
       enum "egress" {
         value "4";
         description
           "Egress.";
       }
       enum "bud" {
         value "5";
         description
           "Bud.";
       }
     }
     description
       "LSR type.";
   }
 }

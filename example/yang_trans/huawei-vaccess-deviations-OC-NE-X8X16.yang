/*
Copyright (C) 2020 Huawei Technologies Co., Ltd. All rights reserved.
*/

 module huawei-vaccess-deviations-OC-NE-X8X16 {
   namespace "urn:huawei:yang:huawei-vaccess-deviations-OC-NE-X8X16";
   prefix "vaccess-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Specifies the virtual access model.";
   revision "2020-03-14" {
     description
       "Init revision.";
     reference
       "Huawei private.";
   }
 }

/*
Copyright (C) 2020 Huawei Technologies Co., Ltd. All rights reserved.
*/

 module huawei-acl-ucl-deviations-OC-NE-X8X16 {
   yang-version "1";
   namespace "urn:huawei:yang:huawei-acl-ucl-deviations-OC-NE-X8X16";
   prefix "acl-ucl-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Access Control List (ACL). An ACL is used to identify and select data "+
     "packets through packet attributes. For example, applying an ACL in the "+
     "firewall can either permit or discard data packets. Applying an ACL in "+
     "IPsec can encrypt data packets that match ACL rules and forward those that"+
     " do not match any ACL rule.";
   revision "2020-02-20" {
     description
       "Initial revision.";
     reference
       "Huawei private.";
   }
 }

/*
Copyright (C) 2019 Huawei Technologies Co., Ltd. All rights reserved.
*/

 module huawei-notifications-deviations-OC-NE-X8X16 {
   namespace "urn:huawei:yang:huawei-notifications-deviations-OC-NE-X8X16";
   prefix "ncEvent-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Notifications deviation file.";
   revision "2019-06-17" {
     description
       "Initial revision.";
     reference
       "Huawei private.";
   }
 }

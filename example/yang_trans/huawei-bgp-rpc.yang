/*
Copyright (C) 2020 Huawei Technologies Co., Ltd. All rights reserved.
*/

 module huawei-bgp-rpc {
   yang-version "1";
   namespace "urn:huawei:yang:huawei-bgp-rpc";
   prefix "bgp-rpc";
   import huawei-network-instance {
     prefix "ni";
   }
   import huawei-extension {
     prefix "ext";
   }
   import huawei-bgp {
     prefix "bgp";
   }
   import ietf-inet-types {
     prefix "inet";
   }
   import ietf-yang-types {
     prefix "yang";
   }
   organization
     "Huawei Technologies Co., Ltd.";
   contact
     "Huawei Industrial Base\nBantian, Longgang\nShenzhen 518129\nPeople's "+
     "Republic of China\nWebsite: http://www.huawei.com\nEmail: support@huawei.c"+
     "om";
   description
     "BGP rpc configuration.";
   revision "2020-11-04" {
     description
       "Initial revision.";
     reference
       "Huawei private.";
   }
   ext:task-name "bgp";
   rpc reset-base-process-bgp-af {
     ext:node-ref "/ni:network-instance/ni:instances/ni:instance/bgp:bgp/bgp:bas"+
                  "e-process/bgp:afs/bgp:af";
     description
       "Reset BGP address family operation.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 labeled address family.";
           }
           enum "ipv6uni" {
             value "5";
             description
               "IPv6 unicast address family.";
           }
           enum "ipv6vpn" {
             value "6";
             description
               "IPv6 VPN address family.";
           }
           enum "ipv4flow" {
             value "7";
             description
               "IPv4 flow address family.";
           }
           enum "l2vpnad" {
             value "8";
             description
               "L2VPN-AD address family.";
           }
           enum "evpn" {
             value "9";
             description
               "EVPN address family.";
           }
           enum "mvpn" {
             value "10";
             description
               "IPv4 MVPN address family.";
           }
           enum "vpntarget" {
             value "11";
             description
               "VPN target address family.";
           }
           enum "ipv4vpnmcast" {
             value "12";
             description
               "IPv4 VPN multicast address family.";
           }
           enum "ls" {
             value "13";
             description
               "Link-state address family.";
           }
           enum "mdt" {
             value "14";
             description
               "IPv4 MDT address family.";
           }
           enum "ipv6flow" {
             value "15";
             description
               "IPv6 flow address family.";
           }
           enum "mvpnv6" {
             value "16";
             description
               "IPv6 MVPN address family.";
           }
           enum "vpnv4flow" {
             value "17";
             description
               "VPNv4 flow address family.";
           }
           enum "vpnv6flow" {
             value "18";
             description
               "VPNv6 flow address family.";
           }
           enum "rpd" {
             value "19";
             description
               "RPD address family.";
           }
           enum "ipv4srpolicy" {
             value "20";
             description
               "IPv4-family SR-Policy address family.";
           }
           enum "ipv6srpolicy" {
             value "21";
             description
               "IPv6-family SR-Policy address family.";
           }
         }
         mandatory "true";
         description
           "Address family type of a BGP instance.";
       }
     }
   }
   rpc reset-base-process-bgp-all {
     ext:node-ref "/ni:network-instance/ni:instances/ni:instance/bgp:bgp/bgp:bas"+
                  "e-process";
     description
       "Reset BGP operation.";
   }
   rpc reset-base-process-bgp-peer-af {
     ext:node-ref "/ni:network-instance/ni:instances/ni:instance/bgp:bgp/bgp:bas"+
                  "e-process/bgp:peers/bgp:peer/bgp:afs/bgp:af";
     description
       "Reset the BGP peer operation.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 labeled address family.";
           }
           enum "ipv6uni" {
             value "5";
             description
               "IPv6 unicast address family.";
           }
           enum "ipv6vpn" {
             value "6";
             description
               "IPv6 VPN address family.";
           }
           enum "ipv4flow" {
             value "7";
             description
               "IPv4 flow address family.";
           }
           enum "l2vpnad" {
             value "8";
             description
               "L2VPN-AD address family.";
           }
           enum "evpn" {
             value "9";
             description
               "EVPN address family.";
           }
           enum "mvpn" {
             value "10";
             description
               "IPv4 MVPN address family.";
           }
           enum "vpntarget" {
             value "11";
             description
               "VPN target address family.";
           }
           enum "ipv4vpnmcast" {
             value "12";
             description
               "IPv4 VPN multicast address family.";
           }
           enum "ls" {
             value "13";
             description
               "Link-state address family.";
           }
           enum "mdt" {
             value "14";
             description
               "IPv4 MDT address family.";
           }
           enum "ipv6flow" {
             value "15";
             description
               "IPv6 flow address family.";
           }
           enum "mvpnv6" {
             value "16";
             description
               "IPv6 MVPN address family.";
           }
           enum "vpnv4flow" {
             value "17";
             description
               "VPNv4 flow address family.";
           }
           enum "vpnv6flow" {
             value "18";
             description
               "VPNv6 flow address family.";
           }
           enum "rpd" {
             value "19";
             description
               "RPD address family.";
           }
           enum "ipv4srpolicy" {
             value "20";
             description
               "IPv4-family SR-Policy address family.";
           }
           enum "ipv6srpolicy" {
             value "21";
             description
               "IPv6-family SR-Policy address family.";
           }
         }
         mandatory "true";
         description
           "Address family type of a BGP instance.";
       }
       leaf remote-address {
         type "inet:ip-address-no-zone";
         mandatory "true";
         description
           "Peer address.";
       }
     }
   }
   rpc reset-base-process-bgp-peer-as {
     ext:node-ref "/ni:network-instance/ni:instances/ni:instance/bgp:bgp/bgp:bas"+
                  "e-process/bgp:peers/bgp:peer/bgp:afs/bgp:af";
     description
       "Reset the BGP AS number.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 labeled address family.";
           }
           enum "ipv6uni" {
             value "5";
             description
               "IPv6 unicast address family.";
           }
           enum "ipv6vpn" {
             value "6";
             description
               "IPv6 VPN address family.";
           }
           enum "ipv4flow" {
             value "7";
             description
               "IPv4 flow address family.";
           }
           enum "l2vpnad" {
             value "8";
             description
               "L2VPN-AD address family.";
           }
           enum "evpn" {
             value "9";
             description
               "EVPN address family.";
           }
           enum "mvpn" {
             value "10";
             description
               "IPv4 MVPN address family.";
           }
           enum "vpntarget" {
             value "11";
             description
               "VPN target address family.";
           }
           enum "ipv4vpnmcast" {
             value "12";
             description
               "IPv4 VPN multicast address family.";
           }
           enum "ls" {
             value "13";
             description
               "Link-state address family.";
           }
           enum "mdt" {
             value "14";
             description
               "IPv4 MDT address family.";
           }
           enum "ipv6flow" {
             value "15";
             description
               "IPv6 flow address family.";
           }
           enum "mvpnv6" {
             value "16";
             description
               "IPv6 MVPN address family.";
           }
           enum "vpnv4flow" {
             value "17";
             description
               "VPNv4 flow address family.";
           }
           enum "vpnv6flow" {
             value "18";
             description
               "VPNv6 flow address family.";
           }
           enum "rpd" {
             value "19";
             description
               "RPD address family.";
           }
           enum "ipv4srpolicy" {
             value "20";
             description
               "IPv4-family SR-Policy address family.";
           }
           enum "ipv6srpolicy" {
             value "21";
             description
               "IPv6-family SR-Policy address family.";
           }
         }
         mandatory "true";
         description
           "Address family type of a BGP instance.";
       }
       leaf remote-as {
         type "bgp:as-number-validate";
         mandatory "true";
         description
           "AS number of a peer.";
       }
     }
   }
   rpc reset-base-process-bgp-peer-type {
     ext:node-ref "/ni:network-instance/ni:instances/ni:instance/bgp:bgp/bgp:bas"+
                  "e-process/bgp:peers/bgp:peer";
     description
       "Reset the BGP peer operation.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 labeled address family.";
           }
           enum "ipv6uni" {
             value "5";
             description
               "IPv6 unicast address family.";
           }
           enum "ipv6vpn" {
             value "6";
             description
               "IPv6 VPN address family.";
           }
           enum "ipv4flow" {
             value "7";
             description
               "IPv4 flow address family.";
           }
           enum "l2vpnad" {
             value "8";
             description
               "L2VPN-AD address family.";
           }
           enum "evpn" {
             value "9";
             description
               "EVPN address family.";
           }
           enum "mvpn" {
             value "10";
             description
               "IPv4 MVPN address family.";
           }
           enum "vpntarget" {
             value "11";
             description
               "VPN target address family.";
           }
           enum "ipv4vpnmcast" {
             value "12";
             description
               "IPv4 VPN multicast address family.";
           }
           enum "ls" {
             value "13";
             description
               "Link-state address family.";
           }
           enum "mdt" {
             value "14";
             description
               "IPv4 MDT address family.";
           }
           enum "ipv6flow" {
             value "15";
             description
               "IPv6 flow address family.";
           }
           enum "mvpnv6" {
             value "16";
             description
               "IPv6 MVPN address family.";
           }
           enum "vpnv4flow" {
             value "17";
             description
               "VPNv4 flow address family.";
           }
           enum "vpnv6flow" {
             value "18";
             description
               "VPNv6 flow address family.";
           }
           enum "rpd" {
             value "19";
             description
               "RPD address family.";
           }
           enum "ipv4srpolicy" {
             value "20";
             description
               "IPv4-family SR-Policy address family.";
           }
           enum "ipv6srpolicy" {
             value "21";
             description
               "IPv6-family SR-Policy address family.";
           }
         }
         mandatory "true";
         description
           "Address family type of a BGP instance.";
       }
       leaf peer-type {
         type "bgp:group-type";
         mandatory "true";
         description
           "Peer type.";
       }
     }
   }
   rpc reset-base-process-bgp-group-af {
     ext:node-ref "/ni:network-instance/ni:instances/ni:instance/bgp:bgp/bgp:bas"+
                  "e-process/bgp:peer-groups/bgp:peer-group/bgp:afs/bgp:af";
     description
       "Reset the BGP group operation.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 Labeled Address Family.";
           }
           enum "ipv6uni" {
             value "5";
             description
               "IPv6 unicast address family.";
           }
           enum "ipv6vpn" {
             value "6";
             description
               "IPv6 VPN address family.";
           }
           enum "l2vpnad" {
             value "8";
             description
               "L2VPN-AD Address Family.";
           }
           enum "evpn" {
             value "9";
             description
               "EVPN address family.";
           }
           enum "mvpn" {
             value "10";
             description
               "IPv4 MVPN address family.";
           }
           enum "vpntarget" {
             value "11";
             description
               "Vpn Target Address Family.";
           }
           enum "ipv4vpnmcast" {
             value "12";
             description
               "IPv4 VPN Multicast Address Family.";
           }
           enum "ls" {
             value "13";
             description
               "Link-state Address Family.";
           }
           enum "mdt" {
             value "14";
             description
               "IPv4 MDT Address Family.";
           }
           enum "mvpnv6" {
             value "16";
             description
               "IPv6 MVPN address family.";
           }
         }
         mandatory "true";
         description
           "Address family type of a BGP instance.";
       }
       leaf group-name {
         type "leafref" {
           path "/ni:network-instance/ni:instances/ni:instance/bgp:bgp/bgp:base-"+
                "process/bgp:peer-groups/bgp:peer-group/bgp:name";
         }
         mandatory "true";
         description
           "Specify the name of a peer group.";
       }
     }
   }
   rpc refresh-base-process-bgp-af-direction {
     ext:node-ref "/ni:network-instance/ni:instances/ni:instance/bgp:bgp/bgp:bas"+
                  "e-process/bgp:afs/bgp:af";
     description
       "Soft reset BGP connections.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 labeled address family.";
           }
           enum "ipv6uni" {
             value "5";
             description
               "IPv6 unicast address family.";
           }
           enum "ipv6vpn" {
             value "6";
             description
               "IPv6 VPN address family.";
           }
           enum "ipv4flow" {
             value "7";
             description
               "IPv4 flow address family.";
           }
           enum "l2vpnad" {
             value "8";
             description
               "L2VPN-AD address family.";
           }
           enum "evpn" {
             value "9";
             description
               "EVPN address family.";
           }
           enum "mvpn" {
             value "10";
             description
               "IPv4 MVPN address family.";
           }
           enum "vpntarget" {
             value "11";
             description
               "VPN target address family.";
           }
           enum "ipv4vpnmcast" {
             value "12";
             description
               "IPv4 VPN multicast address family.";
           }
           enum "ls" {
             value "13";
             description
               "Link-state address family.";
           }
           enum "mdt" {
             value "14";
             description
               "IPv4 MDT address family.";
           }
           enum "ipv6flow" {
             value "15";
             description
               "IPv6 flow address family.";
           }
           enum "mvpnv6" {
             value "16";
             description
               "IPv6 MVPN address family.";
           }
           enum "vpnv4flow" {
             value "17";
             description
               "VPNv4 flow address family.";
           }
           enum "vpnv6flow" {
             value "18";
             description
               "VPNv6 flow address family.";
           }
           enum "rpd" {
             value "19";
             description
               "RPD address family.";
           }
           enum "ipv4srpolicy" {
             value "20";
             description
               "IPv4-family SR-Policy address family.";
           }
           enum "ipv6srpolicy" {
             value "21";
             description
               "IPv6-family SR-Policy address family.";
           }
         }
         mandatory "true";
         description
           "Address family type of a BGP instance.";
       }
       leaf direction {
         type "bgp:direction-type";
         mandatory "true";
         description
           "Soft reset BGP connections in the inbound/outbound direction.";
       }
     }
   }
   rpc refresh-base-process-bgp-peer-af-direction {
     ext:node-ref "/ni:network-instance/ni:instances/ni:instance/bgp:bgp/bgp:bas"+
                  "e-process/bgp:peers/bgp:peer/bgp:afs/bgp:af";
     description
       "Soft reset a peer with a specified peer address.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 labeled address family.";
           }
           enum "ipv6uni" {
             value "5";
             description
               "IPv6 unicast address family.";
           }
           enum "ipv6vpn" {
             value "6";
             description
               "IPv6 VPN address family.";
           }
           enum "ipv4flow" {
             value "7";
             description
               "IPv4 flow address family.";
           }
           enum "l2vpnad" {
             value "8";
             description
               "L2VPN-AD address family.";
           }
           enum "evpn" {
             value "9";
             description
               "EVPN address family.";
           }
           enum "mvpn" {
             value "10";
             description
               "IPv4 MVPN address family.";
           }
           enum "vpntarget" {
             value "11";
             description
               "VPN target address family.";
           }
           enum "ipv4vpnmcast" {
             value "12";
             description
               "IPv4 VPN multicast address family.";
           }
           enum "ls" {
             value "13";
             description
               "Link-state address family.";
           }
           enum "mdt" {
             value "14";
             description
               "IPv4 MDT address family.";
           }
           enum "ipv6flow" {
             value "15";
             description
               "IPv6 flow address family.";
           }
           enum "mvpnv6" {
             value "16";
             description
               "IPv6 MVPN address family.";
           }
           enum "vpnv4flow" {
             value "17";
             description
               "VPNv4 flow address family.";
           }
           enum "vpnv6flow" {
             value "18";
             description
               "VPNv6 flow address family.";
           }
           enum "rpd" {
             value "19";
             description
               "RPD address family.";
           }
           enum "ipv4srpolicy" {
             value "20";
             description
               "IPv4-family SR-Policy address family.";
           }
           enum "ipv6srpolicy" {
             value "21";
             description
               "IPv6-family SR-Policy address family.";
           }
         }
         mandatory "true";
         description
           "Address family type of a BGP instance.";
       }
       leaf remote-address {
         type "inet:ip-address-no-zone";
         mandatory "true";
         description
           "Peer address.";
       }
       leaf direction {
         type "bgp:direction-type";
         mandatory "true";
         description
           "Soft reset BGP connections in the inbound/outbound direction.";
       }
     }
   }
   rpc refresh-base-process-bgp-peer-type-direction {
     ext:node-ref "/ni:network-instance/ni:instances/ni:instance/bgp:bgp/bgp:bas"+
                  "e-process/bgp:peers/bgp:peer/bgp:afs/bgp:af";
     description
       "Soft reset peers with a specified peer type.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 labeled address family.";
           }
           enum "ipv6uni" {
             value "5";
             description
               "IPv6 unicast address family.";
           }
           enum "ipv6vpn" {
             value "6";
             description
               "IPv6 VPN address family.";
           }
           enum "ipv4flow" {
             value "7";
             description
               "IPv4 flow address family.";
           }
           enum "l2vpnad" {
             value "8";
             description
               "L2VPN-AD address family.";
           }
           enum "evpn" {
             value "9";
             description
               "EVPN address family.";
           }
           enum "mvpn" {
             value "10";
             description
               "IPv4 MVPN address family.";
           }
           enum "vpntarget" {
             value "11";
             description
               "VPN target address family.";
           }
           enum "ipv4vpnmcast" {
             value "12";
             description
               "IPv4 VPN multicast address family.";
           }
           enum "ls" {
             value "13";
             description
               "Link-state address family.";
           }
           enum "mdt" {
             value "14";
             description
               "IPv4 MDT address family.";
           }
           enum "ipv6flow" {
             value "15";
             description
               "IPv6 flow address family.";
           }
           enum "mvpnv6" {
             value "16";
             description
               "IPv6 MVPN address family.";
           }
           enum "vpnv4flow" {
             value "17";
             description
               "VPNv4 flow address family.";
           }
           enum "vpnv6flow" {
             value "18";
             description
               "VPNv6 flow address family.";
           }
           enum "rpd" {
             value "19";
             description
               "RPD address family.";
           }
           enum "ipv4srpolicy" {
             value "20";
             description
               "IPv4-family SR-Policy address family.";
           }
           enum "ipv6srpolicy" {
             value "21";
             description
               "IPv6-family SR-Policy address family.";
           }
         }
         mandatory "true";
         description
           "Address family type of a BGP instance.";
       }
       leaf peer-type {
         type "bgp:group-type";
         mandatory "true";
         description
           "Peer type.";
       }
       leaf direction {
         type "bgp:direction-type";
         mandatory "true";
         description
           "Soft reset BGP connections in the inbound/outbound direction.";
       }
     }
   }
   rpc refresh-base-process-bgp-group-af {
     ext:node-ref "/ni:network-instance/ni:instances/ni:instance/bgp:bgp/bgp:bas"+
                  "e-process/bgp:peer-groups/bgp:peer-group/bgp:afs/bgp:af";
     description
       "Soft reset a peer group with a specified group name.";
     input {
       leaf vrf-name {
         type "leafref" {
           path "/ni:network-instance/ni:instances/ni:instance/ni:name";
         }
         mandatory "true";
         description
           "VPN name of a BGP instance.";
       }
       leaf address-family {
         type "enumeration" {
           enum "ipv4uni" {
             value "1";
             description
               "IPv4 unicast address family.";
           }
           enum "ipv4multi" {
             value "2";
             description
               "IPv4 multicast address family.";
           }
           enum "ipv4vpn" {
             value "3";
             description
               "IPv4 VPN address family.";
           }
           enum "ipv4labeluni" {
             value "4";
             description
               "IPv4 Labeled Address Family.";
           }
           enum "ipv6uni" {
             value "5";
             description
               "IPv6 unicast address family.";
           }
           enum "ipv6vpn" {
             value "6";
             description
               "IPv6 VPN address family.";
           }
           enum "l2vpnad" {
             value "8";
             description
               "L2VPN-AD Address Family.";
           }
           enum "evpn" {
             value "9";
             description
               "EVPN address family.";
           }
           enum "mvpn" {
             value "10";
             description
               "IPv4 MVPN address family.";
           }
           enum "vpntarget" {
             value "11";
             description
               "Vpn Target Address Family.";
           }
           enum "ipv4vpnmcast" {
             value "12";
             description
               "IPv4 VPN Multicast Address Family.";
           }
           enum "ls" {
             value "13";
             description
               "Link-state Address Family.";
           }
           enum "mdt" {
             value "14";
             description
               "IPv4 MDT Address Family.";
           }
           enum "mvpnv6" {
             value "16";
             description
               "IPv6 MVPN address family.";
           }
         }
         mandatory "true";
         description
           "Address family type of a BGP instance.";
       }
       leaf group-name {
         type "leafref" {
           path "/ni:network-instance/ni:instances/ni:instance/bgp:bgp/bgp:base-"+
                "process/bgp:peer-groups/bgp:peer-group/bgp:name";
         }
         mandatory "true";
         description
           "Specify the name of a peer group.";
       }
       leaf direction {
         type "bgp:direction-type";
         mandatory "true";
         description
           "Soft reset BGP connections in the inbound/outbound direction.";
       }
     }
   }
   rpc diagnose-base-process-peer-log-info {
     ext:node-ref "/ni:network-instance/ni:instances/ni:instance/bgp:bgp/bgp:bas"+
                  "e-process/bgp:peers/bgp:peer/bgp:afs/bgp:af";
     description
       "Display BGP peer log information.";
     input {
       leaf vrf-name {
         type "leafref" {
           path "/ni:network-instance/ni:instances/ni:instance/ni:name";
         }
         mandatory "true";
         description
           "VPN name of a BGP instance.";
       }
       leaf address-family {
         type "bgp:af-type";
         mandatory "true";
         description
           "Address family type of a BGP instance.";
       }
       leaf remote-address {
         type "inet:ip-address-no-zone";
         mandatory "true";
         description
           "Peer address.";
       }
     }
     output {
       container log-infos {
         description
           "List of BGP peer log information.";
         list log-info {
           key "index";
           description
             "BGP peer log information.";
           leaf index {
             type "uint32";
             description
               "Index of peer log information.";
           }
           leaf state-event {
             type "string" {
               length "1..19";
             }
             description
               "Status of a peer when an event occurs.";
           }
           leaf error-code {
             type "string" {
               length "1..47";
             }
             description
               "Error code that triggers an event.";
           }
           leaf error-sub-code {
             type "string" {
               length "1..47";
             }
             description
               "Error sub-code that triggers an event.";
           }
           leaf notification {
             type "string" {
               length "1..39";
             }
             description
               "Sent or received notification messages.";
           }
           leaf date-time {
             type "yang:date-and-time";
             description
               "Time when the log information was recorded.";
           }
         }
       }
     }
   }
   rpc diagnose-base-process-group-log-info {
     ext:node-ref "/ni:network-instance/ni:instances/ni:instance/bgp:bgp/bgp:bas"+
                  "e-process/bgp:peer-groups/bgp:peer-group/bgp:afs/bgp:af";
     description
       "BGP group log information.";
     input {
       leaf vrf-name {
         type "leafref" {
           path "/ni:network-instance/ni:instances/ni:instance/ni:name";
         }
         mandatory "true";
         description
           "VPN name of a BGP instance.";
       }
       leaf address-family {
         type "bgp:group-af-type";
         mandatory "true";
         description
           "Address family type of a BGP instance.";
       }
       leaf group-name {
         type "leafref" {
           path "/ni:network-instance/ni:instances/ni:instance/bgp:bgp/bgp:base-"+
                "process/bgp:peer-groups/bgp:peer-group/bgp:name";
         }
         mandatory "true";
         description
           "Specify the name of a peer group.";
       }
     }
     output {
       container log-infos {
         description
           "List of BGP group log information.";
         list log-info {
           key "remote-address index";
           description
             "BGP group log information.";
           leaf remote-address {
             type "inet:ip-address-no-zone";
             description
               "Peer address.";
           }
           leaf index {
             type "uint32";
             description
               "Index of peer log information.";
           }
           leaf state-event {
             type "string" {
               length "1..19";
             }
             description
               "Status of a peer when an event occurs.";
           }
           leaf error-code {
             type "string" {
               length "1..47";
             }
             description
               "Error code that triggers an event.";
           }
           leaf error-sub-code {
             type "string" {
               length "1..47";
             }
             description
               "Error sub-code that triggers an event.";
           }
           leaf notification {
             type "string" {
               length "1..39";
             }
             description
               "Sent or received notification messages.";
           }
           leaf date-time {
             type "yang:date-and-time";
             description
               "Time when the log information was recorded.";
           }
         }
       }
     }
   }
   rpc clear-base-process-bgp-loop-detect-alarm {
     ext:node-ref "/bgp:bgp/bgp:base-process/bgp:route-loop-detect-enable";
     description
       "Clear BGP route loop-detect alarm.";
   }
 }

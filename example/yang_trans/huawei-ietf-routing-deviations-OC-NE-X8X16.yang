/*
Copyright (C) 2021 Huawei Technologies Co., Ltd. All rights reserved.
*/

 module huawei-ietf-routing-deviations-OC-NE-X8X16 {
   yang-version "1.1";
   namespace "urn:huawei:yang:huawei-ietf-routing-deviations-OC-NE-X8X16";
   prefix "rt-devs-OC-NE-X8X16";
   import ietf-routing {
     prefix "rt";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Deviations for ietf-network model.";
   revision "2021-01-15" {
     description
       "Initial revision.";
     reference
       "Huawei private.";
   }
   deviation "/rt:routing/rt:control-plane-protocols/rt:control-plane-protocol/r"+
             "t:name" {
     deviate "replace" {
       type "string" {
         length "1..10";
       }
     }
   }
   deviation "/rt:routing/rt:control-plane-protocols/rt:control-plane-protocol/r"+
             "t:name" {
     deviate "add" {
       must "((../type='rt:static' or ../type='rt:direct') and ../name='default'"+
            ")";
     }
   }
   ext:deviation-ext "/rt:routing/rt:control-plane-protocols/rt:control-plane-pr"+
                     "otocol" {
     ext:deviate-ext "add" {
       ext:generated-by "system" {
         when "./name = 'default'";
         description
           "The default protocol is generated automatically.";
       }
     }
   }
 }

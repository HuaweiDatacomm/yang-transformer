submodule openconfig-isis-routing {
   belongs-to openconfig-isis {
     prefix "oc-isis";
   }
   import openconfig-extensions {
     prefix "oc-ext";
   }
   organization
     "OpenConfig working group";
   contact
     "OpenConfig working group\nwww.openconfig.net";
   description
     "This module describes YANG model for ISIS Routing";
   oc-ext:openconfig-version "0.4.2";
   revision "2018-11-21" {
     description
       "Add OpenConfig module metadata extensions.";
     reference
       "0.4.2";
   }
   revision "2018-06-05" {
     description
       "Fix bugs in when statements.";
     reference
       "0.4.1";
   }
   revision "2018-05-14" {
     description
       "Update LSDB model to correct Extended IS reach TLV\nbug. This change is "+
       "backwards incompatible due to\nadding an additional level of hierarchy "+
       "to support\nmultiple instances of the TLV.";
     reference
       "0.4.0";
   }
   revision "2017-07-26" {
     description
       "Update LSDB and fix bugs.";
     reference
       "0.3.2";
   }
   revision "2017-05-15" {
     description
       "Refactor LSDB.";
     reference
       "0.3.0";
   }
   revision "2017-01-13" {
     description
       "Remove top-level /isis container";
     reference
       "0.2.1";
   }
   revision "2016-12-15" {
     description
       "Add segment routing to IS-IS module";
     reference
       "0.2.0";
   }
   revision "2016-10-18" {
     description
       "Initial revision of IS-IS models.";
     reference
       "0.1.0";
   }
 }

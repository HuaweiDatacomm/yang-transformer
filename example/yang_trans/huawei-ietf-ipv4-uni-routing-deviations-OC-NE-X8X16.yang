/*
Copyright (C) 2021 Huawei Technologies Co., Ltd. All rights reserved.
*/

 module huawei-ietf-ipv4-uni-routing-deviations-OC-NE-X8X16 {
   yang-version "1.1";
   namespace "urn:huawei:yang:huawei-ietf-ipv4-uni-routing-deviations-OC-NE-X8X1"+
             "6";
   prefix "v4ur-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Deviations for ietf-network model.";
   revision "2021-01-15" {
     description
       "Initial revision.";
     reference
       "Huawei private.";
   }
 }

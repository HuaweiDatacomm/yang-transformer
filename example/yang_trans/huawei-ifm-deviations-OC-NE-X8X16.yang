/*
Copyright (C) 2019 Huawei Technologies Co., Ltd. All rights reserved.
*/

 module huawei-ifm-deviations-OC-NE-X8X16 {
   namespace "urn:huawei:yang:huawei-ifm-deviations-OC-NE-X8X16";
   prefix "ifm-devs-OC-NE-X8X16";
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "Common interface management, which includes the public configuration of "+
     "interfaces.";
   revision "2019-05-06" {
     description
       "Init revision.";
     reference
       "Huawei private.";
   }
   deviation "/ifm:reset-if-counters-by-type/ifm:input/ifm:if-type" {
     deviate "add" {
       must "../ifm:if-type='Ethernet' or ../ifm:if-type ='GigabitEthernet' or "+
            "../ifm:if-type='Eth-Trunk' or ../ifm:if-type='Ip-Trunk' or "+
            "../ifm:if-type='Pos' or ../ifm:if-type='Tunnel' or ../ifm:if-type='"+
            "NULL' or ../ifm:if-type='LoopBack' or ../ifm:if-type='Vlanif' or "+
            "../ifm:if-type='100GE' or ../ifm:if-type='40GE' or ../ifm:if-type='"+
            "25GE' or ../ifm:if-type='MTunnel' or ../ifm:if-type='Cpos' or "+
            "../ifm:if-type='E1' or ../ifm:if-type='Serial' or ../ifm:if-type='M"+
            "p-group' or ../ifm:if-type='Virtual-Ethernet' or ../ifm:if-type='Im"+
            "a-group' or ../ifm:if-type='Remote-Ap' or ../ifm:if-type='VBridge' "+
            "or ../ifm:if-type='Atm-Bundle' or ../ifm:if-type='Lmpif' or "+
            "../ifm:if-type='T1' or ../ifm:if-type='T3' or ../ifm:if-type='Globa"+
            "l-VE' or ../ifm:if-type='Vbdif' or ../ifm:if-type='E3' or "+
            "../ifm:if-type='Pos-Trunk' or ../ifm:if-type='Trunk-Serial' or "+
            "../ifm:if-type='Global-Ima-Group' or ../ifm:if-type='Global-Mp-Grou"+
            "p' or ../ifm:if-type='Nve' or ../ifm:if-type='Wdm' or ../ifm:if-typ"+
            "e='Virtual-Template' or ../ifm:if-type='XGigabitEthernet' or "+
            "../ifm:if-type='FlexE' or ../ifm:if-type='50|100GE' or ../ifm:if-ty"+
            "pe='50GE' or ../ifm:if-type='PW-VE' or ../ifm:if-type='400GE' or "+
            "../ifm:if-type='HP-GE'";
     }
   }
   deviation "/ifm:reset-if-mib-counters-by-type/ifm:input/ifm:if-type" {
     deviate "add" {
       must "../ifm:if-type='Ethernet' or ../ifm:if-type ='GigabitEthernet' or "+
            "../ifm:if-type='Eth-Trunk' or ../ifm:if-type='Ip-Trunk' or "+
            "../ifm:if-type='Pos' or ../ifm:if-type='Tunnel' or ../ifm:if-type='"+
            "NULL' or ../ifm:if-type='LoopBack' or ../ifm:if-type='Vlanif' or "+
            "../ifm:if-type='100GE' or ../ifm:if-type='40GE' or ../ifm:if-type='"+
            "25GE' or ../ifm:if-type='MTunnel' or ../ifm:if-type='Serial' or "+
            "../ifm:if-type='Mp-group' or ../ifm:if-type='Virtual-Ethernet' or "+
            "../ifm:if-type='Ima-group' or ../ifm:if-type='Remote-Ap' or "+
            "../ifm:if-type='VBridge' or ../ifm:if-type='Atm-Bundle' or "+
            "../ifm:if-type='Lmpif' or ../ifm:if-type='T3' or ../ifm:if-type='Gl"+
            "obal-VE' or ../ifm:if-type='Vbdif' or ../ifm:if-type='Pos-Trunk' or"+
            " ../ifm:if-type='Trunk-Serial' or ../ifm:if-type='Global-Ima-Group'"+
            " or ../ifm:if-type='Global-Mp-Group' or ../ifm:if-type='Nve' or "+
            "../ifm:if-type='Virtual-Template' or ../ifm:if-type='XGigabitEthern"+
            "et' or ../ifm:if-type='FlexE' or ../ifm:if-type='50|100GE' or "+
            "../ifm:if-type='50GE' or ../ifm:if-type='PW-VE' or ../ifm:if-type='"+
            "400GE' or ../ifm:if-type='HP-GE'";
     }
   }
   deviation "/ifm:ifm/ifm:interfaces/ifm:interface/ifm:trap-threshold/ifm:input"+
             "-rising-rate" {
     deviate "replace" {
       default "90";
     }
   }
   deviation "/ifm:ifm/ifm:interfaces/ifm:interface/ifm:trap-threshold/ifm:input"+
             "-resume-rate" {
     deviate "replace" {
       default "80";
     }
   }
   deviation "/ifm:ifm/ifm:interfaces/ifm:interface/ifm:trap-threshold/ifm:outpu"+
             "t-rising-rate" {
     deviate "replace" {
       default "90";
     }
   }
   deviation "/ifm:ifm/ifm:interfaces/ifm:interface/ifm:trap-threshold/ifm:outpu"+
             "t-resume-rate" {
     deviate "replace" {
       default "80";
     }
   }
 }

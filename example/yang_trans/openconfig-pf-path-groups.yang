submodule openconfig-pf-path-groups {
   belongs-to openconfig-policy-forwarding {
     prefix "oc-pf";
   }
   import openconfig-extensions {
     prefix "oc-ext";
   }
   organization
     "OpenConfig working group";
   contact
     "OpenConfig working group\nwww.openconfig.net";
   description
     "This submodule contains configuration and operational state\nrelating to "+
     "path-selection-groups which are used to group\nforwarding entities "+
     "together to be used as policy forwarding\ntargets.";
   oc-ext:openconfig-version "0.2.1";
   revision "2018-11-21" {
     description
       "Add OpenConfig module metadata extensions.";
     reference
       "0.2.1";
   }
   revision "2017-06-21" {
     description
       "Amend policy forwarding model based on ACL changes.";
     reference
       "0.2.0";
   }
   revision "2017-02-28" {
     description
       "Initial public release of policy forwarding.";
     reference
       "0.1.0";
   }
   revision "2016-11-08" {
     description
       "Initial revision";
     reference
       "0.0.1";
   }
 }

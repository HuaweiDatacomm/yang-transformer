/*
Copyright (C) 2019 Huawei Technologies Co., Ltd. All rights reserved.
*/

 module huawei-devm-deviations-OC-NE-X8X16 {
   namespace "urn:huawei:yang:huawei-devm-deviations-OC-NE-X8X16";
   prefix "devm-devs-OC-NE-X8X16";
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "Global Configuration.";
   revision "2019-04-03" {
     description
       "Initial revision.";
     reference
       "Huawei private.";
   }
   deviation "/devm:devm/devm:ports/devm:port/devm:hard-type" {
     deviate "replace" {
       type "string" {
         length "1..32";
       }
     }
   }
 }

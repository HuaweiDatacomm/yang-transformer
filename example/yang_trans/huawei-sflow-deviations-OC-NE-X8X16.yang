/*
Copyright (C) 2020 Huawei Technologies Co., Ltd. All rights reserved.
*/

 module huawei-sflow-deviations-OC-NE-X8X16 {
   namespace "urn:huawei:yang:huawei-sflow-deviations-OC-NE-X8X16";
   prefix "sflow-devs-OC-NE-X8X16";
   import huawei-sflow {
     prefix "sflow";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-sflow module.";
   revision "2020-03-11" {
     description
       "Initial revision.";
     reference
       "Huawei private.";
   }
   deviation "/ifm:ifm/ifm:interfaces/ifm:interface/sflow:sflow/sflow:bind-colle"+
             "ctors/sflow:bind-collector" {
     deviate "add" {
       must "../../../ifm:type='GigabitEthernet' or\n../../../ifm:type='100GE' "+
            "or\n../../../ifm:type='40GE' or\n../../../ifm:type='10GE' "+
            "or\n../../../ifm:type='400GE' or\n../../../ifm:type='50|100GE' "+
            "or\n../../../ifm:type='50GE' or\n../../../ifm:type='200GE' "+
            "or\n../../../ifm:type='4x10GE' or\n../../../ifm:type='10x10GE' "+
            "or\n../../../ifm:type='3x40GE' or\n../../../ifm:type='4x25GE' "+
            "or\n../../../ifm:type='25GE' or\n../../../ifm:type='XGigabitEtherne"+
            "t'";
     }
   }
 }

submodule openconfig-bgp-neighbor {
   belongs-to openconfig-bgp {
     prefix "oc-bgp";
   }
   import openconfig-extensions {
     prefix "oc-ext";
   }
   include openconfig-bgp-common;
   include openconfig-bgp-common-multiprotocol;
   include openconfig-bgp-peer-group;
   include openconfig-bgp-common-structure;
   organization
     "OpenConfig working group";
   contact
     "OpenConfig working group\nnetopenconfig@googlegroups.com";
   description
     "This sub-module contains groupings that are specific to the\nneighbor "+
     "context of the OpenConfig BGP module.";
   oc-ext:openconfig-version "6.0.0";
   revision "2019-07-10" {
     description
       "Normalise timestamp units to nanoseconds.";
     reference
       "6.0.0";
   }
   revision "2019-05-28" {
     description
       "Clarify prefix counter descriptions, add received-pre-policy\ncounter.";
     reference
       "5.2.0";
   }
   revision "2019-04-16" {
     description
       "Add BGP RIB to the top-level BGP container";
     reference
       "5.1.0";
   }
   revision "2018-11-21" {
     description
       "Add OpenConfig module metadata extensions.";
     reference
       "5.0.2";
   }
   revision "2018-08-20" {
     description
       "Correct description of AFI-SAFI enabled leaf.";
     reference
       "5.0.1";
   }
   revision "2018-04-11" {
     description
       "Correct naming of BGP maximum prefix warning percentage leaf.";
     reference
       "5.0.0";
   }
   revision "2018-03-20" {
     description
       "Added SR-TE policy SAFI";
     reference
       "4.1.0";
   }
   revision "2017-07-30" {
     description
       "Clarification of add-paths send-max leaf";
     reference
       "4.0.1";
   }
   revision "2017-07-10" {
     description
       "Add error notifications; moved add-paths config; add AS\nprepend policy "+
       "features; removed unneeded config leaves";
     reference
       "4.0.0";
   }
   revision "2017-02-02" {
     description
       "Bugfix to remove remaining global-level policy data";
     reference
       "3.0.1";
   }
   revision "2017-01-26" {
     description
       "Add dynamic neighbor support, migrate to OpenConfig types";
     reference
       "3.0.0";
   }
   revision "2016-06-21" {
     description
       "OpenConfig BGP refactor";
     reference
       "2.1.1";
   }
 }

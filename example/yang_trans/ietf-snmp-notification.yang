submodule ietf-snmp-notification {
   belongs-to ietf-snmp {
     prefix "snmp";
   }
   include ietf-snmp-common;
   include ietf-snmp-target;
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Martin Bjorklund\n          <mailto:mbj@tail-"+
     "f.com>\nEditor:   Juergen Schoenwaelder\n          <mailto:j.schoenwaelder"+
     "@jacobs-university.de>";
   description
     "This submodule contains a collection of YANG definitions\nfor configuring "+
     "SNMP notifications.\nCopyright (c) 2014 IETF Trust and the persons "+
     "identified as\nauthors of the code.  All rights reserved.\nRedistribution "+
     "and use in source and binary forms, with or\nwithout modification, is "+
     "permitted pursuant to, and subject\nto the license terms contained in, the"+
     " Simplified BSD License\nset forth in Section 4.c of the IETF Trust's "+
     "Legal Provisions\nRelating to IETF Documents\n(http://trustee.ietf.org/lic"+
     "ense-info).\nThis version of this YANG module is part of RFC 7407; "+
     "see\nthe RFC itself for full legal notices.";
   reference
     "RFC 3413: Simple Network Management Protocol (SNMP)\nApplications";
   revision "2014-12-10" {
     description
       "Initial revision.";
     reference
       "RFC 7407: A YANG Data Model for SNMP Configuration";
   }
   feature notification-filter {
     description
       "A server implements this feature if it supports SNMP\nnotification "+
       "filtering.";
     reference
       "RFC 3413: Simple Network Management Protocol (SNMP)\nApplications";
   }
   augment "/snmp:snmp" {
     list notify {
       key "name";
       description
         "Targets that will receive notifications.\nEntries in this list are "+
         "mapped 1-1 to entries in\nsnmpNotifyTable, except that if an entry in "+
         "snmpNotifyTable\nhas an snmpNotifyTag for which no snmpTargetAddrEntry"+
         "\nexists, then the snmpNotifyTable entry is not mapped to an\nentry in"+
         " this list.";
       reference
         "RFC 3413: Simple Network Management Protocol (SNMP).\nApplications.\nS"+
         "NMP-NOTIFICATION-MIB.snmpNotifyTable";
       leaf name {
         type "snmp:identifier";
         description
           "An arbitrary name for the list entry.";
         reference
           "RFC 3413: Simple Network Management Protocol (SNMP).\nApplications."+
           "\nSNMP-NOTIFICATION-MIB.snmpNotifyName";
       }
       leaf tag {
         type "snmp:tag-value";
         mandatory "true";
         description
           "Target tag, selects a set of notification targets.\nImplementations "+
           "MAY restrict the values of this leaf\nto be one of the available "+
           "values of /snmp/target/tag in\na valid configuration.";
         reference
           "RFC 3413: Simple Network Management Protocol (SNMP).\nApplications."+
           "\nSNMP-NOTIFICATION-MIB.snmpNotifyTag";
       }
       leaf type {
         type "enumeration" {
           enum "trap" {
             value "1";
           }
           enum "inform" {
             value "2";
           }
         }
         default "trap";
         description
           "Defines the notification type to be generated.";
         reference
           "RFC 3413: Simple Network Management Protocol (SNMP).\nApplications."+
           "\nSNMP-NOTIFICATION-MIB.snmpNotifyType";
       }
     }
     list notify-filter-profile {
       if-feature "snmp:notification-filter";
       key "name";
       description
         "Notification filter profiles.\nThe leaf /snmp/target/notify-filter-pro"+
         "file is used\nto associate a filter profile with a target.\nIf an "+
         "entry in this list is referred to by one or more\n/snmp/target/notify-"+
         "filter-profile items, each such\nnotify-filter-profile is represented "+
         "by one\nsnmpNotifyFilterProfileEntry.\nIf an entry in this list is not"+
         " referred to by any\n/snmp/target/notify-filter-profile, the entry is "+
         "not mapped\nto snmpNotifyFilterProfileTable.";
       reference
         "RFC 3413: Simple Network Management Protocol (SNMP).\nApplications.\nS"+
         "NMP-NOTIFICATION-MIB.snmpNotifyFilterProfileTable\nSNMP-NOTIFICATION-M"+
         "IB.snmpNotifyFilterTable";
       leaf name {
         type "snmp:identifier";
         description
           "Name of the filter profile.";
         reference
           "RFC 3413: Simple Network Management Protocol (SNMP).\nApplications."+
           "\nSNMP-NOTIFICATION-MIB.snmpNotifyFilterProfileName";
       }
       leaf-list include {
         type "snmp:wildcard-object-identifier";
         description
           "A family of subtrees included in this filter.";
         reference
           "RFC 3413: Simple Network Management Protocol (SNMP).\nApplications."+
           "\nSNMP-NOTIFICATION-MIB.snmpNotifyFilterSubtree\nSNMP-NOTIFICATION-M"+
           "IB.snmpNotifyFilterMask\nSNMP-NOTIFICATION-MIB.snmpNotifyFilterType";
       }
       leaf-list exclude {
         type "snmp:wildcard-object-identifier";
         description
           "A family of subtrees excluded from this filter.";
         reference
           "RFC 3413: Simple Network Management Protocol (SNMP).\nApplications."+
           "\nSNMP-NOTIFICATION-MIB.snmpNotifyFilterSubtree\nSNMP-NOTIFICATION-M"+
           "IB.snmpNotifyFilterMask\nSNMP-NOTIFICATION-MIB.snmpNotifyFilterType";
       }
     }
   }
   augment "/snmp:snmp/snmp:target-params" {
     reference
       "RFC 3413: Simple Network Management Protocol (SNMP).\nApplications.\nSNM"+
       "P-NOTIFICATION-MIB.snmpNotifyFilterProfileTable";
     leaf notify-filter-profile {
       if-feature "snmp:notification-filter";
       type "leafref" {
         path "/snmp/notify-filter-profile/name";
       }
       description
         "This leafref leaf is used to represent the sparse\nrelationship "+
         "between the /snmp/target-params list and the\n/snmp/notify-filter-prof"+
         "ile list.";
       reference
         "RFC 3413: Simple Network Management Protocol (SNMP).\nApplications.\nS"+
         "NMP-NOTIFICATION-MIB.snmpNotifyFilterProfileName";
     }
   }
 }

module openconfig-aft {
   yang-version "1";
   namespace "http://openconfig.net/yang/aft";
   prefix "oc-aft";
   import openconfig-extensions {
     prefix "oc-ext";
   }
   include openconfig-aft-ipv4;
   include openconfig-aft-ipv6;
   include openconfig-aft-mpls;
   include openconfig-aft-pf;
   include openconfig-aft-ethernet;
   include openconfig-aft-common;
   organization
     "OpenConfig working group";
   contact
     "OpenConfig working group\nwww.openconfig.net";
   description
     "A model describing the forwarding entries installed on a network\nelement."+
     " It should be noted that this model is not expected to\nalign 1:1 with the"+
     " underlying structure used directly by a\nforwarding element (e.g., "+
     "linecard), but rather provide an\nabstraction that can be consumed by an "+
     "NMS to observe, and in some\ncases manipulate, the internal forwarding "+
     "database in a simplified\nmanner. Since the underlying model of the "+
     "forwarding table is not\nexpected to align with this model, the structure "+
     "described herein\nis referred to as an Abstract Forwarding Table (AFT), "+
     "rather than\nthe FIB.";
   oc-ext:openconfig-version "0.4.0";
   revision "2019-08-02" {
     description
       "Add installing protocol for IPv[46] unicast entries.\nAdd the ability to"+
       " describe conditional next-hop groups\noutside of the policy forwarding "+
       "module to allow for efficient\nhandling of CBTS, where many prefixes may"+
       " share the same next-hop\ncriteria.";
     reference
       "0.4.0";
   }
   revision "2019-08-01" {
     description
       "Add lsp-name leaf to AFT next-hop.";
     reference
       "0.3.3";
   }
   revision "2018-11-21" {
     description
       "Add OpenConfig module metadata extensions.";
     reference
       "0.3.2";
   }
   revision "2017-08-24" {
     description
       "Formatting fixes";
     reference
       "0.3.1";
   }
   revision "2017-05-10" {
     description
       "Refactor to provide concretised per-AF schemas per AFT.";
     reference
       "0.3.0";
   }
   oc-ext:regexp-posix;
   oc-ext:catalog-organization "openconfig";
   oc-ext:origin "openconfig";
 }

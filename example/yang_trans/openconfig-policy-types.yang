module openconfig-policy-types {
   yang-version "1";
   namespace "http://openconfig.net/yang/policy-types";
   prefix "oc-pol-types";
   import openconfig-extensions {
     prefix "oc-ext";
   }
   organization
     "OpenConfig working group";
   contact
     "OpenConfig working group\nnetopenconfig@googlegroups.com";
   description
     "This module contains general data definitions for use in routing\npolicy. "+
     " It can be imported by modules that contain protocol-\nspecific policy "+
     "conditions and actions.";
   oc-ext:openconfig-version "3.1.1";
   revision "2018-11-21" {
     description
       "Add OpenConfig module metadata extensions.";
     reference
       "3.1.1";
   }
   revision "2018-06-05" {
     description
       "Add PIM, IGMP to INSTALL_PROTOCOL_TYPES identity";
     reference
       "3.1.0";
   }
   revision "2017-07-14" {
     description
       "Replace policy choice node/type with policy-result\nenumeration;simplifi"+
       "ed defined set naming;removed generic\nIGP actions; migrate to "+
       "OpenConfig types; added mode for\nprefix sets";
     reference
       "3.0.0";
   }
   revision "2016-05-12" {
     description
       "OpenConfig public release";
     reference
       "2.0.1";
   }
   oc-ext:regexp-posix;
   oc-ext:catalog-organization "openconfig";
   oc-ext:origin "openconfig";
   identity ATTRIBUTE_COMPARISON {
     description
       "base type for supported comparison operators on route\nattributes";
   }
   identity ATTRIBUTE_EQ {
     base "ATTRIBUTE_COMPARISON";
     description
       "== comparison";
   }
   identity ATTRIBUTE_GE {
     base "ATTRIBUTE_COMPARISON";
     description
       ">= comparison";
   }
   identity ATTRIBUTE_LE {
     base "ATTRIBUTE_COMPARISON";
     description
       "<= comparison";
   }
   identity INSTALL_PROTOCOL_TYPE {
     description
       "Base type for routing protocols, including those which may\ninstall "+
       "prefixes into the RIB";
   }
   identity BGP {
     base "INSTALL_PROTOCOL_TYPE";
     description
       "BGP";
     reference
       "RFC 4271";
   }
   identity ISIS {
     base "INSTALL_PROTOCOL_TYPE";
     description
       "IS-IS";
     reference
       "ISO/IEC 10589";
   }
   identity OSPF {
     base "INSTALL_PROTOCOL_TYPE";
     description
       "OSPFv2";
     reference
       "RFC 2328";
   }
   identity OSPF3 {
     base "INSTALL_PROTOCOL_TYPE";
     description
       "OSPFv3";
     reference
       "RFC 5340";
   }
   identity STATIC {
     base "INSTALL_PROTOCOL_TYPE";
     description
       "Locally-installed static route";
   }
   identity DIRECTLY_CONNECTED {
     base "INSTALL_PROTOCOL_TYPE";
     description
       "A directly connected route";
   }
   identity LOCAL_AGGREGATE {
     base "INSTALL_PROTOCOL_TYPE";
     description
       "Locally defined aggregate route";
   }
   identity PIM {
     base "INSTALL_PROTOCOL_TYPE";
     description
       "Protocol Independent Multicast";
     reference
       "RFC 7761";
   }
   identity IGMP {
     base "INSTALL_PROTOCOL_TYPE";
     description
       "Internet Group Management Protocol";
     reference
       "RFC 3376";
   }
 }

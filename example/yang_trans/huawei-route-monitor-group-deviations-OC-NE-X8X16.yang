/*
Copyright (C) 2019 Huawei Technologies Co., Ltd. All rights reserved.
*/

 module huawei-route-monitor-group-deviations-OC-NE-X8X16 {
   namespace "urn:huawei:yang:huawei-route-monitor-group-deviations-OC-NE-X8X16";
   prefix "rmg-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "A route monitoring group monitors the status of its member routes.";
   revision "2019-04-27" {
     description
       "Initial revision.";
     reference
       "Huawei private.";
   }
 }

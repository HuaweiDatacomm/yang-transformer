/*
Copyright (C) 2021 Huawei Technologies Co., Ltd. All rights reserved.
*/

 module huawei-mpls-te-auto-tunnel-deviations-OC-NE-X8X16 {
   namespace "urn:huawei:yang:huawei-mpls-te-auto-tunnel-deviations-OC-NE-X8X16";
   prefix "mpls-te-auto-tunnel-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Specifies the multi-protocol label switching protocol.";
   revision "2021-07-09" {
     description
       "Init revision.";
     reference
       "Huawei private.";
   }
 }

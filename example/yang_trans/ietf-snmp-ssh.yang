submodule ietf-snmp-ssh {
   belongs-to ietf-snmp {
     prefix "snmp";
   }
   import ietf-inet-types {
     prefix "inet";
   }
   include ietf-snmp-common;
   include ietf-snmp-engine;
   include ietf-snmp-target;
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Martin Bjorklund\n          <mailto:mbj@tail-"+
     "f.com>\nEditor:   Juergen Schoenwaelder\n          <mailto:j.schoenwaelder"+
     "@jacobs-university.de>";
   description
     "This submodule contains a collection of YANG definitions for\nconfiguring "+
     "the Secure Shell Transport Model (SSHTM)\nof SNMP.\nCopyright (c) 2014 "+
     "IETF Trust and the persons identified as\nauthors of the code.  All rights"+
     " reserved.\nRedistribution and use in source and binary forms, with "+
     "or\nwithout modification, is permitted pursuant to, and subject\nto the "+
     "license terms contained in, the Simplified BSD License\nset forth in "+
     "Section 4.c of the IETF Trust's Legal Provisions\nRelating to IETF "+
     "Documents\n(http://trustee.ietf.org/license-info).\nThis version of this "+
     "YANG module is part of RFC 7407; see\nthe RFC itself for full legal "+
     "notices.";
   reference
     "RFC 5592: Secure Shell Transport Model for the\nSimple Network Management "+
     "Protocol (SNMP)";
   revision "2014-12-10" {
     description
       "Initial revision.";
     reference
       "RFC 7407: A YANG Data Model for SNMP Configuration";
   }
   feature sshtm {
     description
       "A server implements this feature if it supports the\nSecure Shell "+
       "Transport Model for SNMP.";
     reference
       "RFC 5592: Secure Shell Transport Model for the\nSimple Network "+
       "Management Protocol (SNMP)";
   }
   augment "/snmp:snmp/snmp:engine/snmp:listen/snmp:transport" {
     if-feature "sshtm";
     case ssh {
       container ssh {
         description
           "The IPv4 or IPv6 address and port to which the\nengine listens for "+
           "SNMP messages over SSH.";
         leaf ip {
           type "inet:ip-address";
           mandatory "true";
           description
             "The IPv4 or IPv6 address on which the engine listens\nfor SNMP "+
             "messages over SSH.";
         }
         leaf port {
           type "inet:port-number";
           description
             "The TCP port on which the engine listens for SNMP\nmessages over "+
             "SSH.\nIf the port is not configured, an engine that\nacts as a "+
             "Command Responder uses port 5161, and\nan engine that acts as a "+
             "Notification Receiver\nuses port 5162.";
         }
       }
     }
   }
   augment "/snmp:snmp/snmp:target/snmp:transport" {
     if-feature "sshtm";
     case ssh {
       reference
         "RFC 5592: Secure Shell Transport Model for the\nSimple Network "+
         "Management Protocol (SNMP).\nSNMP-SSH-TM-MIB.snmpSSHDomain";
       container ssh {
         leaf ip {
           type "inet:host";
           mandatory "true";
           reference
             "RFC 3413: Simple Network Management Protocol (SNMP).\nApplications"+
             ".\nSNMP-TARGET-MIB.snmpTargetAddrTAddress\nRFC 5592: Secure Shell "+
             "Transport Model for the\n  Simple Network Management Protocol "+
             "(SNMP).\n  SNMP-SSH-TM-MIB.SnmpSSHAddress";
         }
         leaf port {
           type "inet:port-number";
           default "5161";
           reference
             "RFC 3413: Simple Network Management Protocol (SNMP).\nApplications"+
             ".\nSNMP-TARGET-MIB.snmpTargetAddrTAddress\nRFC 5592: Secure Shell "+
             "Transport Model for the\n  Simple Network Management Protocol "+
             "(SNMP).\n  SNMP-SSH-TM-MIB.SnmpSSHAddress";
         }
         leaf username {
           type "string";
           reference
             "RFC 3413: Simple Network Management Protocol (SNMP).\nApplications"+
             ".\nSNMP-TARGET-MIB.snmpTargetAddrTAddress\nRFC 5592: Secure Shell "+
             "Transport Model for the\n  Simple Network Management Protocol "+
             "(SNMP).\n  SNMP-SSH-TM-MIB.SnmpSSHAddress";
         }
       }
     }
   }
 }

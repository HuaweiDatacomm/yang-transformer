module iana-hardware {
   yang-version "1.1";
   namespace "urn:ietf:params:xml:ns:yang:iana-hardware";
   prefix "ianahw";
   organization
     "IANA";
   contact
     "        Internet Assigned Numbers Authority\n\nPostal: ICANN\n        "+
     "12025 Waterfront Drive, Suite 300\n        Los Angeles, CA  90094-2536\n  "+
     "      United States of America\n\nTel:    +1 310 301 5800\nE-Mail: "+
     "iana@iana.org>";
   description
     "IANA-defined identities for hardware class.\n\nThe latest revision of this"+
     " YANG module can be obtained from\nthe IANA website.\n\nRequests for new "+
     "values should be made to IANA via\nemail (iana@iana.org).\n\nCopyright (c)"+
     " 2018 IETF Trust and the persons identified as\nauthors of the code.  All "+
     "rights reserved.\n\nRedistribution and use in source and binary forms, "+
     "with or\nwithout modification, is permitted pursuant to, and subject\nto "+
     "the license terms contained in, the Simplified BSD License\n\nset forth in"+
     " Section 4.c of the IETF Trust's Legal Provisions\nRelating to IETF "+
     "Documents\n(https://trustee.ietf.org/license-info).\n\nThe initial version"+
     " of this YANG module is part of RFC 8348;\nsee the RFC itself for full "+
     "legal notices.";
   reference
     "https://www.iana.org/assignments/yang-parameters";
   revision "2018-03-13" {
     description
       "Initial revision.";
     reference
       "RFC 8348: A YANG Data Model for Hardware Management";
   }
   identity hardware-class {
     description
       "This identity is the base for all hardware class\nidentifiers.";
   }
   identity unknown {
     base "ianahw:hardware-class";
     description
       "This identity is applicable if the hardware class is unknown\nto the "+
       "server.";
   }
   identity chassis {
     base "ianahw:hardware-class";
     description
       "This identity is applicable if the hardware class is an\noverall "+
       "container for networking equipment.  Any class of\nphysical component, "+
       "except a stack, may be contained within a\nchassis; a chassis may only "+
       "be contained within a stack.";
   }
   identity backplane {
     base "ianahw:hardware-class";
     description
       "This identity is applicable if the hardware class is some sort\nof "+
       "device for aggregating and forwarding networking traffic,\nsuch as a "+
       "shared backplane in a modular ethernet switch.  Note\nthat an implementa"+
       "tion may model a backplane as a single\nphysical component, which is "+
       "actually implemented as multiple\ndiscrete physical components (within a"+
       " chassis or stack).";
   }
   identity container {
     base "ianahw:hardware-class";
     description
       "This identity is applicable if the hardware class is capable\nof "+
       "containing one or more removable physical entities,\npossibly of "+
       "different types.  For example, each (empty or\nfull) slot in a chassis "+
       "will be modeled as a container.  Note\nthat all removable physical "+
       "components should be modeled\nwithin a container component, such as "+
       "field-replaceable\nmodules, fans, or power supplies.  Note that all "+
       "known\ncontainers should be modeled by the agent, including empty\nconta"+
       "iners.";
   }
   identity power-supply {
     base "ianahw:hardware-class";
     description
       "This identity is applicable if the hardware class is a\npower-supplying "+
       "component.";
   }
   identity fan {
     base "ianahw:hardware-class";
     description
       "This identity is applicable if the hardware class is a fan or\nother "+
       "heat-reduction component.";
   }
   identity sensor {
     base "ianahw:hardware-class";
     description
       "This identity is applicable if the hardware class is some sort\nof "+
       "sensor, such as a temperature sensor within a router\nchassis.";
   }
   identity module {
     base "ianahw:hardware-class";
     description
       "This identity is applicable if the hardware class is some sort\nof "+
       "self-contained sub-system.  If a module component is\nremovable, then it"+
       " should be modeled within a container\n\ncomponent; otherwise, it should"+
       " be modeled directly within\nanother physical component (e.g., a chassis"+
       " or another\nmodule).";
   }
   identity port {
     base "ianahw:hardware-class";
     description
       "This identity is applicable if the hardware class is some sort\nof "+
       "networking port capable of receiving and/or transmitting\nnetworking "+
       "traffic.";
   }
   identity stack {
     base "ianahw:hardware-class";
     description
       "This identity is applicable if the hardware class is some sort\nof "+
       "super-container (possibly virtual) intended to group\ntogether multiple "+
       "chassis entities.  A stack may be realized\nby a virtual cable, a real "+
       "interconnect cable attached to\nmultiple chassis, or multiple interconne"+
       "ct cables.  A stack\nshould not be modeled within any other physical "+
       "components,\nbut a stack may be contained within another stack.  "+
       "Only\nchassis components should be contained within a stack.";
   }
   identity cpu {
     base "ianahw:hardware-class";
     description
       "This identity is applicable if the hardware class is some sort\nof "+
       "central processing unit.";
   }
   identity energy-object {
     base "ianahw:hardware-class";
     description
       "This identity is applicable if the hardware class is some sort\nof "+
       "energy object, i.e., it is a piece of equipment that is\npart of or "+
       "attached to a communications network that is\nmonitored, it is "+
       "controlled, or it aids in the management of\nanother device for Energy "+
       "Management.";
   }
   identity battery {
     base "ianahw:hardware-class";
     description
       "This identity is applicable if the hardware class is some sort\nof "+
       "battery.";
   }
   identity storage-drive {
     base "ianahw:hardware-class";
     description
       "This identity is applicable if the hardware class is some sort\nof "+
       "component with data storage capability as its main\nfunctionality, e.g.,"+
       " hard disk drive (HDD), solid-state device\n(SSD), solid-state hybrid "+
       "drive (SSHD), object storage device\n(OSD), or other.";
   }
 }

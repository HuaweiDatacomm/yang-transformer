/*
Copyright (C) 2021 Huawei Technologies Co., Ltd. All rights reserved.
*/

 module huawei-pbr-deviations-OC-NE-X8X16 {
   namespace "urn:huawei:yang:huawei-pbr-deviations-OC-NE-X8X16";
   prefix "pbr-devs-OC-NE-X8X16";
   import huawei-pbr {
     prefix "pbr";
   }
   import huawei-qos {
     prefix "qos";
   }
   import huawei-devm {
     prefix "devm";
   }
   import huawei-ifm {
     prefix "ifm";
   }
   import huawei-tunnel-management {
     prefix "tnlm";
   }
   import huawei-mpls {
     prefix "mpls";
   }
   import huawei-mpls-te {
     prefix "mpls-te";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-pbr module.";
   revision "2021-05-07" {
     description
       "Initial revision.";
     reference
       "Huawei private.";
   }
   typedef ip-type-deviations {
     type "enumeration" {
       enum "ipv4" {
         value "0";
         description
           "IPv4.";
       }
       enum "ipv6" {
         value "1";
         description
           "IPv6.";
       }
     }
     description
       "Ip type.";
   }
   deviation "/devm:devm/devm:lpu-boards/devm:lpu-board/pbr:pbr/pbr:routing-filt"+
             "ers/pbr:routing-filter/pbr:type" {
     deviate "replace" {
       type "pbr-devs-OC-NE-X8X16:ip-type-deviations";
     }
   }
   deviation "/qos:qos/qos:classifier-template/qos:traffic-behaviors/qos:traffic"+
             "-behavior/pbr:pbr/pbr:pbr-ipv4/pbr:pbr-ipv4/pbr:redirect-srv6-te-p"+
             "olicy/pbr:redirect-srv6-te-policy" {
     deviate "add" {
       must "not( ../../pbr:pbr-ipv6/pbr:ipv6-redirect-public-network or "+
            "../../pbr:pbr-ipv6/pbr:ipv6-redirect-to-interface/pbr:if-name\nor "+
            "../../pbr:pbr-ipv6/pbr:ipv6-nexthop or (count(../../pbr:pbr-ipv6/pb"+
            "r:ipv6-multinhp-interface/pbr:multi-nhp-interfaces/pbr:multi-nhp-in"+
            "terface)>0)\nor (count(../../pbr:pbr-ipv6/pbr:ipv6-multinhp/pbr:mul"+
            "ti-nhps/pbr:multi-nhp)>0) or (count(../../pbr:pbr-ipv6/pbr:ipv6-mul"+
            "tinhp-vpn/pbr:multi-vpns/pbr:multi-vpn)>0)\nor (count(../../pbr:pbr"+
            "-ipv6/pbr:ipv6-multinhp-nqa/pbr:multi-nqas/pbr:multi-nqa)>0) )";
     }
   }
   deviation "/qos:qos/qos:classifier-template/qos:traffic-behaviors/qos:traffic"+
             "-behavior/pbr:pbr/pbr:pbr-ipv4/pbr:pbr-ipv4/pbr:ipv4-multinhp-vpn/"+
             "pbr:ipv4-multinhp-vpn/pbr:multi-vpns" {
     deviate "add" {
       must "count(./multi-vpn/nqa-instance)=0 or count(./multi-vpn)=count(./mul"+
            "ti-vpn/nqa-instance)";
     }
   }
   deviation "/qos:qos/qos:classifier-template/qos:traffic-behaviors/qos:traffic"+
             "-behavior/pbr:pbr/pbr:pbr-ipv6/pbr:pbr-ipv6/pbr:ipv6-multinhp-vpn/"+
             "pbr:ipv6-multinhp-vpn/pbr:multi-vpns" {
     deviate "add" {
       must "count(./multi-vpn/nqa-instance)=0 or count(./multi-vpn)=count(./mul"+
            "ti-vpn/nqa-instance)";
     }
   }
   deviation "/qos:qos/qos:classifier-template/qos:traffic-behaviors/qos:traffic"+
             "-behavior/pbr:pbr/pbr:pbr-ipv4/pbr:pbr-ipv4/pbr:redirect-tunnel/pb"+
             "r:redirect-tunnel" {
     deviate "add" {
       must "(/ifm:ifm/ifm:interfaces/ifm:interface[ifm:name=current()/tunnel-na"+
            "me]/tnlm:tunnel-protocol/mpls-te:te-tunnel/mpls-te:common-attribute"+
            "s/mpls-te:signal-protocol\nand not(/ifm:ifm/ifm:interfaces/ifm:inte"+
            "rface[ifm:name=current()/tunnel-name]/tnlm:tunnel-protocol/mpls-te:"+
            "te-tunnel/mpls-te:rsvp-te/mpls-te:split-tunnel='true'\nor "+
            "/ifm:ifm/ifm:interfaces/ifm:interface[ifm:name=current()/tunnel-nam"+
            "e]/tnlm:tunnel-protocol/mpls-te:te-tunnel/mpls-te:sr-te/mpls-te:spl"+
            "it-tunnel='true'))\nand not(/ifm:ifm/ifm:interfaces/ifm:interface[i"+
            "fm:name=current()/tunnel-name]/tnlm:tunnel-protocol/mpls-te:te-tunn"+
            "el/mpls-te:p2mp-te and ./route-forward='true')\nand not(/mpls:mpls/"+
            "mpls-te:te/mpls-te:associate-groups/mpls-te:associate-group/mpls-te"+
            ":original-tunnels/mpls-te:original-tunnel[mpls-te:name=current()/tu"+
            "nnel-name])";
     }
   }
 }

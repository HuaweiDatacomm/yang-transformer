/*
Copyright (C) 2021 Huawei Technologies Co., Ltd. All rights reserved.
*/

 module huawei-ietf-netconf-nmda-deviations-OC-NE-X8X16 {
   yang-version "1.1";
   namespace "urn:huawei:yang:huawei-ietf-netconf-nmda-deviations-OC-NE-X8X16";
   prefix "nmda-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Ietf netconf nmda deviation file.";
   revision "2021-01-13" {
     description
       "Initial revision.";
     reference
       "Huawei private.";
   }
 }

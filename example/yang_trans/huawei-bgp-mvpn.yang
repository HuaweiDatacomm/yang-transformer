/*
Copyright (C) 2019-2020 Huawei Technologies Co., Ltd. All rights reserved.
*/

 module huawei-bgp-mvpn {
   yang-version "1";
   namespace "urn:huawei:yang:huawei-bgp-mvpn";
   prefix "bgp-mvpn";
   import huawei-extension {
     prefix "ext";
   }
   import ietf-inet-types {
     prefix "inet";
   }
   import huawei-network-instance {
     prefix "ni";
   }
   import huawei-bgp {
     prefix "bgp";
   }
   import huawei-bgp-routing-table {
     prefix "bgp-rt";
   }
   import huawei-pub-type {
     prefix "pub-type";
   }
   import huawei-routing-policy {
     prefix "rtp";
   }
   import huawei-xpl {
     prefix "xpl";
   }
   organization
     "Huawei Technologies Co., Ltd.";
   contact
     "Huawei Industrial Base\nBantian, Longgang\nShenzhen 518129\nPeople's "+
     "Republic of China\nWebsite: http://www.huawei.com\nEmail: support@huawei.c"+
     "om";
   description
     "Inter-AS routing protocol that exchanges Network Layer Reachability "+
     "Information (NLRI) with other BGP systems.";
   revision "2020-02-25" {
     description
       "The YANG descriptions are modified according to new standards.";
     reference
       "Huawei private.";
   }
   revision "2019-03-22" {
     description
       "Initial revision.";
     reference
       "Huawei private.";
   }
   ext:task-name "bgp";
   augment "/ni:network-instance/ni:instances/ni:instance/bgp:bgp/bgp:base-proce"+
           "ss/bgp:afs/bgp:af" {
     description
       "BGP mvpn address family configuration.";
     container ipv4-mvpn {
       when "../bgp:type = 'mvpn'";
       description
         "Configure IPv4-family mvpn options.";
       container common {
         description
           "Configure IPv4-family mvpn common options.";
         leaf policy-vpntarget {
           type "boolean";
           default "true";
           description
             "Enable/disable VPN target-based filtering for the received VPN "+
             "routes. Only the VPN route whose Export RT attribute matches the "+
             "local Import RT attribute can be added to the routing table. This "+
             "option can be used in the inter-AS VPN Option B solution and the "+
             "ASBR MP-EBGP inter-AS L2VPN solution in Kompella mode.";
         }
         leaf vpn-orf-enable {
           type "boolean";
           default "false";
           description
             "Enable/disable vpn-orf capability.";
         }
         leaf route-select-delay {
           type "uint16" {
             range "0..3600";
           }
           units "s";
           default "0";
           description
             "Route selection delay.";
         }
         leaf reflect-change-path {
           type "boolean";
           default "false";
           description
             "Enable/disable an RR to use an export policy to change route "+
             "AS_Path.";
         }
         leaf reflect-between-client {
           type "boolean";
           default "true";
           description
             "Enable/disable route reflection between clients. If clients of a "+
             "route reflector (RR) are fully meshed, you can disable route "+
             "reflection among clients to reduce the cost.";
         }
         choice reflector-type {
           description
             "Set IPv4 address or id.";
           case address {
             description
               "IPv4 address.";
             leaf reflector-cluster-ipv4 {
               type "inet:ipv4-address-no-zone";
               description
                 "Set a cluster ID. The value is expressed in the format of an "+
                 "IPv4 address. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
           case id {
             description
               "Set value.";
             leaf reflector-cluster-id {
               type "uint32" {
                 range "1..4294967295";
               }
               description
                 "Set a cluster ID. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
         }
         leaf add-path-select-num {
           type "uint8" {
             range "2..64";
           }
           description
             "Number of Add-Path routes.";
         }
         leaf route-reflector-ext-community-filter {
           type "leafref" {
             path "/rtp:routing-policy/rtp:ext-community-filters/rtp:ext-communi"+
                  "ty-filter/rtp:name";
           }
           description
             "Set the name of the extended community filter supported by an RR "+
             "group. For the purpose of load balancing, only the IBGP route "+
             "whose route-target extended community attribute meets the matching"+
             " rules can be reflected.";
         }
       }
       container slow-peer {
         description
           "Configure peer advertising routes slowly.";
         leaf detection {
           type "boolean";
           default "true";
           description
             "Enable/disable detect slow peers.";
         }
         leaf detection-threshold {
           type "uint16" {
             range "120..3600";
           }
           units "s";
           default "300";
           description
             "Specify the time in seconds lagging behind average when a peer is "+
             "determined to be a slow peer.";
         }
         leaf absolute-detection {
           type "boolean";
           default "true";
           description
             "Enable/disable absolute-detect slow peers.";
         }
         leaf absolute-detection-threshold {
           type "uint16" {
             range "3..3600";
           }
           units "s";
           default "9";
           description
             "Specify the packet send delay time in second when a peer is "+
             "determined to be a slow peer.";
         }
       }
     }
     container ipv6-mvpn {
       when "../bgp:type='mvpnv6'";
       description
         "Configure IPv6-family mvpn options.";
       container common {
         description
           "Configure IPv6-family mvpn common options.";
         leaf policy-vpntarget {
           type "boolean";
           default "true";
           description
             "Enable/disable VPN target-based filtering for the received VPN "+
             "routes. Only the VPN route whose Export RT attribute matches the "+
             "local Import RT attribute can be added to the routing table. This "+
             "option can be used in the inter-AS VPN Option B solution and the "+
             "ASBR MP-EBGP inter-AS L2VPN solution in Kompella mode.";
         }
         leaf route-select-delay {
           type "uint16" {
             range "0..3600";
           }
           units "s";
           default "0";
           description
             "Route selection delay.";
         }
         leaf reflect-change-path {
           type "boolean";
           default "false";
           description
             "Enable/disable an RR to use an export policy to change route "+
             "AS_Path.";
         }
         leaf reflect-between-client {
           type "boolean";
           default "true";
           description
             "Enable/disable route reflection between clients. If clients of a "+
             "route reflector (RR) are fully meshed, you can disable route "+
             "reflection among clients to reduce the cost.";
         }
         choice reflector-type {
           description
             "Set IPv4 address or id.";
           case address {
             description
               "IPv4 address.";
             leaf reflector-cluster-ipv4 {
               type "inet:ipv4-address-no-zone";
               description
                 "Set a cluster ID. The value is expressed in the format of an "+
                 "IPv4 address. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
           case id {
             description
               "Set value.";
             leaf reflector-cluster-id {
               type "uint32" {
                 range "1..4294967295";
               }
               description
                 "Set a cluster ID. Configuring multiple RRs in a cluster can "+
                 "enhance the stability of the network. If a cluster has more "+
                 "than one RR, select this option to set the same cluster ID for"+
                 " all the RRs to avoid routing loops. To allow clients to "+
                 "receive routes from RRs, ensure that the cluster ID of the RRs"+
                 " is different from the router ID of any client. If the cluster"+
                 " ID of the RRs is the same as the router ID of a client, the "+
                 "client will discard received routes.";
             }
           }
         }
         leaf add-path-select-num {
           type "uint8" {
             range "2..64";
           }
           description
             "Number of Add-Path routes.";
         }
         leaf route-reflector-ext-community-filter {
           type "leafref" {
             path "/rtp:routing-policy/rtp:ext-community-filters/rtp:ext-communi"+
                  "ty-filter/rtp:name";
           }
           description
             "Set the name of the extended community filter supported by an RR "+
             "group. For the purpose of load balancing, only the IBGP route "+
             "whose route-target extended community attribute meets the matching"+
             " rules can be reflected.";
         }
       }
       container slow-peer {
         description
           "Configure peer advertising routes slowly.";
         leaf detection {
           type "boolean";
           default "true";
           description
             "Enable/disable detect slow peers.";
         }
         leaf detection-threshold {
           type "uint16" {
             range "120..3600";
           }
           units "s";
           default "300";
           description
             "Specify the time in seconds lagging behind average when a peer is "+
             "determined to be a slow peer.";
         }
         leaf absolute-detection {
           type "boolean";
           default "true";
           description
             "Enable/disable absolute-detect slow peers.";
         }
         leaf absolute-detection-threshold {
           type "uint16" {
             range "3..3600";
           }
           units "s";
           default "9";
           description
             "Specify the packet send delay time in second when a peer is "+
             "determined to be a slow peer.";
         }
       }
     }
   }
   augment "/ni:network-instance/ni:instances/ni:instance/bgp:bgp/bgp:base-proce"+
           "ss/bgp:peer-groups/bgp:peer-group/bgp:afs/bgp:af" {
     description
       "BGP mvpn address family configuration.";
     container ipv4-mvpn {
       when "../bgp:type = 'mvpn'";
       description
         "Configure IPv4-family mvpn options.";
       leaf advertise-community {
         type "boolean";
         default "false";
         description
           "Enable/disable advertise the community attribute to a peer or a peer"+
           " group.";
       }
       leaf reflect-client {
         when "../../../../bgp:type='ibgp'";
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf import-as-path-filter {
         type "leafref" {
           path "/rtp:routing-policy/rtp:as-path-filters/rtp:as-path-filter/rtp:"+
                "name";
         }
         description
           "Apply an AS_Path-based filtering policy to the routes received from "+
           "a specified peer. The policy can be identified with a name or "+
           "number, and the number ranges from 1 to 256. By default, no such "+
           "policy is specified. Therefore, all BGP routes can be accepted.";
       }
       leaf export-as-path-filter {
         type "leafref" {
           path "/rtp:routing-policy/rtp:as-path-filters/rtp:as-path-filter/rtp:"+
                "name";
         }
         description
           "Apply an AS_Path-based filtering policy to the routes to be "+
           "advertised to a specified peer. The policy can be identified with a "+
           "name or number, and the number ranges from 1 to 256. By default, no "+
           "such policy is specified. Therefore, all BGP routes can be "+
           "advertised.";
       }
       leaf advertise-c-multicast-route {
         type "boolean";
         default "false";
         description
           "Enable/disable advertise C-multicast route directional, only "+
           "advertise to the neighbor which is matched the nexthop in intra-AD "+
           "route.";
       }
       leaf nexthop-configure {
         type "bgp:nexthop-configuration-type";
         must "../nexthop-configure='local'";
         description
           "Both the next-hop-local mode and next-hop-invariable mode are "+
           "available when the peer address family is the VPNv4/VPNV6/L2VPN AD "+
           "address family. Only the next-hop-local mode is available when the "+
           "peer address family is not VPNv4/VPNV6/L2VPN AD address family. In "+
           "next-hop-local mode, you can configure a BGP speaker to set its IP "+
           "address of as the next hop of the routes to be advertised to IBGP "+
           "peers or IBGP peer groups. In next-hop-invariable mode, you can "+
           "configure PEs in different ASs not to change the next hop of routes "+
           "when the PEs advertise the routes to their EBGP peers and use the "+
           "next hop addresses of IGP routes to advertise imported IGP routes to"+
           " IBGP peers. By default, when a BGP speaker advertises routes to "+
           "EBGP peers and imported IGP routes to IBGP peers, the BGP speaker "+
           "changes the next hop to its interface address. If the value of "+
           "nexthop-configure is set to local, the configuration does not take "+
           "effect in the current address family.";
       }
       leaf nexthop-effective {
         when "../nexthop-configure='local'";
         type "boolean";
         default "false";
         description
           "Enable/disable the next hop of group takes effect in the RR "+
           "scenario.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-large-community {
         type "boolean";
         default "false";
         description
           "Enable/disable large-community attribute advertisement. The "+
           "Link-state address family and the RPD address family do not support "+
           "this element.";
       }
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       leaf update-group-independent {
         type "boolean";
         default "false";
         description
           "Enable/disable the peer which can reside in an independent peer "+
           "group.";
       }
       leaf add-path-mode {
         when "../../../../bgp:type='ibgp'";
         type "bgp:add-path-cap-type";
         default "null";
         description
           "Enable Add-Path route advertisement to a peer.";
       }
       leaf add-path-number {
         when "../../../../bgp:type='ibgp'";
         type "uint8" {
           range "2..64";
         }
         description
           "Number of Add-Path routes that can be advertised to a peer.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
     }
     container ipv6-mvpn {
       when "../bgp:type='mvpnv6'";
       description
         "Configure IPv6-family mvpn options.";
       leaf advertise-community {
         type "boolean";
         default "false";
         description
           "Enable/disable advertise the community attribute to a peer or a peer"+
           " group.";
       }
       leaf reflect-client {
         when "../../../../bgp:type='ibgp'";
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf import-as-path-filter {
         type "leafref" {
           path "/rtp:routing-policy/rtp:as-path-filters/rtp:as-path-filter/rtp:"+
                "name";
         }
         description
           "Apply an AS_Path-based filtering policy to the routes received from "+
           "a specified peer. The policy can be identified with a name or "+
           "number, and the number ranges from 1 to 256. By default, no such "+
           "policy is specified. Therefore, all BGP routes can be accepted.";
       }
       leaf export-as-path-filter {
         type "leafref" {
           path "/rtp:routing-policy/rtp:as-path-filters/rtp:as-path-filter/rtp:"+
                "name";
         }
         description
           "Apply an AS_Path-based filtering policy to the routes to be "+
           "advertised to a specified peer. The policy can be identified with a "+
           "name or number, and the number ranges from 1 to 256. By default, no "+
           "such policy is specified. Therefore, all BGP routes can be "+
           "advertised.";
       }
       leaf advertise-c-multicast-route {
         type "boolean";
         default "false";
         description
           "Enable/disable advertise C-multicast route directional, only "+
           "advertise to the neighbor which is matched the nexthop in intra-AD "+
           "route.";
       }
       leaf nexthop-configure {
         type "bgp:nexthop-configuration-type";
         must "../nexthop-configure='local'";
         description
           "Both the next-hop-local mode and next-hop-invariable mode are "+
           "available when the peer address family is the VPNv4/VPNV6/L2VPN AD "+
           "address family. Only the next-hop-local mode is available when the "+
           "peer address family is not VPNv4/VPNV6/L2VPN AD address family. In "+
           "next-hop-local mode, you can configure a BGP speaker to set its IP "+
           "address of as the next hop of the routes to be advertised to IBGP "+
           "peers or IBGP peer groups. In next-hop-invariable mode, you can "+
           "configure PEs in different ASs not to change the next hop of routes "+
           "when the PEs advertise the routes to their EBGP peers and use the "+
           "next hop addresses of IGP routes to advertise imported IGP routes to"+
           " IBGP peers. By default, when a BGP speaker advertises routes to "+
           "EBGP peers and imported IGP routes to IBGP peers, the BGP speaker "+
           "changes the next hop to its interface address. If the value of "+
           "nexthop-configure is set to local, the configuration does not take "+
           "effect in the current address family.";
       }
       leaf nexthop-effective {
         when "../nexthop-configure='local'";
         type "boolean";
         default "false";
         description
           "Enable/disable the next hop of group takes effect in the RR "+
           "scenario.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-large-community {
         type "boolean";
         default "false";
         description
           "Enable/disable large-community attribute advertisement. The "+
           "Link-state address family and the RPD address family do not support "+
           "this element.";
       }
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       leaf update-group-independent {
         type "boolean";
         default "false";
         description
           "Enable/disable the peer which can reside in an independent peer "+
           "group.";
       }
       leaf add-path-mode {
         when "../../../../bgp:type='ibgp'";
         type "bgp:add-path-cap-type";
         default "null";
         description
           "Enable Add-Path route advertisement to a peer.";
       }
       leaf add-path-number {
         when "../../../../bgp:type='ibgp'";
         type "uint8" {
           range "2..64";
         }
         description
           "Number of Add-Path routes that can be advertised to a peer.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
     }
   }
   augment "/ni:network-instance/ni:instances/ni:instance/bgp:bgp/bgp:base-proce"+
           "ss/bgp:peers/bgp:peer/bgp:afs/bgp:af" {
     description
       "BGP mvpn address family configuration.";
     container ipv4-mvpn {
       when "../bgp:type = 'mvpn'";
       description
         "Configure IPv4-family mvpn options.";
       leaf group-name {
         type "leafref" {
           path "../../../../../../bgp:peer-groups/bgp:peer-group/bgp:name";
         }
         must "../../../../../../bgp:peer-groups/bgp:peer-group[bgp:name = "+
              "current()]/bgp:afs/bgp:af[bgp:type='mvpn']";
         description
           "Configure a name for a peer group. After a peer is deleted from the "+
           "peer group, the peer is disabled from the address family. The object"+
           " cannot be modified.";
         ext:operation-exclude "update" {
           description
             "The node cannot be modified, when the peer already belongs to a "+
             "peer-group.";
         }
       }
       leaf advertise-community {
         type "boolean";
         default "false";
         description
           "Enable/disable advertise the community attribute to a peer or a peer"+
           " group.";
       }
       leaf reflect-client {
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf import-as-path-filter {
         type "leafref" {
           path "/rtp:routing-policy/rtp:as-path-filters/rtp:as-path-filter/rtp:"+
                "name";
         }
         description
           "Apply an AS_Path-based filtering policy to the routes received from "+
           "a specified peer. The policy can be identified with a name or "+
           "number, and the number ranges from 1 to 256. By default, no such "+
           "policy is specified. Therefore, all BGP routes can be accepted.";
       }
       leaf export-as-path-filter {
         type "leafref" {
           path "/rtp:routing-policy/rtp:as-path-filters/rtp:as-path-filter/rtp:"+
                "name";
         }
         description
           "Apply an AS_Path-based filtering policy to the routes to be "+
           "advertised to a specified peer. The policy can be identified with a "+
           "name or number, and the number ranges from 1 to 256. By default, no "+
           "such policy is specified. Therefore, all BGP routes can be "+
           "advertised.";
       }
       leaf advertise-c-multicast-route {
         type "boolean";
         default "false";
         description
           "Enable/disable advertise C-multicast route directional, only "+
           "advertise to the neighbor which is matched the nexthop in intra-AD "+
           "route.";
       }
       leaf nexthop-configure {
         type "bgp:nexthop-configuration-type";
         must "../nexthop-configure='local'";
         description
           "Both the next-hop-local mode and next-hop-invariable mode are "+
           "available when the peer address family is the VPNv4/VPNV6/L2VPN AD "+
           "address family. Only the next-hop-local mode is available when the "+
           "peer address family is not VPNv4/VPNV6/L2VPN AD address family. In "+
           "next-hop-local mode, you can configure a BGP speaker to set its IP "+
           "address of as the next hop of the routes to be advertised to IBGP "+
           "peers or IBGP peer groups. In next-hop-invariable mode, you can "+
           "configure PEs in different ASs not to change the next hop of routes "+
           "when the PEs advertise the routes to their EBGP peers and use the "+
           "next hop addresses of IGP routes to advertise imported IGP routes to"+
           " IBGP peers. By default, when a BGP speaker advertises routes to "+
           "EBGP peers and imported IGP routes to IBGP peers, the BGP speaker "+
           "changes the next hop to its interface address. If the value of "+
           "nexthop-configure is set to local, the configuration does not take "+
           "effect in the current address family.";
       }
       leaf nexthop-effective {
         when "../nexthop-configure='local'";
         type "boolean";
         default "false";
         description
           "Enable/disable the next hop of peer takes effect in the RR "+
           "scenario.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-large-community {
         type "bgp:peer-comm-config-type";
         default "default";
         description
           "Enable large-community attribute advertisement. The Link-state "+
           "address family and the RPD address family do not support this "+
           "element.";
       }
       leaf advertise-large-community-state {
         type "boolean";
         default "false";
         config "false";
         description
           "Whether large-community attribute advertisement is enabled on a "+
           "peer. The Link-state address family and the RPD address family do "+
           "not support this element.";
       }
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       leaf update-group-independent {
         type "bgp:peer-comm-config-type";
         default "default";
         description
           "Enable/disable the peer which can reside in an independent peer "+
           "group.";
       }
       leaf update-group-independent-state {
         type "boolean";
         config "false";
         description
           "Whether the peer can reside in an independent peer group.";
       }
       leaf add-path-mode {
         type "bgp:add-path-cap-type";
         default "null";
         description
           "Enable Add-Path route advertisement to a peer.";
       }
       leaf add-path-number {
         type "uint8" {
           range "2..64";
         }
         description
           "Number of Add-Path routes that can be advertised to a peer.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
     container ipv6-mvpn {
       when "../bgp:type='mvpnv6'";
       description
         "Configure IPv6-family mvpn options.";
       leaf group-name {
         type "leafref" {
           path "../../../../../../bgp:peer-groups/bgp:peer-group/bgp:name";
         }
         must "../../../../../../bgp:peer-groups/bgp:peer-group[bgp:name = "+
              "current()]/bgp:afs/bgp:af[bgp:type='mvpnv6']";
         must "../../../../../../bgp:peer-groups/bgp:peer-group[bgp:name = "+
              "current()]/bgp:peer-establish-mode = 'static'";
         description
           "Configure a name for a peer group. After a peer is deleted from the "+
           "peer group, the peer is disabled from the address family. The object"+
           " cannot be modified.";
         ext:operation-exclude "update" {
           description
             "The node cannot be modified, when the peer already belongs to a "+
             "peer-group.";
         }
       }
       leaf advertise-community {
         type "boolean";
         default "false";
         description
           "Enable/disable advertise the community attribute to a peer or a peer"+
           " group.";
       }
       leaf reflect-client {
         type "boolean";
         default "false";
         description
           "Enable/disable the local device as a route reflector (RR) and a peer"+
           " or peer group as its client. This configuration is applicable "+
           "between IBGP peers only. The configurations of RRs and its clients "+
           "in an address family are valid only in this address family. "+
           "Therefore, it is recommended to configure RRs and its clients in the"+
           " specified address family that is required.";
       }
       leaf import-as-path-filter {
         type "leafref" {
           path "/rtp:routing-policy/rtp:as-path-filters/rtp:as-path-filter/rtp:"+
                "name";
         }
         description
           "Apply an AS_Path-based filtering policy to the routes received from "+
           "a specified peer. The policy can be identified with a name or "+
           "number, and the number ranges from 1 to 256. By default, no such "+
           "policy is specified. Therefore, all BGP routes can be accepted.";
       }
       leaf export-as-path-filter {
         type "leafref" {
           path "/rtp:routing-policy/rtp:as-path-filters/rtp:as-path-filter/rtp:"+
                "name";
         }
         description
           "Apply an AS_Path-based filtering policy to the routes to be "+
           "advertised to a specified peer. The policy can be identified with a "+
           "name or number, and the number ranges from 1 to 256. By default, no "+
           "such policy is specified. Therefore, all BGP routes can be "+
           "advertised.";
       }
       leaf advertise-c-multicast-route {
         type "boolean";
         default "false";
         description
           "Enable/disable advertise C-multicast route directional, only "+
           "advertise to the neighbor which is matched the nexthop in intra-AD "+
           "route.";
       }
       leaf nexthop-configure {
         type "bgp:nexthop-configuration-type";
         must "../nexthop-configure='local'";
         description
           "Both the next-hop-local mode and next-hop-invariable mode are "+
           "available when the peer address family is the VPNv4/VPNV6/L2VPN AD "+
           "address family. Only the next-hop-local mode is available when the "+
           "peer address family is not VPNv4/VPNV6/L2VPN AD address family. In "+
           "next-hop-local mode, you can configure a BGP speaker to set its IP "+
           "address of as the next hop of the routes to be advertised to IBGP "+
           "peers or IBGP peer groups. In next-hop-invariable mode, you can "+
           "configure PEs in different ASs not to change the next hop of routes "+
           "when the PEs advertise the routes to their EBGP peers and use the "+
           "next hop addresses of IGP routes to advertise imported IGP routes to"+
           " IBGP peers. By default, when a BGP speaker advertises routes to "+
           "EBGP peers and imported IGP routes to IBGP peers, the BGP speaker "+
           "changes the next hop to its interface address. If the value of "+
           "nexthop-configure is set to local, the configuration does not take "+
           "effect in the current address family.";
       }
       leaf nexthop-effective {
         when "../nexthop-configure='local'";
         type "boolean";
         default "false";
         description
           "Enable/disable the next hop of peer takes effect in the RR "+
           "scenario.";
       }
       choice import-policy-type {
         description
           "Set route policy or filter.";
         case rtp-ref {
           description
             "Route policy.";
           leaf import-policy {
             type "leafref" {
               path "/rtp:routing-policy/rtp:policy-definitions/rtp:policy-defin"+
                    "ition/rtp:name";
             }
             description
               "Specify the filtering policy applied to the routes learned from "+
               "a peer. By default, no such policy is specified.";
           }
         }
         case xpl-ref {
           description
             "Route filter.";
           container import-filter {
             description
               "Configure an import route-filter to filter the routes received "+
               "from peers. By default, no route-filter is specified to filter "+
               "the routes imported from peers.";
             leaf name {
               type "leafref" {
                 path "/xpl:xpl/xpl:route-filters/xpl:route-filter/xpl:name";
               }
               description
                 "Specify an import route-filter name.";
             }
             leaf parameter {
               when "../name";
               type "xpl:filter-parameter-type";
               description
                 "Specify an import route-filter parameter.";
             }
           }
         }
       }
       choice export-policy-type {
         description
           "Set route policy or filter.";
         case rtp-ref {
           description
             "Route policy.";
           leaf export-policy {
             type "leafref" {
               path "/rtp:routing-policy/rtp:policy-definitions/rtp:policy-defin"+
                    "ition/rtp:name";
             }
             description
               "Specify the filtering policy applied to the routes to be "+
               "advertised to a peer. By default, no such policy is specified.";
           }
         }
         case xpl-ref {
           description
             "Route filter.";
           container export-filter {
             description
               "Configure an export route-filter to filter the routes to be "+
               "advertised to peers. By default, no route-filter is specified to"+
               " filter the routes to be advertised to peers.";
             leaf name {
               type "leafref" {
                 path "/xpl:xpl/xpl:route-filters/xpl:route-filter/xpl:name";
               }
               description
                 "Specify an export route-filter name.";
             }
             leaf parameter {
               when "../name";
               type "xpl:filter-parameter-type";
               description
                 "Specify an export route-filter parameter.";
             }
           }
         }
       }
       leaf advertise-large-community {
         type "bgp:peer-comm-config-type";
         default "default";
         description
           "Enable large-community attribute advertisement. The Link-state "+
           "address family and the RPD address family do not support this "+
           "element.";
       }
       leaf advertise-large-community-state {
         type "boolean";
         default "false";
         config "false";
         description
           "Whether large-community attribute advertisement is enabled on a "+
           "peer. The Link-state address family and the RPD address family do "+
           "not support this element.";
       }
       leaf route-update-interval {
         type "uint16" {
           range "0..600";
         }
         units "s";
         description
           "Specify the minimum interval at which Update packets are sent. By "+
           "default, the interval at which Update packets are sent to IBGP peers"+
           " is 15s, \nand the interval at which Update packets are sent to EBGP"+
           " peers is 30s. When routes change, a router will send Update packets"+
           " to notify its peers. \nIf a route changes frequently, you can set "+
           "an interval at which Update packets are sent to prevent the router "+
           "from sending Update packets each time the route changes. \nThis "+
           "configuration is valid only to the routes learned from peers.";
         ext:dynamic-default;
       }
       leaf update-group-independent {
         type "bgp:peer-comm-config-type";
         default "default";
         description
           "Enable/disable the peer which can reside in an independent peer "+
           "group.";
       }
       leaf update-group-independent-state {
         type "boolean";
         config "false";
         description
           "Whether the peer can reside in an independent peer group.";
       }
       leaf add-path-mode {
         type "bgp:add-path-cap-type";
         default "null";
         description
           "Enable Add-Path route advertisement to a peer.";
       }
       leaf add-path-number {
         type "uint8" {
           range "2..64";
         }
         description
           "Number of Add-Path routes that can be advertised to a peer.";
       }
       container route-limit {
         description
           "Configure parameters of routes limited from this peer.";
         leaf number {
           type "uint32" {
             range "1..4294967295";
           }
           description
             "Configure the maximum number of routes that can be accepted from a"+
             " peer.";
         }
         leaf percent {
           when "../number";
           type "uint8" {
             range "1..100";
           }
           default "75";
           description
             "Specify the percentage of routes when a router starts to generate "+
             "an alarm.";
         }
         leaf type {
           when "../number";
           type "bgp:route-limit-type";
           must "(../type='idle-timeout' and ../idle-timeout) or (../type!='idle"+
                "-timeout')";
           default "noparameter";
           description
             "Set the processing method as alert-only, idle-forever, or "+
             "idle-timeout when the number of routes exceeds the set threshold. "+
             "When alert-only is used, only an alarm is generated when the "+
             "number of routes exceeds the threshold. In this case, new routes "+
             "are no longer accepted. When idle-forever is used, connections are"+
             " not automatically reestablished after being cut off until BGP "+
             "connections are reset if the number of routes exceeds the set "+
             "threshold. When idle-timeout is used and the idle-timeout timer is"+
             " specified, the connections are automatically reestablished after "+
             "being cut off if the number of routes exceeds the set threshold. "+
             "You can reset BGP connections to reestablish the connections "+
             "before the idle-timeout times expires.";
         }
         leaf idle-timeout {
           when "../type='idle-timeout'";
           type "uint16" {
             range "1..1200";
           }
           units "min";
           description
             "Specify the value of the idle-timeout timer to automatically "+
             "reestablish the connections after they are cut off when the number"+
             " of routes exceeds the set threshold.";
         }
       }
       container path-attribute-treats {
         description
           "List of modes in which specified path attributes are processed.";
         list path-attribute-treat {
           must "discard-id-map or withdraw-id-map or unknown-id-map";
           key "treat-type";
           description
             "Configure mode in which specified path attributes are processed.";
           leaf treat-type {
             type "bgp:path-attr-treat-type";
             description
               "Mode in which specified path attributes are processed.";
           }
           leaf discard-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a discard attribute ID list. The attribute IDs which are"+
               " not supported as follows: 1 (ORIGIN), 2 (AS_PATH), 3 (NEXT_HOP)"+
               ", 4 (MED), 5 (LOCAL_PREF), 6 (ATOMICAGGREGATE), 7 (AGGREGATOR), "+
               "8 (COMMUNITY), 9 (ORIGINATOR_ID), 10 (CLUSTER_LIST), 14 "+
               "(MP_REACH_NLRI), 15 (MP_UNREACH_NLRI), 17 (AS4PATH), 18 "+
               "(AS4AGGREGATOR).";
           }
           leaf withdraw-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify a withdraw attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
           leaf unknown-id-map {
             type "pub-type:id-range" {
               pattern "((25[0-5]|2[0-4][0-9]|1[0-9][0-9]|[1-9][0-9]|[0-9])?(-(2"+
                       "5[0-5]|2[0-4][0-9]|1[0-9][0-9]|[1-9][0-9]|[0-9]))?(,((25"+
                       "[0-5]|2[0-4][0-9]|1[0-9][0-9]|[1-9][0-9]|[0-9])(-(25[0-5"+
                       "]|2[0-4][0-9]|1[0-9][0-9]|[1-9][0-9]|[0-9]))?))*)|(((["+
                       "\\+|\\-](25[0-5]|2[0-4][0-9]|1[0-9][0-9]|[1-9][0-9]|"+
                       "[0-9]))|([\\+|\\-]\\((25[0-5]|2[0-4][0-9]|1[0-9][0"+
                       "-9]|[1-9][0-9]|[0-9])-(25[0-5]|2[0-4][0-9]|1[0-9][0-9]|["+
                       "1-9][0-9]|[0-9])\\)))?(,(([\\+|\\-](25[0-5]|2[0-4]"+
                       "[0-9]|1[0-9][0-9]|[1-9][0-9]|[0-9]))|([\\+|\\-]\\("+
                       "(25[0-5]|2[0-4][0-9]|1[0-9][0-9]|[1-9][0-9]|[0-9])-(25[0"+
                       "-5]|2[0-4][0-9]|1[0-9][0-9]|[1-9][0-9]|[0-9])\\))))*)";
               ext:value-range "0..255";
             }
             description
               "Specify an unknown attribute ID list. The attribute IDs which "+
               "are not supported as follows: 1 (ORIGIN), 2 (AS_PATH), 3 "+
               "(NEXT_HOP), 4 (MED), 5 (LOCAL_PREF), 6 (ATOMICAGGREGATE), 7 "+
               "(AGGREGATOR), 8 (COMMUNITY), 9 (ORIGINATOR_ID), 10 (CLUSTER_LIST"+
               "), 14 (MP_REACH_NLRI), 15 (MP_UNREACH_NLRI), 17 (AS4PATH), 18 "+
               "(AS4AGGREGATOR).";
           }
         }
       }
     }
   }
   augment "/bgp:bgp/bgp:base-process/bgp-rt:bgp-route" {
     description
       "BGP MVPN address family routes information.";
     container ipv4-mvpn {
       config "false";
       description
         "Statistics of BGP routes information of IPv4-mvpn address family.";
       container ng-type1-routes {
         description
           "List of displayed BGP Intra-AS I-PMSI A-D route information.";
         list ng-type1-route {
           key "vpn-name route-distinguisher prefix from route-type";
           description
             "Statistics of BGP Intra-AS I-PMSI A-D route.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
           leaf path-as {
             type "string" {
               length "1..300";
             }
             description
               "List of the AS_Paths that packets pass through.";
           }
           leaf sending-peers {
             type "string" {
               length "1..300";
             }
             description
               "List of route sending peers.";
           }
           leaf community {
             type "string" {
               length "1..300";
             }
             description
               "Community attribute.";
           }
           leaf large-community {
             type "string" {
               length "1..200";
             }
             description
               "Large-community attribute information.";
           }
           leaf ext-community {
             type "string" {
               length "1..300";
             }
             description
               "Extended community attribute.";
           }
           leaf cluster-list {
             type "string" {
               length "1..300";
             }
             description
               "List of cluster IDs.";
           }
           leaf as-ip {
             type "string" {
               length "1..300";
             }
             description
               "Ng route prefix information.";
           }
           leaf pmsi {
             type "string" {
               length "1..300";
             }
             description
               "PMSI attribute.";
           }
         }
       }
       container ng-type3-routes {
         description
           "List of displayed BGP S-PMSI A-D route.";
         list ng-type3-route {
           key "vpn-name path-id route-distinguisher prefix from route-type";
           description
             "Statistics of BGP S-PMSI A-D route.";
           leaf vpn-name {
             type "leafref" {
               path "/ni:network-instance/ni:instances/ni:instance/ni:name";
             }
             description
               "VPN name of a BGP instance.";
           }
           leaf path-id {
             type "string" {
               length "1..50";
             }
             description
               "Path ID.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
         }
       }
       container ng-type4-routes {
         description
           "List of displayed BGP Leaf A-D route.";
         list ng-type4-route {
           key "vpn-name path-id route-distinguisher prefix from route-type";
           description
             "Statistics of BGP Leaf A-D route.";
           leaf vpn-name {
             type "leafref" {
               path "/ni:network-instance/ni:instances/ni:instance/ni:name";
             }
             description
               "VPN name of a BGP instance.";
           }
           leaf path-id {
             type "string" {
               length "1..50";
             }
             description
               "Path ID.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
         }
       }
       container ng-type5-routes {
         description
           "List of displayed BGP Source Active A-D route.";
         list ng-type5-route {
           key "vpn-name path-id route-distinguisher prefix from route-type";
           description
             "Statistics of BGP Source Active A-D route.";
           leaf vpn-name {
             type "leafref" {
               path "/ni:network-instance/ni:instances/ni:instance/ni:name";
             }
             description
               "VPN name of a BGP instance.";
           }
           leaf path-id {
             type "string" {
               length "1..50";
             }
             description
               "Path ID.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
         }
       }
       container ng-type6-routes {
         description
           "List of displayed BGP Shared Tree Join route.";
         list ng-type6-route {
           key "vpn-name path-id route-distinguisher prefix from route-type";
           description
             "Statistics of BGP Shared Tree Join route.";
           leaf vpn-name {
             type "leafref" {
               path "/ni:network-instance/ni:instances/ni:instance/ni:name";
             }
             description
               "VPN name of a BGP instance.";
           }
           leaf path-id {
             type "string" {
               length "1..50";
             }
             description
               "Path ID.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
         }
       }
       container ng-type7-routes {
         description
           "List of displayed BGP source tree join route information.";
         list ng-type7-route {
           key "vpn-name route-distinguisher prefix from route-type";
           description
             "Statistics of BGP source tree join route.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
           leaf path-as {
             type "string" {
               length "1..300";
             }
             description
               "List of the AS_Paths that packets pass through.";
           }
           leaf sending-peers {
             type "string" {
               length "1..300";
             }
             description
               "List of route sending peers.";
           }
           leaf community {
             type "string" {
               length "1..300";
             }
             description
               "Community attribute.";
           }
           leaf large-community {
             type "string" {
               length "1..200";
             }
             description
               "Large-community attribute information.";
           }
           leaf ext-community {
             type "string" {
               length "1..300";
             }
             description
               "Extended community attribute.";
           }
           leaf cluster-list {
             type "string" {
               length "1..300";
             }
             description
               "List of cluster IDs.";
           }
           leaf as-ip {
             type "string" {
               length "1..300";
             }
             description
               "Ng route prefix information.";
           }
         }
       }
       container statistics {
         description
           "List of BGP routes statistics information of the address family.";
         list statistic {
           key "vpn-name";
           description
             "BGP address family routes statistics.";
           leaf vpn-name {
             type "leafref" {
               path "/ni:network-instance/ni:instances/ni:instance/ni:name";
             }
             description
               "VPN name of a BGP instance.";
           }
           leaf total-number {
             type "uint32";
             description
               "Total number of routes.";
           }
           leaf ng-type1-route-number {
             type "uint32";
             description
               "Number of Intra-AS I-PMSI A-D routes.";
           }
           leaf ng-type2-route-number {
             type "uint32";
             description
               "Number of Inter-AS I-PMSI A-D routes.";
           }
           leaf ng-type3-route-number {
             type "uint32";
             description
               "Number of S-PMSI A-D routes.";
           }
           leaf ng-type4-route-number {
             type "uint32";
             description
               "Number of Leaf A-D routes.";
           }
           leaf ng-type5-route-number {
             type "uint32";
             description
               "Number of Source Active A-D routes.";
           }
           leaf ng-type6-route-number {
             type "uint32";
             description
               "Number of Shared Tree Join routes.";
           }
           leaf ng-type7-route-number {
             type "uint32";
             description
               "Number of Source Tree Join routes.";
           }
         }
       }
     }
     container ipv6-mvpn {
       config "false";
       description
         "Statistics of BGP routes information of IPv6-mvpn address family.";
       container ng-type1-routes {
         description
           "List of displayed BGP Intra-AS I-PMSI A-D route information.";
         list ng-type1-route {
           key "vpn-name route-distinguisher prefix from route-type";
           description
             "Statistics of BGP Intra-AS I-PMSI A-D route.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
           leaf path-as {
             type "string" {
               length "1..300";
             }
             description
               "List of the AS_Paths that packets pass through.";
           }
           leaf sending-peers {
             type "string" {
               length "1..300";
             }
             description
               "List of route sending peers.";
           }
           leaf community {
             type "string" {
               length "1..300";
             }
             description
               "Community attribute.";
           }
           leaf large-community {
             type "string" {
               length "1..200";
             }
             description
               "Large-community attribute information.";
           }
           leaf ext-community {
             type "string" {
               length "1..300";
             }
             description
               "Extended community attribute.";
           }
           leaf cluster-list {
             type "string" {
               length "1..300";
             }
             description
               "List of cluster IDs.";
           }
           leaf as-ip {
             type "string" {
               length "1..300";
             }
             description
               "Ng route prefix information.";
           }
           leaf pmsi {
             type "string" {
               length "1..300";
             }
             description
               "PMSI attribute.";
           }
         }
       }
       container ng-type3-routes {
         description
           "List of displayed BGP S-PMSI A-D route.";
         list ng-type3-route {
           key "vpn-name path-id route-distinguisher prefix from route-type";
           description
             "Statistics of BGP S-PMSI A-D route.";
           leaf vpn-name {
             type "leafref" {
               path "/ni:network-instance/ni:instances/ni:instance/ni:name";
             }
             description
               "VPN name of a BGP instance.";
           }
           leaf path-id {
             type "string" {
               length "1..50";
             }
             description
               "Path ID.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
         }
       }
       container ng-type4-routes {
         description
           "List of displayed BGP Leaf A-D route.";
         list ng-type4-route {
           key "vpn-name path-id route-distinguisher prefix from route-type";
           description
             "Statistics of BGP Leaf A-D route.";
           leaf vpn-name {
             type "leafref" {
               path "/ni:network-instance/ni:instances/ni:instance/ni:name";
             }
             description
               "VPN name of a BGP instance.";
           }
           leaf path-id {
             type "string" {
               length "1..50";
             }
             description
               "Path ID.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
         }
       }
       container ng-type5-routes {
         description
           "List of displayed BGP Source Active A-D route.";
         list ng-type5-route {
           key "vpn-name path-id route-distinguisher prefix from route-type";
           description
             "Statistics of BGP Source Active A-D route.";
           leaf vpn-name {
             type "leafref" {
               path "/ni:network-instance/ni:instances/ni:instance/ni:name";
             }
             description
               "VPN name of a BGP instance.";
           }
           leaf path-id {
             type "string" {
               length "1..50";
             }
             description
               "Path ID.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
         }
       }
       container ng-type6-routes {
         description
           "List of displayed BGP Shared Tree Join route.";
         list ng-type6-route {
           key "vpn-name path-id route-distinguisher prefix from route-type";
           description
             "Statistics of BGP Shared Tree Join route.";
           leaf vpn-name {
             type "leafref" {
               path "/ni:network-instance/ni:instances/ni:instance/ni:name";
             }
             description
               "VPN name of a BGP instance.";
           }
           leaf path-id {
             type "string" {
               length "1..50";
             }
             description
               "Path ID.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
         }
       }
       container ng-type7-routes {
         description
           "List of displayed BGP source tree join route information.";
         list ng-type7-route {
           key "vpn-name route-distinguisher prefix from route-type";
           description
             "Statistics of BGP source tree join route.";
           leaf vpn-name {
             type "leafref" {
               path "/ni:network-instance/ni:instances/ni:instance/ni:name";
             }
             description
               "VPN name of a BGP instance.";
           }
           leaf route-distinguisher {
             type "string" {
               length "1..22";
             }
             description
               "Route distinguisher.";
           }
           leaf prefix {
             type "string" {
               length "1..255";
             }
             description
               "Prefix of a BGP route.";
           }
           leaf from {
             type "inet:ip-address-no-zone";
             description
               "Source peer that sends a route.";
           }
           leaf route-type {
             type "bgp-rt:bgp-route-type-flag";
             description
               "Route type.";
           }
           leaf ng-route-type {
             type "string" {
               length "1..50";
             }
             description
               "Route type.";
           }
           leaf im-table-id {
             type "uint32";
             description
               "ID of the routing table to which routes are imported.";
           }
           leaf nexthop {
             type "inet:ip-address-no-zone";
             description
               "Next hop address to which packets are forwarded.";
           }
           leaf local-preference {
             type "uint32";
             description
               "Local priority. The attribute is only fit for the routes from "+
               "IBGP peer, not suit for which of EBGP peer.";
           }
           leaf preferred-value {
             type "uint32";
             description
               "Preferred value of a protocol.";
           }
           leaf preference {
             type "uint8";
             description
               "Priority of BGP routes.";
           }
           leaf origin {
             type "bgp-rt:bgp-origin-type";
             description
               "Route origin.";
           }
           leaf med {
             type "uint32";
             description
               "Route MED.The attribute is only fit for the routes from EBGP "+
               "peer, not suit for which of IBGP peer.";
           }
           leaf flag-string {
             type "string" {
               length "1..100";
             }
             description
               "Route flag that contains a string of characters.";
           }
           leaf worse-reason {
             type "string" {
               length "1..50";
             }
             description
               "Reason why a route is not selected.";
           }
           leaf time {
             type "pub-type:time-tick";
             description
               "Time stamp of a route.";
           }
           leaf interface-name {
             type "pub-type:if-name";
             description
               "Name of the outbound interface of a route.";
           }
           leaf originator {
             type "inet:ip-address-no-zone";
             description
               "Router ID of the route initiator.";
           }
           leaf remote-route-id {
             type "inet:ipv4-address-no-zone";
             description
               "Router ID of a peer.";
           }
           leaf relay-nexthop {
             type "inet:ip-address-no-zone";
             description
               "Next hop to which a route is iterated.";
           }
           leaf relay-tunnel-name {
             type "string" {
               length "1..64";
             }
             description
               "Name of a tunnel to which a route is iterated.";
           }
           leaf in-label {
             type "uint32";
             description
               "In-label.";
           }
           leaf out-label {
             type "uint32";
             description
               "Out-label.";
           }
           leaf advertise-nexthop {
             type "inet:ip-address-no-zone";
             description
               "Advertise next hop.";
           }
           leaf path-as {
             type "string" {
               length "1..300";
             }
             description
               "List of the AS_Paths that packets pass through.";
           }
           leaf sending-peers {
             type "string" {
               length "1..300";
             }
             description
               "List of route sending peers.";
           }
           leaf community {
             type "string" {
               length "1..300";
             }
             description
               "Community attribute.";
           }
           leaf large-community {
             type "string" {
               length "1..200";
             }
             description
               "Large-community attribute information.";
           }
           leaf ext-community {
             type "string" {
               length "1..300";
             }
             description
               "Extended community attribute.";
           }
           leaf cluster-list {
             type "string" {
               length "1..300";
             }
             description
               "List of cluster IDs.";
           }
           leaf as-ip {
             type "string" {
               length "1..300";
             }
             description
               "Ng route prefix information.";
           }
         }
       }
       container statistics {
         description
           "List of BGP routes statistics information of the address family.";
         list statistic {
           key "vpn-name";
           description
             "BGP address family routes statistics.";
           leaf vpn-name {
             type "leafref" {
               path "/ni:network-instance/ni:instances/ni:instance/ni:name";
             }
             description
               "VPN name of a BGP instance.";
           }
           leaf total-number {
             type "uint32";
             description
               "Total number of routes.";
           }
           leaf ng-type1-route-number {
             type "uint32";
             description
               "Number of Intra-AS I-PMSI A-D routes.";
           }
           leaf ng-type2-route-number {
             type "uint32";
             description
               "Number of Inter-AS I-PMSI A-D routes.";
           }
           leaf ng-type3-route-number {
             type "uint32";
             description
               "Number of S-PMSI A-D routes.";
           }
           leaf ng-type4-route-number {
             type "uint32";
             description
               "Number of Leaf A-D routes.";
           }
           leaf ng-type5-route-number {
             type "uint32";
             description
               "Number of Source Active A-D routes.";
           }
           leaf ng-type6-route-number {
             type "uint32";
             description
               "Number of Shared Tree Join routes.";
           }
           leaf ng-type7-route-number {
             type "uint32";
             description
               "Number of Source Tree Join routes.";
           }
         }
       }
     }
   }
 }

submodule openconfig-mpls-static {
   yang-version "1";
   belongs-to openconfig-mpls {
     prefix "mpls";
   }
   import openconfig-extensions {
     prefix "oc-ext";
   }
   organization
     "OpenConfig working group";
   contact
     "OpenConfig working group\nnetopenconfig@googlegroups.com";
   description
     "Defines static LSP configuration";
   oc-ext:openconfig-version "3.0.1";
   revision "2018-11-21" {
     description
       "Add OpenConfig module metadata extensions.";
     reference
       "3.0.1";
   }
   revision "2018-07-02" {
     description
       "Add new RSVP-TE statistics, remove associated-rsvp-session\nleaf. Remove"+
       " use of date-and-time.";
     reference
       "3.0.0";
   }
   revision "2018-06-16" {
     description
       "Included attributes for base LDP configuration.";
     reference
       "2.6.0";
   }
   revision "2018-06-13" {
     description
       "Add ttl-propagation to global MPLS config";
     reference
       "2.5.0";
   }
   revision "2018-06-05" {
     description
       "Fixed bugs in when statements on RSVP-TE attributes";
     reference
       "2.4.2";
   }
   revision "2017-08-24" {
     description
       "Minor formatting fixes.";
     reference
       "2.4.1";
   }
   revision "2017-06-21" {
     description
       "Add TC bits typedef.";
     reference
       "2.4.0";
   }
   revision "2017-03-22" {
     description
       "Add RSVP calculated-absolute-subscription-bw";
     reference
       "2.3.0";
   }
   revision "2017-01-26" {
     description
       "Add RSVP Tspec, clarify units for RSVP, remove unused LDP";
     reference
       "2.2.0";
   }
   revision "2016-12-15" {
     description
       "Add additional MPLS parameters";
     reference
       "2.1.0";
   }
   revision "2016-09-01" {
     description
       "Revisions based on implementation feedback";
     reference
       "2.0.0";
   }
   revision "2016-08-08" {
     description
       "Public release of MPLS models";
     reference
       "1.0.1";
   }
 }

module openconfig-vlan-types {
   yang-version "1";
   namespace "http://openconfig.net/yang/vlan-types";
   prefix "oc-vlan-types";
   import openconfig-extensions {
     prefix "oc-ext";
   }
   organization
     "OpenConfig working group";
   contact
     "OpenConfig working group\nnetopenconfig@googlegroups.com";
   description
     "This module defines configuration and state variables for VLANs,\nin "+
     "addition to VLAN parameters associated with interfaces";
   oc-ext:openconfig-version "3.1.0";
   revision "2019-01-31" {
     description
       "Add TPID_ANY wildcard match and a QinQ list type.";
     reference
       "3.1.0";
   }
   revision "2018-11-21" {
     description
       "Add OpenConfig module metadata extensions.";
     reference
       "3.0.1";
   }
   revision "2018-02-14" {
     description
       "Fix bug with name of 802.1ad identity.";
     reference
       "3.0.0";
   }
   revision "2017-07-14" {
     description
       "Move top-level vlan data to network-instance; Update\nidentities to "+
       "comply to style guide; fixed pattern\nquoting; corrected trunk vlan "+
       "types; added TPID config to\nbase interface.";
     reference
       "2.0.0";
   }
   revision "2016-05-26" {
     description
       "OpenConfig public release";
     reference
       "1.0.2";
   }
   oc-ext:regexp-posix;
   oc-ext:catalog-organization "openconfig";
   oc-ext:origin "openconfig";
   identity TPID_TYPES {
     description
       "Base identity for TPID values that can be matched or that override\nthe "+
       "VLAN ethertype value";
   }
   identity TPID_0X8100 {
     base "TPID_TYPES";
     description
       "Default TPID value for 802.1q single-tagged VLANs.";
   }
   identity TPID_0X88A8 {
     base "TPID_TYPES";
     description
       "TPID value for 802.1ad provider bridging, QinQ or\nstacked VLANs.";
   }
   identity TPID_0X9100 {
     base "TPID_TYPES";
     description
       "Alternate TPID value.";
   }
   identity TPID_0X9200 {
     base "TPID_TYPES";
     description
       "Alternate TPID value.";
   }
   identity TPID_ANY {
     base "TPID_TYPES";
     description
       "A wildcard that matches any of the generally used TPID values\nfor "+
       "singly- or multiply-tagged VLANs. Equivalent to matching\nany of "+
       "TPID_0X8100, TPID_0X88A8, TPID_0X9100 and TPID_0x9200.\nThis value is "+
       "only applicable where the TPID of a packet is\nbeing matched.";
   }
   typedef vlan-id {
     type "uint16" {
       range "1..4094";
     }
     description
       "Type definition representing a single-tagged VLAN";
   }
 }

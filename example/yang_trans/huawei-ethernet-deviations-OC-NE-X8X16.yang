/*
Copyright (C) 2020 Huawei Technologies Co., Ltd. All rights reserved.
*/

 module huawei-ethernet-deviations-OC-NE-X8X16 {
   namespace "urn:huawei:yang:huawei-ethernet-deviations-OC-NE-X8X16";
   prefix "ethernet-devs-OC-NE-X8X16";
   import huawei-ethernet {
     prefix "ethernet";
   }
   import huawei-ifm {
     prefix "ifm";
   }
   import huawei-vlan {
     prefix "vlan";
   }
   organization
     "Huawei Technologies Co., Ltd.";
   contact
     "Huawei Industrial Base\nBantian, Longgang\nShenzhen 518129\nPeople's "+
     "Republic of China\nWebsite: http://www.huawei.com\nEmail: support@huawei.c"+
     "om";
   description
     "VLAN member interfaces and QinQ.";
   revision "2020-04-26" {
     description
       "Initial revision.";
     reference
       "Huawei private.";
   }
   deviation "/ifm:ifm/ifm:interfaces/ifm:interface/ethernet:ethernet/ethernet:m"+
             "ain-interface/ethernet:l2-attribute/ethernet:vlan-mappings/etherne"+
             "t:vlan-mapping/ethernet:mapping-vlan" {
     deviate "add" {
       must "/vlan:vlan/vlan:vlans/vlan:vlan[vlan:id=current()]/vlan:type!='supe"+
            "r'";
     }
   }
   deviation "/ifm:ifm/ifm:interfaces/ifm:interface/ethernet:ethernet/ethernet:l"+
             "3-sub-interface/ethernet:flow-type/ethernet:qinq-termination/ether"+
             "net:qinq-termination/ethernet:remark-8021p/ethernet:remark-type" {
     deviate "add" {
       must "(../remark-type='trust-pe-8021p') or (/ifm:ifm/ifm:interfaces/ifm:i"+
            "nterface[ifm:name=current()/../../../../../ifm:name]/ifm:type!='PW-"+
            "VE')";
     }
   }
   deviation "/ifm:ifm/ifm:interfaces/ifm:interface/ethernet:ethernet/ethernet:m"+
             "ain-interface/ethernet:encapsulation/ethernet:pvid" {
     deviate "replace" {
       type "uint16" {
         range "1..4094";
       }
     }
   }
 }

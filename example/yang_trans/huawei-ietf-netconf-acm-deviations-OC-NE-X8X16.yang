/*
Copyright (C) 2021 Huawei Technologies Co., Ltd. All rights reserved.
*/

 module huawei-ietf-netconf-acm-deviations-OC-NE-X8X16 {
   namespace "urn:huawei:yang:huawei-ietf-netconf-acm-deviations-OC-NE-X8X16";
   prefix "nacm-devs-OC-NE-X8X16";
   import ietf-netconf-acm {
     prefix "nacm";
   }
   import ietf-yang-types {
     prefix "yang";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for ietf-netconf-acm module.";
   revision "2021-05-07" {
     description
       "Initial revision.";
     reference
       "Huawei private.";
   }
   typedef group-name-type-deviations {
     type "string" {
       length "1..max";
       pattern "[^\\*].*";
     }
     description
       "Name of administrative group to which\nusers can be assigned.";
   }
   typedef node-instance-identifier-deviations {
     type "yang:xpath1.0";
     description
       "Path expression used to represent a special\ndata node instance "+
       "identifier string.\nA node-instance-identifier value is an\nunrestricted"+
       " YANG instance-identifier expression.\nAll the same rules as an "+
       "instance-identifier apply\nexcept predicates for keys are optional.\nIf "+
       "a key predicate is missing, then the node-instance-identifier\nrepresent"+
       "s all possible server instances for that key.\nThis XPath expression is "+
       "evaluated in the following context:\n  The set of namespace declarations"+
       " are those in scope on\n   the leaf element where this type is used.\n  "+
       "The set of variable bindings contains one variable,\n   'USER', which "+
       "contains the name of the user of the current\n    session.\n  The "+
       "function library is the core function library, but\n   note that due to "+
       "the syntax restrictions of an\n   instance-identifier, no functions are "+
       "allowed.\n  The context node is the root node in the data tree.";
   }
   typedef user-name-type-deviations {
     type "string" {
       length "1..max";
     }
     description
       "General Purpose Username string.";
   }
   deviation "/nacm:nacm/nacm:enable-nacm" {
     deviate "replace" {
       default "false";
     }
   }
   deviation "/nacm:nacm/nacm:read-default" {
     deviate "replace" {
       default "deny";
     }
   }
   deviation "/nacm:nacm/nacm:exec-default" {
     deviate "replace" {
       default "deny";
     }
   }
   deviation "/nacm:nacm/nacm:groups/nacm:group" {
     deviate "add" {
       max-elements "16";
     }
   }
   deviation "/nacm:nacm/nacm:groups/nacm:group/nacm:name" {
     deviate "replace" {
       type "nacm-devs-OC-NE-X8X16:group-name-type-deviations" {
         length "1..32";
       }
     }
   }
   deviation "/nacm:nacm/nacm:groups/nacm:group/nacm:user-name" {
     deviate "replace" {
       type "nacm-devs-OC-NE-X8X16:user-name-type-deviations" {
         length "1..255";
       }
     }
   }
   deviation "/nacm:nacm/nacm:rule-list" {
     deviate "add" {
       max-elements "64";
     }
   }
   deviation "/nacm:nacm/nacm:rule-list/nacm:name" {
     deviate "replace" {
       type "string" {
         length "1..15";
       }
     }
   }
   deviation "/nacm:nacm/nacm:rule-list/nacm:group" {
     deviate "replace" {
       type "union" {
         type "nacm:matchall-string-type";
         type "string" {
           length "1..32";
           pattern "[^\\*].*";
         }
       }
     }
     deviate "add" {
       max-elements "16";
     }
   }
   deviation "/nacm:nacm/nacm:rule-list/nacm:rule" {
     deviate "add" {
       max-elements "256";
     }
   }
   deviation "/nacm:nacm/nacm:rule-list/nacm:rule/nacm:name" {
     deviate "replace" {
       type "string" {
         length "1..15";
       }
     }
   }
   deviation "/nacm:nacm/nacm:rule-list/nacm:rule/nacm:module-name" {
     deviate "replace" {
       type "union" {
         type "nacm:matchall-string-type";
         type "string" {
           length "1..63";
         }
       }
     }
   }
   deviation "/nacm:nacm/nacm:rule-list/nacm:rule/nacm:rule-type/nacm:protocol-o"+
             "peration/nacm:rpc-name" {
     deviate "replace" {
       type "union" {
         type "nacm:matchall-string-type";
         type "string" {
           length "1..63";
         }
       }
     }
   }
   deviation "/nacm:nacm/nacm:rule-list/nacm:rule/nacm:rule-type/nacm:notificati"+
             "on/nacm:notification-name" {
     deviate "replace" {
       type "union" {
         type "nacm:matchall-string-type";
         type "string" {
           length "1..63";
         }
       }
     }
   }
   deviation "/nacm:nacm/nacm:rule-list/nacm:rule/nacm:rule-type/nacm:data-node/"+
             "nacm:path" {
     deviate "replace" {
       type "nacm-devs-OC-NE-X8X16:node-instance-identifier-deviations" {
         length "1..1023";
       }
     }
   }
   deviation "/nacm:nacm/nacm:rule-list/nacm:rule/nacm:comment" {
     deviate "replace" {
       type "string" {
         length "1..63";
       }
     }
   }
 }

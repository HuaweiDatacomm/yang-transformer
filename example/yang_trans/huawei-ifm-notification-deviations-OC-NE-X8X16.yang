/*
Copyright (C) 2019 Huawei Technologies Co., Ltd. All rights reserved.
*/

 module huawei-ifm-notification-deviations-OC-NE-X8X16 {
   namespace "urn:huawei:yang:huawei-ifm-notification-deviations-OC-NE-X8X16";
   prefix "ifm-notification-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-ifm-notification "+
     "module.";
   revision "2019-11-06" {
     description
       "Initial revision.";
     reference
       "Huawei private.";
   }
 }

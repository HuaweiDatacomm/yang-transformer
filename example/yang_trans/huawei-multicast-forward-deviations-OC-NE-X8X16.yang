/*
Copyright (C) 2021 Huawei Technologies Co., Ltd. All rights reserved.
*/

 module huawei-multicast-forward-deviations-OC-NE-X8X16 {
   namespace "urn:huawei:yang:huawei-multicast-forward-deviations-OC-NE-X8X16";
   prefix "multicast-forward-devs-OC-NE-X8X16";
   import huawei-multicast-forward {
     prefix "multicast-forward";
   }
   import huawei-bd {
     prefix "bd";
   }
   import huawei-l2vpn {
     prefix "l2vpn";
   }
   import huawei-vlan {
     prefix "vlan";
   }
   import huawei-igmp-mld-snooping {
     prefix "ims";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-multicast-forward "+
     "module.";
   revision "2021-05-07" {
     description
       "Initial revision.";
     reference
       "Huawei private.";
   }
   deviation "/multicast-forward:multicast-forward/multicast-forward:spatial-mul"+
             "ticast/multicast-forward:ipv4-multicast-bandwidths/multicast-forwa"+
             "rd:ipv4-multicast-bandwidth/multicast-forward:bandwidth" {
     deviate "replace" {
       type "uint64" {
         range "1..40000000";
       }
     }
   }
   deviation "/multicast-forward:multicast-forward/multicast-forward:spatial-mul"+
             "ticast/multicast-forward:vlan-multicast-bandwidths/multicast-forwa"+
             "rd:vlan-multicast-bandwidth/multicast-forward:bandwidth" {
     deviate "replace" {
       type "uint64" {
         range "1..40000000";
       }
     }
   }
   deviation "/multicast-forward:multicast-forward/multicast-forward:spatial-mul"+
             "ticast/multicast-forward:vsi-multicast-bandwidths/multicast-forwar"+
             "d:vsi-multicast-bandwidth/multicast-forward:vsi-name" {
     deviate "replace" {
       type "leafref" {
         path "/l2vpn:l2vpn/l2vpn:instances/l2vpn:instance/l2vpn:name";
       }
     }
     deviate "add" {
       must "((/l2vpn:l2vpn/l2vpn:instances/l2vpn:instance[l2vpn:name=current()]"+
            "[l2vpn:type='vpls']/l2vpn:vpls/l2vpn:work-mode != 'bd-mode')\nand "+
            "(/l2vpn:l2vpn/l2vpn:instances/l2vpn:instance[l2vpn:name=current()]["+
            "l2vpn:type='vpls']/l2vpn:vpls/l2vpn:work-mode != 'b-vsi')\nand "+
            "(/l2vpn:l2vpn/l2vpn:instances/l2vpn:instance[l2vpn:name=current()]["+
            "l2vpn:type='vpls']/l2vpn:vpls/l2vpn:work-mode != 'i-vsi')\nand "+
            "(/l2vpn:l2vpn/l2vpn:instances/l2vpn:instance[l2vpn:name=current()]["+
            "l2vpn:type='vpls']/l2vpn:vpls/l2vpn:work-mode != 'i-vsi-p2p')\nand "+
            "(/l2vpn:l2vpn/l2vpn:instances/l2vpn:instance[l2vpn:name=current()]["+
            "l2vpn:type='vpls']/l2vpn:vpls/l2vpn:work-mode != 'i-vsi-b-evpn-inte"+
            "rworking')\nand (/l2vpn:l2vpn/l2vpn:instances/l2vpn:instance[l2vpn:"+
            "name=current()][l2vpn:type='vpls']/l2vpn:vpls/l2vpn:p2p-vsi != "+
            "'true'))";
     }
     deviate "add" {
       must "(/l2vpn:l2vpn/l2vpn:instances/l2vpn:instance[l2vpn:name=current()]["+
            "l2vpn:type='vpls']/l2vpn:vpls/ims:igmp-snooping/ims:global/ims:enab"+
            "le = 'true')";
     }
   }
   deviation "/multicast-forward:multicast-forward/multicast-forward:spatial-mul"+
             "ticast/multicast-forward:vsi-multicast-bandwidths/multicast-forwar"+
             "d:vsi-multicast-bandwidth/multicast-forward:bandwidth" {
     deviate "replace" {
       type "uint64" {
         range "1..40000000";
       }
     }
   }
   deviation "/multicast-forward:multicast-forward/multicast-forward:spatial-mul"+
             "ticast/multicast-forward:mpls-bandwidths/multicast-forward:mpls-ba"+
             "ndwidth/multicast-forward:bandwidth" {
     deviate "replace" {
       type "uint64" {
         range "1..40000000";
       }
     }
   }
   deviation "/multicast-forward:multicast-forward/multicast-forward:l2-egress-s"+
             "tatistics/multicast-forward:vlan-enables/multicast-forward:vlan-en"+
             "able/multicast-forward:vlan-id" {
     deviate "add" {
       must "(/vlan:vlan/vlan:vlans/vlan:vlan[vlan:id=current()]/ims:igmp-snoopi"+
            "ng/ims:global/ims:enable = 'true')";
     }
   }
   deviation "/multicast-forward:multicast-forward/multicast-forward:l2-egress-s"+
             "tatistics/multicast-forward:vsi-enables/multicast-forward:vsi-enab"+
             "le/multicast-forward:vsi-name" {
     deviate "replace" {
       type "leafref" {
         path "/l2vpn:l2vpn/l2vpn:instances/l2vpn:instance/l2vpn:name";
       }
     }
     deviate "add" {
       must "(/l2vpn:l2vpn/l2vpn:instances/l2vpn:instance[l2vpn:name=current()]["+
            "l2vpn:type='vpls']/l2vpn:vpls/ims:igmp-snooping/ims:global/ims:enab"+
            "le = 'true')";
     }
   }
   deviation "/multicast-forward:multicast-forward/multicast-forward:l2-egress-s"+
             "tatistics/multicast-forward:bd-enables/multicast-forward:bd-enable"+
             "/multicast-forward:bd-id" {
     deviate "replace" {
       type "leafref" {
         path "/bd:bd/bd:instances/bd:instance/bd:id";
       }
     }
     deviate "add" {
       must "(/bd:bd/bd:instances/bd:instance[bd:id=current()]/ims:igmp-snooping"+
            "/ims:global/ims:enable = 'true')";
     }
   }
   deviation "/multicast-forward:multicast-forward/multicast-forward:l2-egress-s"+
             "tatistics/multicast-forward:vsi-statistics/multicast-forward:vsi-s"+
             "tatistic/multicast-forward:vsi-name" {
     deviate "replace" {
       type "leafref" {
         path "/l2vpn:l2vpn/l2vpn:instances/l2vpn:instance/l2vpn:name";
       }
     }
   }
   deviation "/multicast-forward:multicast-forward/multicast-forward:l2-egress-s"+
             "tatistics/multicast-forward:bd-statistics/multicast-forward:bd-sta"+
             "tistic/multicast-forward:bd-id" {
     deviate "replace" {
       type "leafref" {
         path "/bd:bd/bd:instances/bd:instance/bd:id";
       }
     }
   }
   deviation "/multicast-forward:reset-vsi-egress-statistics/multicast-forward:i"+
             "nput/multicast-forward:vsi-name" {
     deviate "replace" {
       type "leafref" {
         path "/l2vpn:l2vpn/l2vpn:instances/l2vpn:instance/l2vpn:name";
       }
     }
   }
   deviation "/multicast-forward:reset-bd-egress-statistics/multicast-forward:in"+
             "put/multicast-forward:bd-id" {
     deviate "replace" {
       type "leafref" {
         path "/bd:bd/bd:instances/bd:instance/bd:id";
       }
     }
   }
 }

/*
Copyright (C) 2019 Huawei Technologies Co., Ltd. All rights reserved.
*/

 module huawei-ietf-connless-oam-meth-deviations-OC-NE-X8X16 {
   yang-version "1.1";
   namespace "urn:huawei:yang:huawei-ietf-connless-oam-meth-deviations-OC-NE-X8X"+
             "16";
   prefix "cloam-methods-devs-OC-NE-X8X16";
   import ietf-connectionless-oam-methods {
     prefix "cloam-methods";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for ietf-connectionless-oam-metho"+
     "ds module.";
   revision "2019-11-06" {
     description
       "Initial revision.";
     reference
       "Huawei private.";
   }
   deviation "/cloam-methods:continuity-check/cloam-methods:input/cloam-methods:"+
             "count" {
     deviate "replace" {
       type "uint8" {
         range "1..10";
       }
     }
   }
   deviation "/cloam-methods:path-discovery/cloam-methods:input/cloam-methods:ma"+
             "x-ttl" {
     deviate "replace" {
       type "uint8" {
         range "1..10";
       }
     }
     deviate "replace" {
       default "10";
     }
   }
 }

module ietf-netconf-nmda {
   yang-version "1.1";
   namespace "urn:ietf:params:xml:ns:yang:ietf-netconf-nmda";
   prefix "ncds";
   import ietf-yang-types {
     prefix "yang";
     reference
       "RFC 6991: Common YANG Data Types";
   }
   import ietf-inet-types {
     prefix "inet";
     reference
       "RFC 6991: Common YANG Data Types";
   }
   import ietf-datastores {
     prefix "ds";
     reference
       "RFC 8342: Network Management Datastore Architecture\n        (NMDA)";
   }
   import ietf-netconf {
     prefix "nc";
     reference
       "RFC 6241: Network Configuration Protocol (NETCONF)";
   }
   import ietf-netconf-with-defaults {
     prefix "ncwd";
     reference
       "RFC 6243: With-defaults Capability for NETCONF";
   }
   organization
     "IETF NETCONF Working Group";
   contact
     "WG Web:   <https://datatracker.ietf.org/wg/netconf/>\n\nWG List:  "+
     "<mailto:netconf@ietf.org>\n\nAuthor:   Martin Bjorklund\n          "+
     "<mailto:mbj@tail-f.com>\n\nAuthor:   Juergen Schoenwaelder\n          "+
     "<mailto:j.schoenwaelder@jacobs-university.de>\n\nAuthor:   Phil Shafer\n  "+
     "        <mailto:phil@juniper.net>\n\nAuthor:   Kent Watsen\n          "+
     "<mailto:kent+ietf@watsen.net>\n\nAuthor:   Robert Wilton\n          "+
     "<mailto:rwilton@cisco.com>";
   description
     "This YANG module defines a set of NETCONF operations to support\nthe "+
     "Network Management Datastore Architecture (NMDA).\n\nThe key words 'MUST',"+
     " 'MUST NOT', 'REQUIRED', 'SHALL', 'SHALL\nNOT', 'SHOULD', 'SHOULD NOT', "+
     "'RECOMMENDED', 'NOT RECOMMENDED',\n'MAY', and 'OPTIONAL' in this document "+
     "are to be interpreted as\ndescribed in BCP 14 (RFC 2119) (RFC 8174) when, "+
     "and only when,\nthey appear in all capitals, as shown here.\n\nCopyright "+
     "(c) 2019 IETF Trust and the persons identified as\nauthors of the code.  "+
     "All rights reserved.\n\nRedistribution and use in source and binary forms,"+
     " with or\nwithout modification, is permitted pursuant to, and subject "+
     "to\nthe license terms contained in, the Simplified BSD License set\nforth "+
     "in Section 4.c of the IETF Trust's Legal Provisions\nRelating to IETF "+
     "Documents\n(https://trustee.ietf.org/license-info).\n\nThis version of "+
     "this YANG module is part of RFC 8526; see\nthe RFC itself for full legal "+
     "notices.";
   revision "2019-01-07" {
     description
       "Initial revision.";
     reference
       "RFC 8526: NETCONF Extensions to Support the Network Management\n        "+
       "Datastore Architecture";
   }
   feature origin {
     description
       "Indicates that the server supports the 'origin' annotation.";
     reference
       "RFC 8342: Network Management Datastore Architecture (NMDA)";
   }
   feature with-defaults {
     description
       "NETCONF :with-defaults capability.  If the server advertises\nthe "+
       ":with-defaults capability for a session, then this\nfeature must also be"+
       " enabled for that session.  Otherwise,\nthis feature must not be "+
       "enabled.";
     reference
       "RFC 6243: With-defaults Capability for NETCONF, Section 4; and\nRFC "+
       "8526: NETCONF Extensions to Support the Network Management\n          "+
       "Datastore Architecture, Section 3.1.1.2";
   }
   rpc get-data {
     description
       "Retrieve data from an NMDA datastore.  The content returned\nby get-data"+
       " must satisfy all filters, i.e., the filter\ncriteria are logically "+
       "ANDed.\n\nAny ancestor nodes (including list keys) of nodes selected "+
       "by\nthe filters are included in the response.\n\nThe 'with-origin' "+
       "parameter is only valid for an operational\ndatastore.  If 'with-origin'"+
       " is used with an invalid\ndatastore, then the server MUST return an "+
       "<rpc-error> element\nwith an <error-tag> value of 'invalid-value'.\n\nTh"+
       "e 'with-defaults' parameter only applies to the operational\ndatastore "+
       "if the NETCONF :with-defaults and\n:with-operational-defaults capabiliti"+
       "es are both advertised.\nIf the 'with-defaults' parameter is present in "+
       "a request for\nwhich it is not supported, then the server MUST return "+
       "an\n<rpc-error> element with an <error-tag> value of\n'invalid-value'.";
     input {
       leaf datastore {
         type "ds:datastore-ref";
         mandatory "true";
         description
           "Datastore from which to retrieve data.\n\nIf the datastore is not "+
           "supported by the server, then the\nserver MUST return an <rpc-error>"+
           " element with an\n<error-tag> value of 'invalid-value'.";
       }
       choice filter-spec {
         description
           "The content filter specification for this request.";
         anydata subtree-filter {
           description
             "This parameter identifies the portions of the\ntarget datastore to"+
             " retrieve.";
           reference
             "RFC 6241: Network Configuration Protocol (NETCONF),\n        "+
             "Section 6";
         }
         leaf xpath-filter {
           if-feature "nc:xpath";
           type "yang:xpath1.0";
           description
             "This parameter contains an XPath expression identifying\nthe "+
             "portions of the target datastore to retrieve.\n\nIf the expression"+
             " returns a node-set, all nodes in the\nnode-set are selected by "+
             "the filter.  Otherwise, if the\nexpression does not return a "+
             "node-set, then the\n<get-data> operation fails.\n\nThe expression "+
             "is evaluated in the following XPath\ncontext:\n\n  o  The set of "+
             "namespace declarations are those in\n     scope on the 'xpath-filt"+
             "er' leaf element.\n\n  o  The set of variable bindings is "+
             "empty.\n\n  o  The function library is the core function "+
             "library,\n     and the XPath functions are defined in Section 10\n"+
             "     of RFC 7950.\n\n  o  The context node is the root node of the"+
             " target\n     datastore.";
         }
       }
       leaf with-defaults {
         description
           "The explicit defaults processing mode requested.";
         reference
           "RFC 6243; Section 4.5.1";
         type "ncwd:with-defaults-mode";
       }
     }
     output {
       anydata data {
         description
           "Copy of the source datastore subset that matched\nthe filter "+
           "criteria (if any).  An empty data\ncontainer indicates that the "+
           "request did not\nproduce any results.";
       }
     }
   }
   rpc edit-data {
     description
       "Edit data in an NMDA datastore.\n\nIf an error condition occurs such "+
       "that an error severity\n<rpc-error> element is generated, the server "+
       "will stop\nprocessing the <edit-data> operation and restore the\nspecifi"+
       "ed configuration to its complete state at\nthe start of this <edit-data>"+
       " operation.";
     input {
       leaf datastore {
         type "ds:datastore-ref";
         mandatory "true";
         description
           "Datastore that is the target of the <edit-data> operation.\n\nIf the"+
           " target datastore is not writable, or is not\nsupported by the "+
           "server, then the server MUST return an\n<rpc-error> element with an "+
           "<error-tag> value of\n'invalid-value'.";
       }
       leaf default-operation {
         type "enumeration" {
           enum "merge" {
             description
               "The default operation is merge.";
           }
           enum "replace" {
             description
               "The default operation is replace.";
           }
           enum "none" {
             description
               "There is no default operation.";
           }
         }
         default "merge";
         description
           "The default operation to use.";
       }
       choice edit-content {
         mandatory "true";
         description
           "The content for the edit operation.";
         anydata config {
           description
             "Inline config content.";
         }
         leaf url {
           if-feature "nc:url";
           type "inet:uri";
           description
             "URL-based config content.";
         }
       }
     }
   }
   augment "/nc:lock/nc:input/nc:target/nc:config-target" {
     description
       "Add NMDA datastore as target.";
     leaf datastore {
       type "ds:datastore-ref";
       description
         "Datastore to lock.\n\nThe <lock> operation is only supported on "+
         "writable\ndatastores.\n\nIf the <lock> operation is not supported by "+
         "the server on\nthe specified target datastore, then the server MUST "+
         "return\nan <rpc-error> element with an <error-tag> value of\n'invalid-"+
         "value'.";
     }
   }
   augment "/nc:unlock/nc:input/nc:target/nc:config-target" {
     description
       "Add NMDA datastore as target.";
     leaf datastore {
       type "ds:datastore-ref";
       description
         "Datastore to unlock.\n\nThe <unlock> operation is only supported on "+
         "writable\ndatastores.\n\nIf the <unlock> operation is not supported by"+
         " the server on\nthe specified target datastore, then the server MUST "+
         "return\nan <rpc-error> element with an <error-tag> value of\n'invalid-"+
         "value'.";
     }
   }
   augment "/nc:validate/nc:input/nc:source/nc:config-source" {
     description
       "Add NMDA datastore as source.";
     leaf datastore {
       type "ds:datastore-ref";
       description
         "Datastore to validate.\n\nThe <validate> operation is supported only "+
         "on configuration\ndatastores.\n\nIf the <validate> operation is not "+
         "supported by the server\non the specified target datastore, then the "+
         "server MUST\nreturn an <rpc-error> element with an <error-tag> value "+
         "of\n'invalid-value'.";
     }
   }
 }

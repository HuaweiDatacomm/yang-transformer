module ietf-connectionless-oam-methods {
   yang-version "1.1";
   namespace "urn:ietf:params:xml:ns:yang:ietf-connectionless-oam-methods";
   prefix "cloam-methods";
   import ietf-connectionless-oam {
     prefix "cl-oam";
   }
   import ietf-inet-types {
     prefix "inet";
   }
   organization
     "IETF LIME Working Group";
   contact
     "WG Web:   <https://datatracker.ietf.org/wg/lime>\nWG List:  <mailto:lmap@i"+
     "etf.org>\n\nDeepak Kumar <dekumar@cisco.com>\nQin Wu <bill.wu@huawei.com>"+
     "\nSrihari Raghavan <rihari@cisco.com>\nMichael Wang <wangzitao@huawei.com>"+
     "\nReshad Rahman <rrahman@cisco.com>";
   description
     "This YANG module defines the RPC operations for\nconnectionless OAM to be "+
     "used within the IETF\nin a protocol-independent manner.  It is\nassumed "+
     "that each protocol maps corresponding\nabstracts to its native format.  "+
     "Each protocol\nmay extend the YANG data model defined here to\ninclude "+
     "protocol-specific extensions.\n\nCopyright (c) 2019 IETF Trust and the "+
     "persons identified as\nauthors of the code.  All rights reserved.\n\nRedis"+
     "tribution and use in source and binary forms, with or\nwithout modificatio"+
     "n, is permitted pursuant to, and subject\nto the license terms contained "+
     "in, the Simplified BSD License\nset forth in Section 4.c of the IETF "+
     "Trust's Legal Provisions\nRelating to IETF Documents\n(http://trustee.ietf"+
     ".org/license-info).\n\nThis version of this YANG module is part of RFC "+
     "8533; see\nthe RFC itself for full legal notices.";
   revision "2019-04-16" {
     description
       "Initial revision.";
     reference
       "RFC 8533: Retrieval Methods YANG Data Model for the Management\nof "+
       "Operations, Administration, and Maintenance (OAM)\nProtocols That Use "+
       "Connectionless Communications";
   }
   identity protocol-id {
     description
       "This is the base identity for a generic protocol\nID.  The protocol "+
       "registry can be found at\nhttps://www.iana.org/protocols.";
   }
   identity protocol-id-internet {
     base "protocol-id";
     description
       "Identity for Internet Protocols.";
   }
   identity protocol-id-proprietary {
     base "protocol-id";
     description
       "Identity for proprietary protocols (e.g.,\nIP SLA).";
   }
   identity protocol-id-sfc {
     base "protocol-id";
     description
       "Identity for Service Function Chaining.";
   }
   identity protocol-id-mpls {
     base "protocol-id";
     description
       "The MPLS protocol.";
   }
   identity protocol-id-mpls-tp {
     base "protocol-id";
     description
       "The MPLS-TP protocol.";
   }
   identity protocol-id-twamp {
     base "protocol-id";
     description
       "The Two-Way Active Measurement Protocol (TWAMP)\nprotocol.";
   }
   identity protocol-id-bier {
     base "protocol-id";
     description
       "The Bit Index Explicit Replication (BIER)\nprotocol.";
   }
   identity status-code {
     description
       "This is base identity for a status code.";
   }
   identity success-reach {
     base "status-code";
     description
       "Indicates that the destination being verified\nis reachable (see RFC "+
       "7276).";
     reference
       "RFC 7276: An Overview of Operations, Administration, and\nMaintenance "+
       "(OAM) Tools";
   }
   identity fail-reach {
     base "status-code";
     description
       "Indicates that the destination being verified\nis not reachable (see RFC"+
       " 7276).";
     reference
       "RFC 7276: An Overview of Operations, Administration, and\nMaintenance "+
       "(OAM) Tools";
   }
   identity success-path-verification {
     base "status-code";
     description
       "Indicates that the path verification is performed\nsuccessfully (see RFC"+
       " 7276).";
     reference
       "RFC 7276: An Overview of Operations, Administration, and\nMaintenance "+
       "(OAM) Tools";
   }
   identity fail-path-verification {
     base "status-code";
     description
       "Indicates that the path verification fails\n(see RFC 7276).";
     reference
       "RFC 7276: An Overview of Operations, Administration, and\nMaintenance "+
       "(OAM) Tools";
   }
   identity status-sub-code {
     description
       "IdentityBase status-sub-code.";
   }
   identity invalid-cc {
     base "status-sub-code";
     description
       "Indicates that the Continuity Check message is invalid\n(see RFC 7276).";
     reference
       "RFC 7276: An Overview of Operations, Administration, and\nMaintenance "+
       "(OAM) Tools";
   }
   identity invalid-pd {
     base "status-sub-code";
     description
       "Indicates that the path discovery message is invalid\n(see RFC 7276).";
     reference
       "RFC 7276: An Overview of Operations, Administration, and\nMaintenance "+
       "(OAM) Tools";
   }
   identity protocol-id-meta-data {
     description
       "This is the base identity for metadata that corresponds\nto the protocol"+
       " ID.";
   }
   identity protocol-internet-number {
     base "protocol-id-meta-data";
     description
       "Internet Protocol number for standard\nInternet Protocols (IANA-assigned"+
       " Internet\nProtocol numbers) to help in protocol processing.\nThe "+
       "Protocol Numbers registry can be found at\nhttps://www.iana.org/assignme"+
       "nts/protocol-numbers.";
   }
   rpc continuity-check {
     if-feature "cl-oam:continuity-check";
     description
       "Continuity Check RPC operation as per RFC 7276.";
     reference
       "RFC 7276: An Overview of Operations, Administration, and\nMaintenance "+
       "(OAM) Tools";
     input {
       container destination-tp {
         leaf tp-location-type {
           type "identityref" {
             base "cl-oam:tp-address-technology-type";
           }
           mandatory "true";
           description
             "Test point address type.";
         }
         container ipv4-address {
           when "derived-from-or-self(../tp-location-type,'cl-oam:ipv4-address-t"+
                "ype')" {
             description
               "IPv4 address type.";
           }
           leaf ipv4-address {
             type "inet:ipv4-address";
             mandatory "true";
             description
               "IPv4 address.";
           }
           description
             "IP address based TP addressing.";
         }
         container ipv6-address {
           when "derived-from-or-self(../tp-location-type,'cl-oam:ipv6-address-t"+
                "ype')" {
             description
               "IPv6 address type.";
           }
           leaf ipv6-address {
             type "inet:ipv6-address";
             mandatory "true";
             description
               "IPv6 address.";
           }
           description
             "IPv6 address based TP addressing.";
         }
         description
           "Destination test point.";
       }
       leaf count {
         type "uint8" {
           range "1..10";
         }
         default "5";
         description
           "Specifies the number of\npackets that will be sent.  By\ndefault, "+
           "the packet number is\nset to 5.";
       }
       leaf ttl {
         type "uint8";
         default "255";
         description
           "Time to live (TTL) used to limit the lifetime\nof data packets "+
           "transmitted in the network\nto prevent looping.  The TTL value is "+
           "decremented\nfor every hop that the packet traverses.  If the\nTTL "+
           "is zero, the data packet will be discarded.";
       }
       leaf packet-size {
         type "uint32" {
           range "64..10000";
         }
         default "64";
         description
           "Packet size of the Continuity Check message, in octets.\nBy default,"+
           " the packet size is set to 64 octets.";
       }
     }
     output {
       container response-info {
         leaf protocol-id {
           type "identityref" {
             base "protocol-id";
           }
           mandatory "true";
           description
             "Protocol used in the Continuity Check message.\nThis could be a "+
             "standard protocol (e.g.,\nTCP/IP protocols, MPLS, etc.) or a "+
             "proprietary\nprotocol as identified by this field.";
         }
         leaf protocol-id-meta-data {
           type "identityref" {
             base "protocol-id-meta-data";
           }
           description
             "An optional metadata related to the protocol ID.\nFor example, "+
             "this could be the Internet Protocol\nnumber for standard Internet "+
             "Protocols used for\nhelp with protocol processing.";
         }
         leaf status-code {
           type "identityref" {
             base "status-code";
           }
           mandatory "true";
           description
             "Status code for Continuity Check RPC operation.\nThis could be a "+
             "basic status code (e.g., destination\nis reachable or destination "+
             "is not reachable; see RFC 7276)\nor some customized status code as"+
             " identified by this\nfield.";
           reference
             "RFC 7276: An Overview of Operations, Administration, and\nMaintena"+
             "nce (OAM) Tools";
         }
         description
           "Status code and status-sub-code for Continuity Check RPC\noperation."+
           "";
       }
       container session-packet-statistics {
         description
           "Statistics per session packet.";
         leaf rx-packet-count {
           type "uint32" {
             range "0..4294967295";
           }
           default "0";
           description
             "Total count of received OAM packets.\n\nThe value of count will be"+
             " set to zero (0)\non creation and will thereafter increase\nmonoto"+
             "nically until it reaches a maximum value\nof 2^32-1 (4294967295 "+
             "decimal), when it wraps\naround and starts increasing again from "+
             "zero.";
         }
         leaf tx-packet-count {
           type "uint32" {
             range "0..4294967295";
           }
           default "0";
           description
             "Total count of transmitted OAM packets.\nThe value of count will "+
             "be set to zero (0)\non creation and will thereafter increase\nmono"+
             "tonically until it reaches a maximum value\nof 2^32-1 (4294967295 "+
             "decimal), when it wraps\naround and starts increasing again from "+
             "zero.";
         }
         leaf rx-bad-packet {
           type "uint32" {
             range "0..4294967295";
           }
           default "0";
           description
             "Total number of received bad OAM packets.\nThe value of count will"+
             " be set to zero (0)\non creation and will thereafter increase\nmon"+
             "otonically until it reaches a maximum value\nof 2^32-1 (4294967295"+
             " decimal), when it wraps\naround and starts increasing again from "+
             "zero.";
         }
         leaf tx-packet-failed {
           type "uint32" {
             range "0..4294967295";
           }
           default "0";
           description
             "Total number of OAM packets that failed when sent.\nThe value of "+
             "count will be set to zero (0)\non creation and will thereafter "+
             "increase\nmonotonically until it reaches a maximum value\nof "+
             "2^32-1 (4294967295 decimal), when it wraps\naround and starts "+
             "increasing again from zero.";
         }
       }
       container session-error-statistics {
         description
           "Per-session error statistics.";
         leaf packet-loss-count {
           type "uint32" {
             range "0..4294967295";
           }
           default "0";
           description
             "Total count of received packet drops.\nThe value of count will be "+
             "set to zero (0)\non creation and will thereafter increase\nmonoton"+
             "ically until it reaches a maximum value\nof 2^32-1 (4294967295 "+
             "decimal), when it wraps\naround and starts increasing again from "+
             "zero.";
         }
         leaf loss-ratio {
           type "cl-oam:percentage";
           description
             "Loss ratio of the packets.  Expressed as percentage\nof packets "+
             "lost with respect to packets sent.";
         }
         leaf packets-out-of-seq-count {
           type "uint32" {
             range "0..4294967295";
           }
           description
             "Total count of packets received out of sequence.\nThe value of "+
             "count will be set to zero (0)\n\non creation and will thereafter "+
             "increase\nmonotonically until it reaches a maximum value\nof "+
             "2^32-1 (4294967295 decimal), when it wraps\naround and starts "+
             "increasing again from zero.";
         }
         leaf packets-dup-count {
           type "uint32" {
             range "0..4294967295";
           }
           description
             "Total count of received packet duplicates.\nThe value of count "+
             "will be set to zero (0)\non creation and will thereafter "+
             "increase\nmonotonically until it reaches a maximum value\nof "+
             "2^32-1 (4294967295 decimal), when it wraps\naround and starts "+
             "increasing again from zero.";
         }
       }
     }
   }
   rpc path-discovery {
     if-feature "cl-oam:path-discovery";
     description
       "Path discovery RPC operation as per RFC 7276.";
     reference
       "RFC 7276: An Overview of Operations, Administration, and\nMaintenance "+
       "(OAM) Tools";
     input {
       container destination-tp {
         leaf tp-location-type {
           type "identityref" {
             base "cl-oam:tp-address-technology-type";
           }
           mandatory "true";
           description
             "Test point address type.";
         }
         container ipv4-address {
           when "derived-from-or-self(../tp-location-type,'cl-oam:ipv4-address-t"+
                "ype')" {
             description
               "IPv4 address type.";
           }
           leaf ipv4-address {
             type "inet:ipv4-address";
             mandatory "true";
             description
               "IPv4 address.";
           }
           description
             "IP address based TP addressing.";
         }
         container ipv6-address {
           when "derived-from-or-self(../tp-location-type,'cl-oam:ipv6-address-t"+
                "ype')" {
             description
               "IPv6 address type.";
           }
           leaf ipv6-address {
             type "inet:ipv6-address";
             mandatory "true";
             description
               "IPv6 address.";
           }
           description
             "IPv6 address based TP addressing.";
         }
         description
           "Destination test point.";
       }
       leaf max-ttl {
         type "uint8" {
           range "1..10";
         }
         default "10";
         description
           "Maximum TTL indicates the maximum number of hops that\na packet is "+
           "permitted to travel before being discarded\nby a router.  By "+
           "default, the maximum TTL is set to\n255.";
       }
     }
     output {
       list response-list {
         key "response-index";
         description
           "Path discovery response list.";
         leaf response-index {
           type "uint32";
           mandatory "true";
           description
             "Response index.";
         }
         leaf protocol-id {
           type "identityref" {
             base "protocol-id";
           }
           mandatory "true";
           description
             "Protocol used in path discovery.  This could be a\nstandard "+
             "protocol (e.g., TCP/IP protocols, MPLS, etc.)\nor a proprietary "+
             "protocol as identified by\nthis field.";
         }
         leaf protocol-id-meta-data {
           type "identityref" {
             base "protocol-id-meta-data";
           }
           description
             "An optional metadata related to the protocol ID.\nFor example, "+
             "this could be the Internet Protocol\nnumber for standard Internet "+
             "Protocols used for\nhelp with protocol processing.";
         }
         leaf status-code {
           type "identityref" {
             base "status-code";
           }
           mandatory "true";
           description
             "Status code for Continuity Check RPC operation.\nThis could be a "+
             "basic status code (e.g., destination\nis reachable or destination "+
             "is not reachable) or some\ncustomized status code as identified by"+
             " this field.";
         }
       }
       leaf hop-cnt {
         type "uint8";
         default "0";
         description
           "Hop count.  A value of zero indicates\nthat no hop count is sent.";
       }
       container session-packet-statistics {
         description
           "Statistics per session packet.";
         leaf rx-packet-count {
           type "uint32" {
             range "0..4294967295";
           }
           default "0";
           description
             "Total count of received OAM packets.\n\nThe value of count will be"+
             " set to zero (0)\non creation and will thereafter increase\nmonoto"+
             "nically until it reaches a maximum value\nof 2^32-1 (4294967295 "+
             "decimal), when it wraps\naround and starts increasing again from "+
             "zero.";
         }
         leaf tx-packet-count {
           type "uint32" {
             range "0..4294967295";
           }
           default "0";
           description
             "Total count of transmitted OAM packets.\nThe value of count will "+
             "be set to zero (0)\non creation and will thereafter increase\nmono"+
             "tonically until it reaches a maximum value\nof 2^32-1 (4294967295 "+
             "decimal), when it wraps\naround and starts increasing again from "+
             "zero.";
         }
         leaf rx-bad-packet {
           type "uint32" {
             range "0..4294967295";
           }
           default "0";
           description
             "Total number of received bad OAM packets.\nThe value of count will"+
             " be set to zero (0)\non creation and will thereafter increase\nmon"+
             "otonically until it reaches a maximum value\nof 2^32-1 (4294967295"+
             " decimal), when it wraps\naround and starts increasing again from "+
             "zero.";
         }
         leaf tx-packet-failed {
           type "uint32" {
             range "0..4294967295";
           }
           default "0";
           description
             "Total number of OAM packets that failed when sent.\nThe value of "+
             "count will be set to zero (0)\non creation and will thereafter "+
             "increase\nmonotonically until it reaches a maximum value\nof "+
             "2^32-1 (4294967295 decimal), when it wraps\naround and starts "+
             "increasing again from zero.";
         }
       }
       container path-trace-info {
         description
           "Optional per-hop path trace information about test points.\nThe path"+
           " trace information list typically has a single\nelement for per-hop "+
           "cases such as path-discovery RPC operation\nbut allows a list of "+
           "hop-related information for other types of\ndata retrieval methods.";
         list path-trace-info-list {
           key "index";
           description
             "Path trace information list.";
           leaf index {
             type "uint32";
             description
               "Trace information index.";
           }
           leaf tp-location-type {
             type "identityref" {
               base "cl-oam:tp-address-technology-type";
             }
             mandatory "true";
             description
               "Test point address type.";
           }
           container ipv4-address {
             when "derived-from-or-self(../tp-location-type,'cl-oam:ipv4-address"+
                  "-type')" {
               description
                 "IPv4 address type.";
             }
             leaf ipv4-address {
               type "inet:ipv4-address";
               mandatory "true";
               description
                 "IPv4 address.";
             }
             description
               "IP address based TP addressing.";
           }
           container ipv6-address {
             when "derived-from-or-self(../tp-location-type,'cl-oam:ipv6-address"+
                  "-type')" {
               description
                 "IPv6 address type.";
             }
             leaf ipv6-address {
               type "inet:ipv6-address";
               mandatory "true";
               description
                 "IPv6 address.";
             }
             description
               "IPv6 address based TP addressing.";
           }
         }
       }
     }
   }
 }

/*
Copyright (C) 2019 Huawei Technologies Co., Ltd. All rights reserved.
*/

 module huawei-telnetc {
   namespace "urn:huawei:yang:huawei-telnetc";
   prefix "telnetc";
   import huawei-pub-type {
     prefix "pub-type";
   }
   import ietf-inet-types {
     prefix "inet";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Telnet client component.";
   revision "2019-05-02" {
     description
       "Initial revision.";
     reference
       "Huawei private.";
   }
   ext:task-name "telnet-client";
   container telnetc {
     description
       "Telnet client component.";
     container client {
       description
         "Configure Telnet client information.";
       leaf src-interface {
         type "pub-type:if-name";
         description
           "Specify the source interface name. The specified source interface "+
           "must exist and an IP address must be configured on the interface.";
       }
       leaf src-ipv4-addr {
         when "not(../src-interface)";
         type "inet:ipv4-address-no-zone";
         description
           "Source IPv4 address.";
       }
       leaf packet-dscp {
         type "uint32" {
           range "0..63";
         }
         default "48";
         description
           "Config DSCP value.";
       }
       leaf src-ipv6-addr {
         type "inet:ipv6-address-no-zone";
         description
           "Telnet source IPv6 address.";
       }
       leaf ipv6-vpn-instance-name {
         when "../src-ipv6-addr";
         type "string" {
           length "1..31";
         }
         description
           "The specified VPN instance must exist and IPv6-family must be "+
           "enabled in the VPN instance.";
       }
     }
   }
 }

/*
Copyright (C) 2021 Huawei Technologies Co., Ltd. All rights reserved.
*/

 module huawei-dcn-deviations-OC-NE-X8X16 {
   namespace "urn:huawei:yang:huawei-dcn-deviations-OC-NE-X8X16";
   prefix "dcn-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Data communication network.";
   revision "2021-07-28" {
     description
       "Init revision.";
     reference
       "Huawei private.";
   }
 }

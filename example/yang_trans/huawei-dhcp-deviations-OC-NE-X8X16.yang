/*
Copyright (C) 2019 Huawei Technologies Co., Ltd. All rights reserved.
*/

 module huawei-dhcp-deviations-OC-NE-X8X16 {
   namespace "urn:huawei:yang:huawei-dhcp-deviations-OC-NE-X8X16";
   prefix "dhcp-devs-OC-NE-X8X16";
   import huawei-dhcp {
     prefix "dhcp";
   }
   import huawei-ifm {
     prefix "ifm";
   }
   import huawei-vlan {
     prefix "vlan";
   }
   organization
     "Huawei Technologies Co., Ltd.";
   contact
     "Huawei Industrial Base\nBantian, Longgang\nShenzhen 518129\nPeople's "+
     "Republic of China\nWebsite: http://www.huawei.com\nEmail: support@huawei.c"+
     "om";
   description
     "Dynamic Host Configuration Protocol.";
   revision "2019-04-29" {
     description
       "Initial revision.";
     reference
       "Huawei private.";
   }
   typedef option82-format-deviations {
     type "enumeration" {
       enum "user-defined" {
         value "3";
         description
           "DHCP option82 user-defined format.";
       }
       enum "type1" {
         value "5";
         description
           "DHCP option82 type1 format.";
       }
       enum "type2" {
         value "6";
         description
           "DHCP option82 type2 format.";
       }
       enum "self-define" {
         value "7";
         description
           "DHCP option82 self-define format.";
       }
       enum "cn-telecom" {
         value "9";
         description
           "DHCP option82 cn-telecom format.";
       }
       enum "cn-telecom-inherit" {
         value "12";
         description
           "DHCP option82 cn-telecom-inherit format.";
       }
     }
     description
       "Type of dhcp-opt82-format.";
   }
   deviation "/dhcp:dhcp/dhcp:server/dhcp:global-ip-pools/dhcp:global-ip-pool/dh"+
             "cp:ip-pool-name" {
     deviate "replace" {
       type "string" {
         length "1..128";
       }
     }
   }
   deviation "/dhcp:dhcp/dhcp:common/dhcp:global/dhcp:enable" {
     deviate "replace" {
       default "true";
     }
   }
   deviation "/ifm:ifm/ifm:interfaces/ifm:interface/dhcp:dhcp-if/dhcp:option82-f"+
             "ormats/dhcp:option82-format/dhcp:option82-format" {
     deviate "replace" {
       type "dhcp-devs-OC-NE-X8X16:option82-format-deviations";
     }
   }
   deviation "/vlan:vlan/vlan:vlans/vlan:vlan/dhcp:dhcp-vlan/dhcp:interface-opti"+
             "on82-formats/dhcp:interface-option82-format/dhcp:option82-format" {
     deviate "replace" {
       type "dhcp-devs-OC-NE-X8X16:option82-format-deviations";
     }
   }
   deviation "/dhcp:dhcp/dhcp:server/dhcp:global-ip-pools/dhcp:global-ip-pool/dh"+
             "cp:domain-name" {
     deviate "replace" {
       type "string" {
         length "1..50";
       }
     }
   }
   deviation "/dhcp:dhcp/dhcp:server/dhcp:global-ip-pools/dhcp:global-ip-pool/dh"+
             "cp:static-binds/dhcp:static-bind" {
     deviate "replace" {
       max-elements "2000";
     }
   }
 }

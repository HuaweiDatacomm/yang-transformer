module ietf-ipv4-unicast-routing {
   yang-version "1.1";
   namespace "urn:ietf:params:xml:ns:yang:ietf-ipv4-unicast-routing";
   prefix "v4ur";
   import ietf-routing {
     prefix "rt";
     description
       "An 'ietf-routing' module version that is compatible with\nthe Network "+
       "Management Datastore Architecture (NMDA)\nis required.";
   }
   import ietf-inet-types {
     prefix "inet";
   }
   import ietf-interfaces {
     prefix "if";
   }
   organization
     "IETF NETMOD (Network Modeling) Working Group";
   contact
     "WG Web:   <https://datatracker.ietf.org/wg/netmod/>\nWG List:  <mailto:rtg"+
     "wg@ietf.org>\n\nEditor:   Ladislav Lhotka\n          <mailto:lhotka@nic.cz"+
     ">\n          Acee Lindem\n          <mailto:acee@cisco.com>\n          "+
     "Yingzhen Qu\n          <mailto:yingzhen.qu@huawei.com>";
   description
     "This YANG module augments the 'ietf-routing' module with basic\nparameters"+
     " for IPv4 unicast routing.  The model fully conforms\nto the Network "+
     "Management Datastore Architecture (NMDA).\n\nCopyright (c) 2018 IETF Trust"+
     " and the persons\nidentified as authors of the code.  All rights "+
     "reserved.\n\nRedistribution and use in source and binary forms, with "+
     "or\nwithout modification, is permitted pursuant to, and subject\nto the "+
     "license terms contained in, the Simplified BSD License\nset forth in "+
     "Section 4.c of the IETF Trust's Legal Provisions\nRelating to IETF "+
     "Documents\n(https://trustee.ietf.org/license-info).\n\nThis version of "+
     "this YANG module is part of RFC 8349; see\nthe RFC itself for full legal "+
     "notices.";
   revision "2018-03-13" {
     description
       "Network Management Datastore Architecture (NMDA) revision.";
     reference
       "RFC 8349: A YANG Data Model for Routing Management\n        (NMDA "+
       "Version)";
   }
   revision "2016-11-04" {
     description
       "Initial revision.";
     reference
       "RFC 8022: A YANG Data Model for Routing Management";
   }
   identity ipv4-unicast {
     base "rt:ipv4";
     description
       "This identity represents the IPv4 unicast address family.";
   }
   augment "/rt:routing/rt:control-plane-protocols/rt:control-plane-protocol/rt:"+
           "static-routes" {
     description
       "This augment defines the 'static' pseudo-protocol\nwith data specific to"+
       " IPv4 unicast.";
     container ipv4 {
       description
         "Support for a 'static' pseudo-protocol instance\nconsists of a list of"+
         " routes.";
       list route {
         key "destination-prefix";
         description
           "A list of static routes.";
         leaf destination-prefix {
           type "inet:ipv4-prefix";
           mandatory "true";
           description
             "IPv4 destination prefix.";
         }
         container next-hop {
           description
             "Support for next-hop.";
           choice next-hop-options {
             mandatory "true";
             description
               "Options for next hops in static routes.\n\nIt is expected that "+
               "further cases will be added through\naugments from other "+
               "modules.";
             case simple-next-hop {
               description
                 "This case represents a simple next hop consisting of "+
                 "the\nnext-hop address and/or outgoing interface.\n\nModules "+
                 "for address families MUST augment this case with a\nleaf "+
                 "containing a next-hop address of that address\nfamily.";
               leaf outgoing-interface {
                 type "if:interface-ref";
                 description
                   "Name of the outgoing interface.";
               }
               leaf next-hop-address {
                 type "inet:ipv4-address";
                 description
                   "IPv4 address of the next hop.";
               }
             }
           }
         }
       }
     }
   }
 }

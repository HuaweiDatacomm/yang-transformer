/*
Copyright (C) 2019 Huawei Technologies Co., Ltd. All rights reserved.
*/

 module huawei-acl-deviations-OC-NE-X8X16 {
   yang-version "1";
   namespace "urn:huawei:yang:huawei-acl-deviations-OC-NE-X8X16";
   prefix "acl-devs-OC-NE-X8X16";
   import huawei-acl {
     prefix "acl";
   }
   import huawei-acl-ucl {
     prefix "acl-ucl";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Access Control List (ACL). An ACL is used to identify and select data "+
     "packets through packet attributes. For example, applying an ACL in the "+
     "firewall can either permit or discard data packets. Applying an ACL in "+
     "IPsec can encrypt data packets that match ACL rules and forward those that"+
     " do not match any ACL rule.";
   revision "2019-06-23" {
     description
       "Initial revision.";
     reference
       "Huawei private.";
   }
   typedef group4-type-deviations {
     type "enumeration" {
       enum "interface" {
         value "0";
         description
           "Interface ACL.";
       }
       enum "link" {
         value "1";
         description
           "Link ACL.";
       }
       enum "basic" {
         value "2";
         description
           "Basic ACL.";
       }
       enum "advance" {
         value "3";
         description
           "Advanced ACL.";
       }
       enum "mpls" {
         value "7";
         description
           "MPLS ACL.";
       }
       enum "UCL" {
         value "10";
         description
           "UCL.";
       }
     }
     description
       "Type of a rule group.";
   }
   deviation "/acl:acl/acl:groups/acl:group/acl:type" {
     deviate "replace" {
       type "acl-devs-OC-NE-X8X16:group4-type-deviations";
     }
   }
   deviation "/acl:acl/acl:group6s/acl:group6/acl:rule-basics/acl:rule-basic/acl"+
             ":source-ipaddr" {
     deviate "add" {
       must "(../source-ipaddr and ../source-wild) or (../source-ipaddr and "+
            "../source-mask-len)";
     }
   }
   ext:deviation-ext "/acl:acl/acl:groups/acl:group/acl:match-order" {
     ext:deviate-ext "add" {
       ext:operation-exclude "update" {
         when "(../acl:rule-basics/acl:rule-basic) or (../acl:rule-advances/acl:"+
              "rule-advance) or (../acl:rule-ethernets/acl:rule-ethernet) or "+
              "(../acl:rule-mplss/acl:rule-mpls) or (../acl-ucl:rule-ucls/acl-uc"+
              "l:rule-ucl) or (../acl:rule-interfaces/acl:rule-interface)";
         description
           "When an ACL rule exists, this value can not be changed.";
       }
     }
   }
   ext:deviation-ext "/acl:acl/acl:group6s/acl:group6/acl:match-order" {
     ext:deviate-ext "add" {
       ext:operation-exclude "update" {
         when "(../acl:rule-basics/acl:rule-basic) or (../acl:rule-advances/acl:"+
              "rule-advance) or (../acl-ucl:rule-ucls/acl-ucl:rule-ucl) ";
         description
           "When an ACL rule exists, this value can not be changed.";
       }
     }
   }
 }

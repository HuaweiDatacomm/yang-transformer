/*
Copyright (C) 2020 Huawei Technologies Co., Ltd. All rights reserved.
*/

 module huawei-oam-cfm-evpn-deviations-OC-NE-X8X16 {
   yang-version "1";
   namespace "urn:huawei:yang:huawei-oam-cfm-evpn-deviations-OC-NE-X8X16";
   prefix "oam-cfm-evpn-devs-OC-NE-X8X16";
   import huawei-oammgr {
     prefix "oammgr";
   }
   import huawei-oam-cfm-evpn {
     prefix "oam-cfm-evpn";
   }
   organization
     "Huawei Technologies Co., Ltd.";
   contact
     "Huawei Industrial Base\nBantian, Longgang\nShenzhen 518129\nPeople's "+
     "Republic of China\nWebsite: http://www.huawei.com\nEmail: support@huawei.c"+
     "om";
   description
     "Configure the operation, administration and maintenance (OAM) association "+
     "function.";
   revision "2020-09-18" {
     description
       "Initial revision.";
     reference
       "Huawei private.";
   }
   typedef cfm-bind-evpn-type-deviations {
     type "enumeration" {
       enum "EVPN-CFM" {
         value "2";
         description
           "Type that EVPN transfers fault information to CFM.";
       }
     }
     description
       "Binding type.";
   }
   deviation "/oammgr:oammgr/oam-cfm-evpn:cfm-bind-evpns/oam-cfm-evpn:cfm-bind-e"+
             "vpn/oam-cfm-evpn:bind-type" {
     deviate "replace" {
       type "oam-cfm-evpn-devs-OC-NE-X8X16:cfm-bind-evpn-type-deviations";
     }
   }
 }

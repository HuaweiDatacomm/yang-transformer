/*
Copyright (C) 2019 Huawei Technologies Co., Ltd. All rights reserved.
*/

 module huawei-mac-deviations-OC-NE-X8X16 {
   yang-version "1";
   namespace "urn:huawei:yang:huawei-mac-deviations-OC-NE-X8X16";
   prefix "mac-devs-OC-NE-X8X16";
   import huawei-mac {
     prefix "mac";
   }
   import huawei-ifm {
     prefix "ifm";
   }
   import huawei-l2vpn {
     prefix "l2vpn";
   }
   import huawei-ethernet {
     prefix "ethernet";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "MAC address forwarding.";
   revision "2019-04-23" {
     description
       "Initial revision.";
     reference
       "Huawei private.";
   }
   typedef mac-type-deviations {
     type "enumeration" {
       enum "dynamic" {
         value "2";
         description
           "Dynamic type.";
       }
       enum "dynamic-black-hole" {
         value "15";
         description
           "Dynamic blackhole MAC.";
       }
       enum "sticky" {
         value "3";
         description
           "Sticky type.";
       }
       enum "sticky-static" {
         value "17";
         description
           "Sticky static type.";
       }
     }
     description
       "MAC type.";
   }
   deviation "/mac:mac/mac:mac-usages/mac:mac-usage/mac:slot" {
     deviate "replace" {
       type "leafref" {
         path "/devm:devm/devm:lpu-boards/devm:lpu-board/devm:position";
       }
     }
   }
   deviation "/mac:mac/mac:bd-dynamic-macs/mac:bd-dynamic-mac/mac:type" {
     deviate "replace" {
       type "mac-devs-OC-NE-X8X16:mac-type-deviations";
     }
   }
   deviation "/ifm:ifm/ifm:interfaces/ifm:interface/ethernet:ethernet/ethernet:m"+
             "ain-interface/mac:mac-limit/mac:limit-type/mac:limit-parameter/mac"+
             ":maximum" {
     deviate "add" {
       must "(../../ethernet:l2-attribute) or (/l2vpn:l2vpn/l2vpn:instances/l2vp"+
            "n:instance/l2vpn:vpls/l2vpn:acs/l2vpn:ac[l2vpn:interface-name=curre"+
            "nt()/../../../../ifm:name])";
     }
   }
   deviation "/ifm:ifm/ifm:interfaces/ifm:interface/ethernet:ethernet/ethernet:m"+
             "ain-interface/mac:mac-limit/mac:limit-type/mac:limit-rule-ref/mac:"+
             "rule-name" {
     deviate "add" {
       must "../../ethernet:l2-attribute";
     }
   }
 }

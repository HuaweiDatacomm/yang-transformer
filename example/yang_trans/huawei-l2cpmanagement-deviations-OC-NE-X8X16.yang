/*
Copyright (C) 2021 Huawei Technologies Co., Ltd. All rights reserved.
*/

 module huawei-l2cpmanagement-deviations-OC-NE-X8X16 {
   namespace "urn:huawei:yang:huawei-l2cpmanagement-deviations-OC-NE-X8X16";
   prefix "l2cpmanagement-devs-OC-NE-X8X16";
   import huawei-l2cpmanagement {
     prefix "l2cpmanagement";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-l2cpmanagement "+
     "module.";
   revision "2021-05-07" {
     description
       "Initial revision.";
     reference
       "Huawei private.";
   }
   deviation "/ifm:ifm/ifm:interfaces/ifm:interface/l2cpmanagement:protocol-acti"+
             "ons/l2cpmanagement:protocol-action" {
     deviate "add" {
       must "(action='transport' and protocol-type='link-oam') or (action='forwa"+
            "rding' and (protocol-type='link-oam' or protocol-type='c-stp' or "+
            "protocol-type='s-stp' or protocol-type='elmi' or protocol-type='ptp"+
            "')) or (action='discard' and protocol-type='bpdu')";
     }
   }
 }

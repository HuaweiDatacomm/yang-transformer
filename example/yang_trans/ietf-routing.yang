module ietf-routing {
   yang-version "1.1";
   namespace "urn:ietf:params:xml:ns:yang:ietf-routing";
   prefix "rt";
   organization
     "IETF NETMOD (Network Modeling) Working Group";
   contact
     "WG Web:   <https://datatracker.ietf.org/wg/netmod/>\nWG List:  <mailto:rtg"+
     "wg@ietf.org>\n\nEditor:   Ladislav Lhotka\n          <mailto:lhotka@nic.cz"+
     ">\n          Acee Lindem\n          <mailto:acee@cisco.com>\n          "+
     "Yingzhen Qu\n          <mailto:yingzhen.qu@huawei.com>";
   description
     "This YANG module defines essential components for the management\nof a "+
     "routing subsystem.  The model fully conforms to the Network\nManagement "+
     "Datastore Architecture (NMDA).\n\nCopyright (c) 2018 IETF Trust and the "+
     "persons\nidentified as authors of the code.  All rights reserved.\n\nRedis"+
     "tribution and use in source and binary forms, with or\nwithout modificatio"+
     "n, is permitted pursuant to, and subject\nto the license terms contained "+
     "in, the Simplified BSD License\nset forth in Section 4.c of the IETF "+
     "Trust's Legal Provisions\nRelating to IETF Documents\n(https://trustee.iet"+
     "f.org/license-info).\nThis version of this YANG module is part of RFC "+
     "8349; see\nthe RFC itself for full legal notices.";
   revision "2018-03-13" {
     description
       "Network Management Datastore Architecture (NMDA) revision.";
     reference
       "RFC 8349: A YANG Data Model for Routing Management\n        (NMDA "+
       "Version)";
   }
   revision "2016-11-04" {
     description
       "Initial revision.";
     reference
       "RFC 8022: A YANG Data Model for Routing Management";
   }
   feature multiple-ribs {
     description
       "This feature indicates that the server supports\nuser-defined RIBs.\n\nS"+
       "ervers that do not advertise this feature SHOULD provide\nexactly one "+
       "system-controlled RIB per supported address family\nand also make it the"+
       " default RIB.  This RIB then appears as an\nentry in the list '/routing/"+
       "ribs/rib'.";
   }
   feature router-id {
     description
       "This feature indicates that the server supports an explicit\n32-bit "+
       "router ID that is used by some routing protocols.\n\nServers that do not"+
       " advertise this feature set a router ID\nalgorithmically, usually to one"+
       " of the configured IPv4\naddresses.  However, this algorithm is "+
       "implementation\nspecific.";
   }
   identity address-family {
     description
       "Base identity from which identities describing address\nfamilies are "+
       "derived.";
   }
   identity ipv4 {
     base "address-family";
     description
       "This identity represents an IPv4 address family.";
   }
   identity ipv6 {
     base "address-family";
     description
       "This identity represents an IPv6 address family.";
   }
   identity control-plane-protocol {
     description
       "Base identity from which control-plane protocol identities are\nderived."+
       "";
   }
   identity routing-protocol {
     base "control-plane-protocol";
     description
       "Identity from which Layer 3 routing protocol identities are\nderived.";
   }
   identity direct {
     base "routing-protocol";
     description
       "Routing pseudo-protocol that provides routes to directly\nconnected "+
       "networks.";
   }
   identity static {
     base "routing-protocol";
     description
       "'Static' routing pseudo-protocol.";
   }
   container routing {
     description
       "Configuration parameters for the routing subsystem.";
     container control-plane-protocols {
       description
         "Support for control-plane protocol instances.";
       list control-plane-protocol {
         key "type name";
         description
           "Each entry contains a control-plane protocol instance.";
         leaf type {
           type "identityref" {
             base "control-plane-protocol";
           }
           description
             "Type of the control-plane protocol -- an identity\nderived from "+
             "the 'control-plane-protocol'\nbase identity.";
         }
         leaf name {
           type "string" {
             length "1..10";
           }
           description
             "An arbitrary name of the control-plane protocol\ninstance.";
           must "((../type='rt:static' or ../type='rt:direct') and ../name='defa"+
                "ult')";
         }
         container static-routes {
           when "derived-from-or-self(../type, 'rt:static')" {
             description
               "This container is only valid for the 'static' routing\nprotocol."+
               "";
           }
           description
             "Support for the 'static' pseudo-protocol.\n\nAddress-family-specif"+
             "ic modules augment this node with\ntheir lists of routes.";
         }
       }
     }
   }
 }

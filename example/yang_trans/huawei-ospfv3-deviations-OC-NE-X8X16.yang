/*
Copyright (C) 2019 Huawei Technologies Co., Ltd. All rights reserved.
*/

 module huawei-ospfv3-deviations-OC-NE-X8X16 {
   namespace "urn:huawei:yang:huawei-ospfv3-deviations-OC-NE-X8X16";
   prefix "ospfv3-devs-OC-NE-X8X16";
   import huawei-ospfv3 {
     prefix "ospfv3";
   }
   import huawei-ifm {
     prefix "ifm";
   }
   import huawei-if-ip {
     prefix "if-ip";
   }
   import huawei-ip {
     prefix "ip";
   }
   import huawei-network-instance {
     prefix "ni";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-ospfv3 module.";
   revision "2019-04-04" {
     description
       "Initial revision.";
     reference
       "Huawei private.";
   }
   typedef authen-mode-deviations {
     type "enumeration" {
       enum "none" {
         value "0";
         description
           "To cancel authentication.";
       }
       enum "hmac-sha256" {
         value "2";
         description
           "Cipher text authentication mode.";
       }
       enum "hmac-sm3" {
         value "4";
         description
           "Cipher text authentication mode.";
       }
     }
     description
       "OSPFv3 authencation mode.";
   }
   deviation "/ni:network-instance/ni:instances/ni:instance/ospfv3:ospfv3/ospfv3"+
             ":sites/ospfv3:site/ospfv3:authentication/ospfv3:mode" {
     deviate "replace" {
       type "ospfv3-devs-OC-NE-X8X16:authen-mode-deviations";
     }
   }
   deviation "/ni:network-instance/ni:instances/ni:instance/ospfv3:ospfv3/ospfv3"+
             ":sites/ospfv3:site/ospfv3:areas/ospfv3:area/ospfv3:authentication/"+
             "ospfv3:mode" {
     deviate "replace" {
       type "ospfv3-devs-OC-NE-X8X16:authen-mode-deviations";
     }
   }
   deviation "/ni:network-instance/ni:instances/ni:instance/ospfv3:ospfv3/ospfv3"+
             ":sites/ospfv3:site/ospfv3:areas/ospfv3:area/ospfv3:interfaces/ospf"+
             "v3:interface/ospfv3:authentication/ospfv3:mode" {
     deviate "replace" {
       type "ospfv3-devs-OC-NE-X8X16:authen-mode-deviations";
     }
   }
   deviation "/ni:network-instance/ni:instances/ni:instance/ospfv3:ospfv3/ospfv3"+
             ":sites/ospfv3:site/ospfv3:nexthop-weights/ospfv3:nexthop-weight/os"+
             "pfv3:if-name" {
     deviate "add" {
       must "/ifm:ifm/ifm:interfaces/ifm:interface[ifm:name=current()]/ip:ipv6 "+
            "or /ni:network-instance/ni:instances/ni:instance/if-ip:ipv6-ifs/if-"+
            "ip:ipv6-if[if-ip:name=current()/../ospfv3:if-name]";
     }
   }
   deviation "/ni:network-instance/ni:instances/ni:instance/ospfv3:ospfv3/ospfv3"+
             ":sites/ospfv3:site/ospfv3:silent-interfaces/ospfv3:silent-interfac"+
             "e/ospfv3:if-name" {
     deviate "add" {
       must "/ifm:ifm/ifm:interfaces/ifm:interface[ifm:name=current()]/ip:ipv6 "+
            "or /ni:network-instance/ni:instances/ni:instance/if-ip:ipv6-ifs/if-"+
            "ip:ipv6-if[if-ip:name=current()/../ospfv3:if-name]";
     }
   }
   deviation "/ni:network-instance/ni:instances/ni:instance/ospfv3:ospfv3/ospfv3"+
             ":sites/ospfv3:site/ospfv3:undo-silent-interfaces/ospfv3:undo-silen"+
             "t-interface/ospfv3:if-name" {
     deviate "add" {
       must "/ifm:ifm/ifm:interfaces/ifm:interface[ifm:name=current()]/ip:ipv6 "+
            "or /ni:network-instance/ni:instances/ni:instance/if-ip:ipv6-ifs/if-"+
            "ip:ipv6-if[if-ip:name=current()/../ospfv3:if-name]";
     }
   }
   deviation "/ni:network-instance/ni:instances/ni:instance/ospfv3:ospfv3/ospfv3"+
             ":sites/ospfv3:site/ospfv3:areas/ospfv3:area/ospfv3:interfaces/ospf"+
             "v3:interface/ospfv3:name" {
     deviate "add" {
       must "/ifm:ifm/ifm:interfaces/ifm:interface[ifm:name=current()]/ip:ipv6 "+
            "or /ni:network-instance/ni:instances/ni:instance/if-ip:ipv6-ifs/if-"+
            "ip:ipv6-if[if-ip:name=current()/../ospfv3:name]";
     }
   }
 }

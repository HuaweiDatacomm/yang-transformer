/*
Copyright (C) 2019 Huawei Technologies Co., Ltd. All rights reserved.
*/

 module huawei-bfd-notification-deviations-OC-NE-X8X16 {
   yang-version "1";
   namespace "urn:huawei:yang:huawei-bfd-notification-deviations-OC-NE-X8X16";
   prefix "bfd-notification-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Notification of bfd-notification-deviations-ne40e.";
   revision "2019-07-08" {
     description
       "Initial revision.";
     reference
       "Huawei private.";
   }
 }

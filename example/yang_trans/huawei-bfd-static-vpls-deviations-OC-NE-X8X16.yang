/*
Copyright (C) 2019 Huawei Technologies Co., Ltd. All rights reserved.
*/

 module huawei-bfd-static-vpls-deviations-OC-NE-X8X16 {
   yang-version "1";
   namespace "urn:huawei:yang:huawei-bfd-static-vpls-deviations-OC-NE-X8X16";
   prefix "bfd-vpls-devs-OC-NE-X8X16";
   import huawei-bfd {
     prefix "bfd";
   }
   import huawei-bfd-static-vpls {
     prefix "bfd-static-vpls";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "Bidirectional Forwarding Detection (BFD) is a detection mechanism used "+
     "uniformly on the entire network. BFD is used to rapidly detect and monitor"+
     " the connectivity of links or IP routes on a network.";
   revision "2019-04-23" {
     description
       "Initial revision.";
     reference
       "Huawei private.";
   }
   deviation "/bfd:bfd/bfd:sessions/bfd:session/bfd-static-vpls:vpls-groups/bfd-"+
             "static-vpls:vpls-group/bfd-static-vpls:sub-select-slot-id" {
     deviate "replace" {
       type "leafref" {
         path "/devm:devm/devm:lpu-boards/devm:lpu-board/devm:position";
       }
     }
   }
 }

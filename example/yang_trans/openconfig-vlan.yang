module openconfig-vlan {
   yang-version "1";
   namespace "http://openconfig.net/yang/vlan";
   prefix "oc-vlan";
   import openconfig-vlan-types {
     prefix "oc-vlan-types";
   }
   import openconfig-interfaces {
     prefix "oc-if";
   }
   import openconfig-if-ethernet {
     prefix "oc-eth";
   }
   import openconfig-if-aggregate {
     prefix "oc-lag";
   }
   import openconfig-extensions {
     prefix "oc-ext";
   }
   organization
     "OpenConfig working group";
   contact
     "OpenConfig working group\nnetopenconfig@googlegroups.com";
   description
     "This module defines configuration and state variables for VLANs,\nin "+
     "addition to VLAN parameters associated with interfaces";
   oc-ext:openconfig-version "3.2.0";
   revision "2019-04-16" {
     description
       "Update import prefix for iana-if-type module";
     reference
       "3.2.0";
   }
   revision "2019-01-31" {
     description
       "Revise QinQ matching and add input/output VLAN stack operations.";
     reference
       "3.1.0";
   }
   revision "2018-11-21" {
     description
       "Add OpenConfig module metadata extensions.";
     reference
       "3.0.2";
   }
   revision "2018-06-05" {
     description
       "Fix bugs in when statements.";
     reference
       "3.0.1";
   }
   revision "2018-02-14" {
     description
       "Fix bug with name of 802.1ad identity.";
     reference
       "3.0.0";
   }
   revision "2017-07-14" {
     description
       "Move top-level vlan data to network-instance; Update\nidentities to "+
       "comply to style guide; fixed pattern\nquoting; corrected trunk vlan "+
       "types; added TPID config to\nbase interface.";
     reference
       "2.0.0";
   }
   revision "2016-05-26" {
     description
       "OpenConfig public release";
     reference
       "1.0.2";
   }
   oc-ext:regexp-posix;
   oc-ext:catalog-organization "openconfig";
   oc-ext:origin "openconfig";
   augment "/oc-if:interfaces/oc-if:interface/oc-if:subinterfaces/oc-if:subinter"+
           "face" {
     description
       "Adds VLAN settings to individual subinterfaces";
     container vlan {
       description
         "Enclosing container for VLAN interface-specific\ndata on subinterfaces"+
         "";
       container match {
         description
           "Configuration for various VLAN tag matching schemes,\nincluding "+
           "single-tagged 802.1q packets and double-tagged\n802.1ad 'Q-in-Q' "+
           "packets. Typically only one of the subordinate\ncontainers should be"+
           " specified.\n\nWildcards may be matched by specifying range values "+
           "of 2-4094.\nIf implementations have a more efficient way to match "+
           "Wildcards\nthen they should recognize this pattern and translate "+
           "accordingly.\n\nImplementations are expected to return errors for "+
           "combinations\nthat they do not support, or provide deviations to the"+
           " same effect.\n\nFor simple VLAN configurations without an "+
           "'egress-mapping' then\nusing the 'single-tagged' and 'double-tagged'"+
           " VLAN matches that\nresolve to specific values, these specify the "+
           "VLAN identifiers\napplied to packets on egress.";
         container single-tagged {
           description
             "Match single-tagged packets with an exact VLAN identifier.";
           container config {
             description
               "Configuration for matching single-tagged packets with an "+
               "exact\nVLAN identifier.";
             leaf vlan-id {
               type "oc-vlan-types:vlan-id";
               description
                 "VLAN identifier for single-tagged packets.";
               must "not(../../../oc-vlan:double-tagged/oc-vlan:config/oc-vlan:i"+
                    "nner-vlan-id) and not(../../../oc-vlan:double-tagged/oc-vla"+
                    "n:config/oc-vlan:outer-vlan-id)";
             }
           }
           container state {
             config "false";
             description
               "State for matching single-tagged packets with an exact "+
               "VLAN\nidentifier.";
             leaf vlan-id {
               type "oc-vlan-types:vlan-id";
               description
                 "VLAN identifier for single-tagged packets.";
             }
           }
         }
         container double-tagged {
           description
             "Match double-tagged packets against inner exact and outer "+
             "exact\nVLAN identifiers.";
           container config {
             description
               "Configuration for matching double-tagged packets against "+
               "inner\nexact and outer exact VLAN identifiers.";
             leaf inner-vlan-id {
               type "oc-vlan-types:vlan-id";
               description
                 "Inner VLAN identifier for double-tagged packets.";
               must "../outer-vlan-id and not(../../../oc-vlan:single-tagged/oc-"+
                    "vlan:config/oc-vlan:vlan-id)";
             }
             leaf outer-vlan-id {
               type "oc-vlan-types:vlan-id";
               description
                 "Outer VLAN identifier for double-tagged packets.";
               must "../inner-vlan-id and not(../../../oc-vlan:single-tagged/oc-"+
                    "vlan:config/oc-vlan:vlan-id)";
             }
           }
           container state {
             config "false";
             description
               "State for matching double-tagged packets against inner "+
               "exact\nand outer exact VLAN identifiers.";
             leaf inner-vlan-id {
               type "oc-vlan-types:vlan-id";
               description
                 "Inner VLAN identifier for double-tagged packets.";
             }
             leaf outer-vlan-id {
               type "oc-vlan-types:vlan-id";
               description
                 "Outer VLAN identifier for double-tagged packets.";
             }
           }
         }
       }
     }
   }
   augment "/oc-if:interfaces/oc-if:interface/oc-if:config" {
     description
       "Adds TPID / ethertype setting for the base interface";
     leaf tpid {
       type "identityref" {
         base "oc-vlan-types:TPID_TYPES";
       }
       default "oc-vlan-types:TPID_0X8100";
       description
         "Optionally set the tag protocol identifier field (TPID) that\nis "+
         "accepted on the VLAN";
       must "../tpid!='oc-vlan-types:TPID_ANY'";
     }
   }
   augment "/oc-if:interfaces/oc-if:interface/oc-if:state" {
     description
       "Adds TPID / ethertype opstate for the base interface";
     leaf tpid {
       type "identityref" {
         base "oc-vlan-types:TPID_TYPES";
       }
       default "oc-vlan-types:TPID_0X8100";
       description
         "Optionally set the tag protocol identifier field (TPID) that\nis "+
         "accepted on the VLAN";
     }
   }
   augment "/oc-if:interfaces/oc-if:interface/oc-eth:ethernet" {
     description
       "Adds VLAN settings to individual Ethernet interfaces";
   }
   augment "/oc-if:interfaces/oc-if:interface/oc-lag:aggregation" {
     description
       "Adds VLAN settings to a LAG interface";
   }
   augment "/oc-if:interfaces/oc-if:interface" {
     description
       "Adds configuration and state for routed VLAN interfaces";
   }
 }

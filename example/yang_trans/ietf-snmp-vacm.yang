submodule ietf-snmp-vacm {
   belongs-to ietf-snmp {
     prefix "snmp";
   }
   include ietf-snmp-common;
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Martin Bjorklund\n          <mailto:mbj@tail-"+
     "f.com>\nEditor:   Juergen Schoenwaelder\n          <mailto:j.schoenwaelder"+
     "@jacobs-university.de>";
   description
     "This submodule contains a collection of YANG definitions\nfor configuring "+
     "the View-based Access Control Model (VACM)\nof SNMP.\nCopyright (c) 2014 "+
     "IETF Trust and the persons identified as\nauthors of the code.  All rights"+
     " reserved.\nRedistribution and use in source and binary forms, with "+
     "or\nwithout modification, is permitted pursuant to, and subject\nto the "+
     "license terms contained in, the Simplified BSD License\nset forth in "+
     "Section 4.c of the IETF Trust's Legal Provisions\nRelating to IETF "+
     "Documents\n(http://trustee.ietf.org/license-info).\nThis version of this "+
     "YANG module is part of RFC 7407; see\nthe RFC itself for full legal "+
     "notices.";
   reference
     "RFC 3415: View-based Access Control Model (VACM) for the\nSimple Network "+
     "Management Protocol (SNMP)";
   revision "2014-12-10" {
     description
       "Initial revision.";
     reference
       "RFC 7407: A YANG Data Model for SNMP Configuration";
   }
   typedef view-name {
     type "snmp:identifier";
     description
       "The view-name type represents an SNMP VACM view name.";
   }
   typedef group-name {
     type "snmp:identifier";
     description
       "The group-name type represents an SNMP VACM group name.";
   }
   augment "/snmp:snmp" {
     container vacm {
       description
         "Configuration of the View-based Access Control Model.";
       list group {
         key "name";
         description
           "VACM groups.\nThis data model has a different structure than the "+
           "MIB.\nGroups are explicitly defined in this list, and group\nmembers"+
           " are defined in the 'member' list (mapped to\nvacmSecurityToGroupTab"+
           "le), and access for the group is\ndefined in the 'access' list "+
           "(mapped to\nvacmAccessTable).";
         reference
           "RFC 3415: View-based Access Control Model (VACM) for the\nSimple "+
           "Network Management Protocol (SNMP).\nSNMP-VIEW-BASED-ACM-MIB.vacmSec"+
           "urityToGroupTable\nSNMP-VIEW-BASED-ACM-MIB.vacmAccessTable";
         leaf name {
           type "group-name";
           description
             "The name of this VACM group.";
           reference
             "RFC 3415: View-based Access Control Model (VACM) for the\nSimple "+
             "Network Management Protocol (SNMP).\nSNMP-VIEW-BASED-ACM-MIB.vacmG"+
             "roupName";
         }
         list member {
           key "security-name";
           description
             "A member of this VACM group.\nA specific combination of security-n"+
             "ame and\nsecurity-model MUST NOT be present in more than\none "+
             "group.";
           reference
             "RFC 3415: View-based Access Control Model (VACM) for the\nSimple "+
             "Network Management Protocol (SNMP).\nSNMP-VIEW-BASED-ACM-MIB.vacmS"+
             "ecurityToGroupTable";
           leaf security-name {
             type "snmp:security-name";
             description
               "The securityName of a group member.";
             reference
               "RFC 3415: View-based Access Control Model (VACM) for\nthe Simple"+
               " Network Management Protocol (SNMP).\nSNMP-VIEW-BASED-ACM-MIB.va"+
               "cmSecurityName";
           }
           leaf-list security-model {
             type "snmp:security-model";
             min-elements "1";
             description
               "The security models under which this security-name\nis a member "+
               "of this group.";
             reference
               "RFC 3415: View-based Access Control Model (VACM) for\nthe Simple"+
               " Network Management Protocol (SNMP).\nSNMP-VIEW-BASED-ACM-MIB.va"+
               "cmSecurityModel";
           }
         }
         list access {
           key "context security-model security-level";
           description
             "Definition of access right for groups.";
           reference
             "RFC 3415: View-based Access Control Model (VACM) for\nthe Simple "+
             "Network Management Protocol (SNMP).\nSNMP-VIEW-BASED-ACM-MIB.vacmA"+
             "ccessTable";
           leaf context {
             type "empty";
             description
               "The context (prefix) under which the access rights\napply.";
             reference
               "RFC 3415: View-based Access Control Model (VACM) for\nthe Simple"+
               " Network Management Protocol (SNMP).\nSNMP-VIEW-BASED-ACM-MIB.va"+
               "cmAccessContextPrefix";
           }
           leaf context-match {
             type "enumeration" {
               enum "exact" {
                 value "1";
                 description
                   "Exact.";
               }
             }
             default "exact";
             reference
               "RFC 3415: View-based Access Control Model (VACM) for\nthe Simple"+
               " Network Management Protocol (SNMP).\nSNMP-VIEW-BASED-ACM-MIB.va"+
               "cmAccessContextMatch";
           }
           leaf security-model {
             type "snmp:security-model-or-any";
             description
               "The security model under which the access rights\napply.";
             reference
               "RFC 3415: View-based Access Control Model (VACM) for\nthe Simple"+
               " Network Management Protocol (SNMP).\nSNMP-VIEW-BASED-ACM-MIB.va"+
               "cmAccessSecurityModel";
           }
           leaf security-level {
             type "snmp:security-level";
             description
               "The minimum security level under which the access\nrights "+
               "apply.";
             reference
               "RFC 3415: View-based Access Control Model (VACM) for\nthe Simple"+
               " Network Management Protocol (SNMP).\nSNMP-VIEW-BASED-ACM-MIB.va"+
               "cmAccessSecurityLevel";
           }
           leaf read-view {
             type "view-name";
             description
               "The name of the MIB view of the SNMP context\nauthorizing read "+
               "access.  If this leaf does not\nexist in a configuration, it "+
               "maps to a zero-length\nvacmAccessReadViewName.\nImplementations "+
               "MAY restrict the values of this\nleaf to be one of the available"+
               " values of\n/snmp/vacm/view/name in a valid configuration.";
             reference
               "RFC 3415: View-based Access Control Model (VACM) for\nthe Simple"+
               " Network Management Protocol (SNMP).\nSNMP-VIEW-BASED-ACM-MIB.va"+
               "cmAccessReadViewName";
             default "ViewDefault";
           }
           leaf write-view {
             type "view-name";
             description
               "The name of the MIB view of the SNMP context\nauthorizing write "+
               "access.  If this leaf does not\nexist in a configuration, it "+
               "maps to a zero-length\nvacmAccessWriteViewName.\nImplementations"+
               " MAY restrict the values of this\nleaf to be one of the "+
               "available values of\n/snmp/vacm/view/name in a valid configurati"+
               "on.";
             reference
               "RFC 3415: View-based Access Control Model (VACM) for\nthe Simple"+
               " Network Management Protocol (SNMP).\nSNMP-VIEW-BASED-ACM-MIB.va"+
               "cmAccessWriteViewName";
           }
           leaf notify-view {
             type "view-name";
             description
               "The name of the MIB view of the SNMP context\nauthorizing notify"+
               " access.  If this leaf does not\nexist in a configuration, it "+
               "maps to a zero-length\nvacmAccessNotifyViewName.\nImplementation"+
               "s MAY restrict the values of this\nleaf to be one of the "+
               "available values of\n/snmp/vacm/view/name in a valid configurati"+
               "on.";
             reference
               "RFC 3415: View-based Access Control Model (VACM) for\n  the "+
               "Simple Network Management Protocol (SNMP).\n  SNMP-VIEW-BASED-AC"+
               "M-MIB.vacmAccessNotifyViewName";
           }
         }
       }
       list view {
         key "name";
         description
           "Definition of MIB views.";
         reference
           "RFC 3415: View-based Access Control Model (VACM) for\nthe Simple "+
           "Network Management Protocol (SNMP).\nSNMP-VIEW-BASED-ACM-MIB.vacmVie"+
           "wTreeFamilyTable";
         leaf name {
           type "view-name";
           description
             "The name of this VACM MIB view.";
           reference
             "RFC 3415: View-based Access Control Model (VACM) for\nthe Simple "+
             "Network Management Protocol (SNMP).\nSNMP-VIEW-BASED-ACM-MIB.vacmV"+
             "iewTreeFamilyName";
         }
         leaf-list include {
           type "snmp:wildcard-object-identifier";
           description
             "A family of subtrees included in this MIB view.";
           reference
             "RFC 3415: View-based Access Control Model (VACM) for\nthe Simple "+
             "Network Management Protocol (SNMP).\nSNMP-VIEW-BASED-ACM-MIB.vacmV"+
             "iewTreeFamilySubtree\nSNMP-VIEW-BASED-ACM-MIB.vacmViewTreeFamilyMa"+
             "sk\nSNMP-VIEW-BASED-ACM-MIB.vacmViewTreeFamilyType";
         }
         leaf-list exclude {
           type "snmp:wildcard-object-identifier";
           description
             "A family of subtrees excluded from this MIB view.";
           reference
             "RFC 3415: View-based Access Control Model (VACM) for\nthe Simple "+
             "Network Management Protocol (SNMP).\nSNMP-VIEW-BASED-ACM-MIB.vacmV"+
             "iewTreeFamilySubtree\nSNMP-VIEW-BASED-ACM-MIB.vacmViewTreeFamilyMa"+
             "sk\nSNMP-VIEW-BASED-ACM-MIB.vacmViewTreeFamilyType";
         }
       }
     }
   }
 }

/*
Copyright (C) 2019 Huawei Technologies Co., Ltd. All rights reserved.
*/

 module huawei-mvpn-forward {
   namespace "urn:huawei:yang:huawei-mvpn-forward";
   prefix "mvpn-forward";
   import huawei-network-instance {
     prefix "ni";
   }
   import huawei-l3vpn {
     prefix "l3vpn";
   }
   import huawei-extension {
     prefix "ext";
   }
   import huawei-mvpn {
     prefix "mvpn";
   }
   organization
     "Huawei Technologies Co., Ltd.";
   contact
     "Huawei Industrial Base\nBantian, Longgang\nShenzhen 518129\nPeople's "+
     "Republic of China\nWebsite: http://www.huawei.com\nEmail: support@huawei.c"+
     "om";
   description
     "Multicast virtual private network.";
   revision "2019-03-26" {
     description
       "Init revision.";
     reference
       "Huawei private.";
   }
   ext:task-name "mvpn";
   typedef enableflag {
     type "enumeration" {
       enum "true" {
         value "1";
         description
           "Multicast-vpn TTL propagate is enabled.";
       }
       enum "false" {
         value "0";
         description
           "Multicast-vpn TTL propagate is disabled.";
       }
     }
     description
       "Enable flag type.";
   }
   container mvpn-forward {
     description
       "Multicast forwarding table.";
     container global {
       description
         "Configure MVPN global configuration.";
       container ttl-propagate {
         description
           "Configure MVPN TTL value.";
         leaf enable {
           type "enableflag";
           default "false";
           description
             "Propagate the TTL value used by the private network to the public "+
             "network.";
         }
       }
       container multicast-vpn-slots {
         description
           "List of MVPN integrated boards.";
         list multicast-vpn-slot {
           key "slot";
           description
             "Configure MVPN integrated board.";
           leaf slot {
             type "string" {
               length "1..15";
             }
             description
               "Slot number of the board on which MVPN is to be enabled.";
           }
         }
       }
       container ng-mvpn-forward-mode {
         description
           "Configure the NGMVPN forwarding mode. You can modify the configurati"+
           "on five minutes after the configuration takes effect.";
         leaf propagate-enable {
           type "enableflag";
           default "false";
           description
             "Config loopback mode.";
         }
       }
     }
   }
   augment "/ni:network-instance/ni:instances/ni:instance/l3vpn:afs/l3vpn:af/mvp"+
           "n:mvpn/mvpn:mvpn-type/mvpn:ng-mvpn/mvpn:ng" {
     description
       "Configure WTR attribute on MVPN template.";
     container multicast-wtr {
       when "../mvpn:is-c-multicast-frr='true'";
       description
         "Configure wait time restore.";
       leaf wtr {
         type "uint16" {
           range "60..1800";
         }
         units "s";
         default "600";
         description
           "Wait time restore.";
       }
     }
   }
 }

/*
Copyright (C) 2019 Huawei Technologies Co., Ltd. All rights reserved.
*/

 module huawei-nd-deviations-OC-NE-X8X16 {
   namespace "urn:huawei:yang:huawei-nd-deviations-OC-NE-X8X16";
   prefix "nd-devs-OC-NE-X8X16";
   import huawei-nd {
     prefix "nd";
   }
   organization
     "Huawei Technologies Co., Ltd.";
   contact
     "Huawei Industrial Base\nBantian, Longgang\nShenzhen 518129\nPeople's "+
     "Republic of China\nWebsite: http://www.huawei.com\nEmail: support@huawei.c"+
     "om";
   description
     "ND management.";
   revision "2019-04-24" {
     description
       "Initial revision.";
     reference
       "Huawei private.";
   }
   deviation "/nd:nd/nd:ipv6-neighbors/nd:ipv6-neighbor/nd:bd-id" {
     deviate "replace" {
       type "uint32" {
         range "1..32768";
       }
     }
   }
 }

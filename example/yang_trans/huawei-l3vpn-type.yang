/*
Copyright (C) 2019-2020 Huawei Technologies Co., Ltd. All rights reserved.
*/

 submodule huawei-l3vpn-type {
   belongs-to huawei-l3vpn {
     prefix "l3vpn";
   }
   organization
     "Huawei Technologies Co., Ltd.";
   contact
     "Huawei Industrial Base\nBantian, Longgang\nShenzhen 518129\nPeople's "+
     "Republic of China\nWebsite: http://www.huawei.com\nEmail: support@huawei.c"+
     "om";
   description
     "This YANG module defines a YANG data model to configure and manage "+
     "\nLayer3 VPNs. It augments the huawei-network-instance yang model \nto add"+
     " L3VPN specific configuration.";
   revision "2020-03-13" {
     description
       "The YANG descriptions are modified according to new standards.";
     reference
       "Huawei private.";
   }
   revision "2019-04-27" {
     description
       "Initial revision.";
     reference
       "Huawei private.";
   }
   typedef vpn-target-type {
     type "enumeration" {
       enum "export-extcommunity" {
         value "2";
         description
           "Specifies the value of the extended community attribute \nof the "+
           "route from an outbound interface to the destination\nVPN.";
       }
       enum "import-extcommunity" {
         value "3";
         description
           "Receives routes that carry the specified extended community "+
           "attribute value.";
       }
     }
     description
       "The type of vpn target.";
   }
   typedef label-mode-type {
     type "enumeration" {
       enum "per-instance" {
         value "1";
         description
           "Labels are assigned to VPN instances in 'one label per \ninstance' "+
           "mode, that is, all routes in a VPN instance \nare assigned with the "+
           "same label.";
       }
       enum "per-route" {
         value "0";
         description
           "Labels are assigned to routes in the 'one label per route' "+
           "mode,\nthat is, each route is assigned with one label.";
       }
       enum "per-nexthop" {
         value "2";
         description
           "Labels are assigned to routes in the 'one label per nexthop' \nmode,"+
           " that is, all routes with the same nexthop are assigned \nwith the "+
           "same label.";
       }
     }
     description
       "The mode of l3vpncommonLabel.";
   }
   typedef af-type {
     type "enumeration" {
       enum "ipv4-unicast" {
         value "1";
         description
           "IPv4 unicast address family.";
       }
       enum "ipv6-unicast" {
         value "5";
         description
           "IPv6 unicast address family.";
       }
     }
     description
       "The type of l3vpncommonL3vpnPrefix.";
   }
   typedef vpn-status-type {
     type "enumeration" {
       enum "up" {
         value "1";
         description
           "VPN Instance status Up.";
       }
       enum "down" {
         value "2";
         description
           "VPN Instance status Down.";
       }
     }
     description
       "The status of the vpn-instance.";
   }
   typedef lsp-operation-type {
     type "enumeration" {
       enum "pop" {
         value "0";
         description
           "Label Operation Mode: POP.";
       }
       enum "pop-go" {
         value "1";
         description
           "Label Operation Mode: POPGO.";
       }
     }
     description
       "The label operation mode of the l3vpncommon.";
   }
 }

/*
Copyright (C) 2020 Huawei Technologies Co., Ltd. All rights reserved.
*/

 module huawei-system-event-management {
   namespace "urn:huawei:yang:huawei-system-event-management";
   prefix "sem";
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "System Event Management (SEM).";
   revision "2020-05-08" {
     description
       "Initial revision.";
     reference
       "Huawei private.";
   }
   ext:task-name "device-mgr";
   typedef slave-switch-mode {
     type "enumeration" {
       enum "enable" {
         value "0";
         description
           "Enable.";
       }
       enum "disable" {
         value "1";
         description
           "Disable.";
       }
     }
     description
       "Switchover enable type.";
   }
   container system-event-management {
     description
       "System Event Management (SEM).";
     container slave-switch {
       description
         "Configure swithover.";
       leaf enable {
         type "slave-switch-mode";
         default "enable";
         description
           "Indicates whether to enable slave switch.";
       }
       leaf status {
         type "string" {
           length "1..80";
         }
         config "false";
         description
           "Switchover status.";
       }
       leaf primary-board-position {
         type "string" {
           length "1..32";
         }
         config "false";
         description
           "Master board position.";
       }
       leaf slave-board-position {
         type "string" {
           length "1..32";
         }
         config "false";
         description
           "Slave board position.";
       }
     }
     container batch-backup-timeout {
       description
         "Configure batch backup timeout.";
       leaf self-healing-timeout {
         type "uint32" {
           range "10..14400";
         }
         units "min";
         description
           "Self healing timeout.";
       }
     }
   }
   rpc switch-over {
     description
       "Switch over.";
     input {
       leaf position {
         type "string" {
           length "1..32";
         }
         description
           "Chassis position.";
       }
     }
   }
 }

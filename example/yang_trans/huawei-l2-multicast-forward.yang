/*
Copyright (C) 2019 Huawei Technologies Co., Ltd. All rights reserved.
*/

 module huawei-l2-multicast-forward {
   namespace "urn:huawei:yang:huawei-l2-multicast-forward";
   prefix "l2-multicast-forward";
   import huawei-vlan {
     prefix "vlan";
   }
   import huawei-extension {
     prefix "ext";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "L2 multicast VLAN fwroding.";
   revision "2019-07-01" {
     description
       "Init revision.";
     reference
       "Huawei private.";
   }
   ext:task-name "l2mc";
   container l2-multicast-forward {
     description
       "Global configuration of l2mc forward.";
     container select-boards {
       description
         "Configure boards selected for l2mc.";
       leaf-list slot {
         type "leafref" {
           path "/devm:devm/devm:lpu-boards/devm:lpu-board/devm:position";
         }
         max-elements "20";
         description
           "Configure slot ID.";
       }
     }
   }
   augment "/vlan:vlan/vlan:vlans/vlan:vlan" {
     description
       "Multicast forward configuration to the VLAN module.";
     container multicast-forward {
       description
         "Configure multicast load splitting trunks in a VLAN.";
       container port-isolate-state {
         description
           "Configure the isolation of non-multicast traffic in a VLAN.";
         leaf enable {
           type "boolean";
           default "false";
           description
             "Enable/disable isolate non-multicast traffic.";
         }
       }
     }
   }
 }

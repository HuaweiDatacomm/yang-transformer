module openconfig-aft-types {
   namespace "http://openconfig.net/yang/fib-types";
   prefix "oc-aftt";
   import openconfig-extensions {
     prefix "oc-ext";
   }
   organization
     "OpenConfig Working Group";
   contact
     "OpenConfig Working Group\nwww.openconfig.net";
   description
     "Types related to the OpenConfig Abstract Forwarding\nTable (AFT) model";
   oc-ext:openconfig-version "0.3.3";
   revision "2019-08-01" {
     description
       "Add lsp-name leaf to AFT next-hop.";
     reference
       "0.3.3";
   }
   revision "2018-11-21" {
     description
       "Add OpenConfig module metadata extensions.";
     reference
       "0.3.2";
   }
   revision "2017-08-24" {
     description
       "Formatting fixes";
     reference
       "0.3.1";
   }
   revision "2017-05-10" {
     description
       "Refactor to provide concretised per-AF schemas per AFT.";
     reference
       "0.3.0";
   }
   oc-ext:regexp-posix;
   oc-ext:catalog-organization "openconfig";
   oc-ext:origin "openconfig";
 }

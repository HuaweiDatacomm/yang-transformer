/*
Copyright (C) 2020 Huawei Technologies Co., Ltd. All rights reserved.
*/

 module huawei-openconfig-lacp-deviations-OC-NE-X8X16 {
   yang-version "1";
   namespace "urn:huawei:yang:huawei-openconfig-lacp-deviations-OC-NE-X8X16";
   prefix "of-lacp-devs-OC-NE-X8X16";
   import openconfig-lacp {
     prefix "oc-lacp";
   }
   organization
     "Huawei Technologies Co., Ltd.";
   contact
     "Huawei Industrial Base\nBantian, Longgang\nShenzhen 518129\nPeople's "+
     "Republic of China\nWebsite: http://www.huawei.com\nEmail: support@huawei.c"+
     "om";
   description
     "Link Aggregation Control Protocol (LACP) management, which includes static"+
     " LACP configuration, dynamic LACP learning.";
   revision "2020-02-18" {
     description
       "Initial revision.";
     reference
       "Huawei private.";
   }
   typedef lacp-activity-type-deviations {
     type "enumeration" {
       enum "ACTIVE" {
         value "1";
         description
           "Interface is an active member, i.e., will detect and maintain "+
           "aggregates.";
       }
     }
     description
       "Describes the LACP membership type, active or passive, of the interface "+
       "in the aggregate.";
     reference
       "IEEE 802.1AX-2008";
   }
   deviation "/oc-lacp:lacp/oc-lacp:interfaces/oc-lacp:interface/oc-lacp:config/"+
             "oc-lacp:lacp-mode" {
     deviate "replace" {
       type "of-lacp-devs-OC-NE-X8X16:lacp-activity-type-deviations";
     }
   }
 }

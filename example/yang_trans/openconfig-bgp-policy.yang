module openconfig-bgp-policy {
   yang-version "1";
   namespace "http://openconfig.net/yang/bgp-policy";
   prefix "oc-bgp-pol";
   import openconfig-routing-policy {
     prefix "oc-rpol";
   }
   import openconfig-extensions {
     prefix "oc-ext";
   }
   organization
     "OpenConfig working group";
   contact
     "OpenConfig working group\nnetopenconfig@googlegroups.com";
   description
     "This module contains data definitions for BGP routing policy.\nIt augments"+
     " the base routing-policy module with BGP-specific\noptions for conditions "+
     "and actions.";
   oc-ext:openconfig-version "6.0.0";
   revision "2019-02-01" {
     description
       "Move BGP community match-set-options from\npolicy-definitions/statements"+
       "/.../bgp-conditions to\ndefined-sets/bgp-defined-sets/community-set for "+
       "wider platform\nsupport.";
     reference
       "6.0.0";
   }
   revision "2018-11-21" {
     description
       "Add OpenConfig module metadata extensions.";
     reference
       "5.0.2";
   }
   revision "2018-08-20" {
     description
       "Correct description of AFI-SAFI enabled leaf.";
     reference
       "5.0.1";
   }
   revision "2018-04-11" {
     description
       "Correct naming of BGP maximum prefix warning percentage leaf.";
     reference
       "5.0.0";
   }
   revision "2018-03-20" {
     description
       "Added SR-TE policy SAFI";
     reference
       "4.1.0";
   }
   revision "2017-07-10" {
     description
       "Add error notifications; moved add-paths config; add AS\nprepend policy "+
       "features; removed unneeded config leaves";
     reference
       "4.0.0";
   }
   revision "2017-02-02" {
     description
       "Bugfix to remove remaining global-level policy data";
     reference
       "3.0.1";
   }
   revision "2017-01-26" {
     description
       "Add dynamic neighbor support, migrate to OpenConfig types";
     reference
       "3.0.0";
   }
   revision "2016-06-21" {
     description
       "OpenConfig BGP refactor";
     reference
       "2.1.1";
   }
   oc-ext:regexp-posix;
   oc-ext:catalog-organization "openconfig";
   oc-ext:origin "openconfig";
   augment "/oc-rpol:routing-policy/oc-rpol:defined-sets" {
     description
       "adds BGP defined sets container to routing policy\nmodel";
     container bgp-defined-sets {
       description
         "BGP-related set definitions for policy match conditions";
       container ext-community-sets {
         description
           "Enclosing container for list of extended BGP community\nsets";
         list ext-community-set {
           key "ext-community-set-name";
           description
             "List of defined extended BGP community sets";
           leaf ext-community-set-name {
             type "leafref" {
               path "../config/ext-community-set-name";
             }
             description
               "Reference to list key";
           }
           container config {
             description
               "Configuration data for extended BGP community sets";
             leaf ext-community-set-name {
               type "union";
               description
                 "name / label of the extended community set -- this is\nused to"+
                 " reference the set in match conditions";
             }
             leaf-list ext-community-member {
               type "union" {
                 type "union";
                 type "string" {
                   length "1..1026";
                 }
               }
               description
                 "members of the extended community set\nFor an ADD operation "+
                 "these are the communities that will be added;\nthe regexp type"+
                 " is not valid in this operation.\nFor REMOVE or REPLACE "+
                 "operations then matching communities will\nbe removed unless "+
                 "match-set-options is INVERT which will\nreverse this to mean "+
                 "that anything that does not match will be\nremoved.";
               min-elements "1";
             }
             leaf match-set-options {
               type "enumeration" {
                 enum "ANY" {
                   value "0";
                   description
                     "match is true if given value matches any member\nof the "+
                     "defined set";
                 }
               }
               description
                 "Optional parameter that governs the behaviour of the\nmatch "+
                 "operation";
               default "ANY";
             }
           }
           container state {
             config "false";
             description
               "Operational state data for extended BGP community sets";
             leaf ext-community-set-name {
               type "union";
               description
                 "name / label of the extended community set -- this is\nused to"+
                 " reference the set in match conditions";
             }
             leaf-list ext-community-member {
               type "union" {
                 type "union";
                 type "string" {
                   length "1..1026";
                 }
               }
               description
                 "members of the extended community set\nFor an ADD operation "+
                 "these are the communities that will be added;\nthe regexp type"+
                 " is not valid in this operation.\nFor REMOVE or REPLACE "+
                 "operations then matching communities will\nbe removed unless "+
                 "match-set-options is INVERT which will\nreverse this to mean "+
                 "that anything that does not match will be\nremoved.";
             }
             leaf match-set-options {
               type "enumeration" {
                 enum "ANY" {
                   value "0";
                   description
                     "match is true if given value matches any member\nof the "+
                     "defined set";
                 }
               }
               description
                 "Optional parameter that governs the behaviour of the\nmatch "+
                 "operation";
               default "ANY";
             }
           }
         }
       }
     }
   }
   augment "/oc-rpol:routing-policy/oc-rpol:policy-definitions/oc-rpol:policy-de"+
           "finition/oc-rpol:statements/oc-rpol:statement/oc-rpol:conditions" {
     description
       "BGP policy conditions added to routing policy module";
     container bgp-conditions {
       description
         "Top-level container ";
       container config {
         description
           "Configuration data for BGP-specific policy conditions";
         leaf ext-community-set {
           type "leafref" {
             path "/oc-rpol:routing-policy/oc-rpol:defined-sets/oc-bgp-pol:bgp-d"+
                  "efined-sets/oc-bgp-pol:ext-community-sets/oc-bgp-pol:ext-comm"+
                  "unity-set/oc-bgp-pol:ext-community-set-name";
           }
           description
             "References a defined extended community set";
         }
       }
       container state {
         config "false";
         description
           "Operational state data for BGP-specific policy\nconditions";
         leaf ext-community-set {
           type "leafref" {
             path "/oc-rpol:routing-policy/oc-rpol:defined-sets/oc-bgp-pol:bgp-d"+
                  "efined-sets/oc-bgp-pol:ext-community-sets/oc-bgp-pol:ext-comm"+
                  "unity-set/oc-bgp-pol:ext-community-set-name";
           }
           description
             "References a defined extended community set";
         }
       }
     }
   }
   augment "/oc-rpol:routing-policy/oc-rpol:policy-definitions/oc-rpol:policy-de"+
           "finition/oc-rpol:statements/oc-rpol:statement/oc-rpol:actions" {
     description
       "BGP policy actions added to routing policy\nmodule";
   }
 }

/*
Copyright (C) 2019 Huawei Technologies Co., Ltd. All rights reserved.
*/

 module huawei-isis-deviations-OC-NE-X8X16 {
   namespace "urn:huawei:yang:huawei-isis-deviations-OC-NE-X8X16";
   prefix "isis-devs-OC-NE-X8X16";
   import huawei-isis {
     prefix "isis";
   }
   import huawei-network-instance {
     prefix "ni";
   }
   import huawei-mpls {
     prefix "mpls";
   }
   import huawei-mpls-ldp {
     prefix "mpls-ldp";
   }
   import huawei-l3vpn {
     prefix "l3vpn";
   }
   import huawei-ifm {
     prefix "ifm";
   }
   import huawei-tunnel-management {
     prefix "tnlm";
   }
   import huawei-mpls-te {
     prefix "mpls-te";
   }
   import huawei-if-ip {
     prefix "if-ip";
   }
   import huawei-ip {
     prefix "ip";
   }
   organization
     "Huawei Technologies Co., Ltd.";
   contact
     "Huawei Industrial Base\nBantian, Longgang\nShenzhen 518129\nPeople's "+
     "Republic of China\nWebsite: http://www.huawei.com\nEmail: support@huawei.c"+
     "om";
   description
     "IS-IS management.";
   revision "2019-04-04" {
     description
       "Initial revision.";
     reference
       "Huawei private.";
   }
   deviation "/ni:network-instance/ni:instances/ni:instance/isis:isis/isis:sites"+
             "/isis:site/isis:afs/isis:af/isis:mpls-ldp-global/isis:auto-flag" {
     deviate "add" {
       must "../auto-flag='false' or (../../../../../../../ni:name='_public_' "+
            "and /mpls:mpls/mpls-ldp:ldp/mpls-ldp:enable='true')";
     }
   }
   deviation "/ni:network-instance/ni:instances/ni:instance/l3vpn:afs/l3vpn:af/i"+
             "sis:isis-import-rts/isis:isis-import-rt/isis:src-vrf" {
     deviate "add" {
       must "(../../../l3vpn:type='ipv4-unicast' and /ni:network-instance/ni:ins"+
            "tances/ni:instance[ni:name=current()]/l3vpn:afs/l3vpn:af[l3vpn:type"+
            "='ipv4-unicast']) or (../../../l3vpn:type='ipv6-unicast' and "+
            "/ni:network-instance/ni:instances/ni:instance[ni:name=current()]/l3"+
            "vpn:afs/l3vpn:af[l3vpn:type='ipv6-unicast'])";
     }
   }
   deviation "/ni:network-instance/ni:instances/ni:instance/isis:isis/isis:sites"+
             "/isis:site/isis:circuits/isis:circuit/isis:silent-enable" {
     deviate "add" {
       must "../silent-enable='false' or not(/ifm:ifm/ifm:interfaces/ifm:interfa"+
            "ce[ifm:name=current()/../isis:name]/tnlm:tunnel-protocol/mpls-te:te"+
            "-tunnel)";
     }
   }
   deviation "/ni:network-instance/ni:instances/ni:instance/isis:isis/isis:sites"+
             "/isis:site/isis:circuits/isis:circuit/isis:afs/isis:af/isis:type" {
     deviate "add" {
       must "(../type='afipv4') or (../type='afipv6' and (/ifm:ifm/ifm:interface"+
            "s/ifm:interface[ifm:name=current()/../../../isis:name]/ip:ipv6 or "+
            "../../../../../../../../if-ip:ipv6-ifs/if-ip:ipv6-if[if-ip:name=cur"+
            "rent()/../../../isis:name]))";
     }
   }
 }

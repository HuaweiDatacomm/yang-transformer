/*
Copyright (C) 2019 Huawei Technologies Co., Ltd. All rights reserved.
*/

 /*
module: huawei-ietf-netconf-ext
augment /nc:commit/nc:input:
   +---- description?   string
rpcs:
   +---x cancel-query
      +---w input
         +---w set-id    uint32
notifications:
   +---n netconf-rpc-keepalive
      +--ro session-id?   uint32
      +--ro message-id?    string
*/

 module huawei-ietf-netconf-ext {
   namespace "urn:huawei:yang:huawei-ietf-netconf-ext";
   prefix "nc-ext";
   import ietf-netconf {
     prefix "nc";
   }
   import huawei-extension {
     prefix "ext";
   }
   organization
     "Huawei Technologies Co., Ltd.";
   contact
     "Huawei Industrial Base\nBantian, Longgang\nShenzhen 518129\nPeople's "+
     "Republic of China\nWebsite: http://www.huawei.com\nEmail: support@huawei.c"+
     "om";
   description
     "Extension of NETCONF protocol standard operations that were used privately"+
     " for Huawei device.";
   revision "2019-05-25" {
     description
       "Initial revision.";
     reference
       "Huawei private.";
   }
   ext:task-name "netconf";
   notification netconf-rpc-keepalive {
     description
       "This notification will be generated every 20 seconds if the operation "+
       "takes more time,\nClient must use filter to subscribe this notification "+
       "for a specific session,\nand it can report error if this notification is"+
       " not enabled without the filter.";
     leaf session-id {
       type "uint32";
       description
         "Session in which client want to receive this notitification; \nUnique "+
         "identifier for the session. This value is the NETCONF session "+
         "identifier, as defined in [RFC4741].Refer to RFC 6022 section 2.1.4.";
     }
     leaf message-id {
       type "string" {
         length "0..4095";
       }
       description
         "Message id of the rpc operation that is taking long time to execute.";
     }
   }
   augment "/nc:commit/nc:input" {
     description
       "Adds the <description> parameter to\nthe input of the NETCONF <commit> "+
       "operation.";
     leaf description {
       type "string" {
         length "1..60";
       }
       description
         "This is used for commit comments to identify specific commit "+
         "operation.";
     }
   }
   augment "/nc:delete-config/nc:input/nc:target/nc:config-target" {
     description
       "Adds the <candidate> target to\nthe input of the NETCONF <delete-config>"+
       " operation.";
     leaf candidate {
       type "empty";
       description
         "The candidate configuration is the config target.";
     }
   }
 }

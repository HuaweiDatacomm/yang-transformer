submodule openconfig-aaa-tacacs {
   yang-version "1";
   belongs-to openconfig-aaa {
     prefix "oc-aaa";
   }
   import openconfig-extensions {
     prefix "oc-ext";
   }
   import openconfig-aaa-types {
     prefix "oc-aaa-types";
   }
   organization
     "OpenConfig working group";
   contact
     "OpenConfig working group\nwww.openconfig.net";
   description
     "This module defines configuration and operational state data\nrelated to "+
     "the TACACS+ protocol for authentication,\nauthorization, and accounting.";
   oc-ext:openconfig-version "0.3.0";
   revision "2017-09-18" {
     description
       "Updated to use OpenConfig types modules";
     reference
       "0.3.0";
   }
   revision "2017-07-06" {
     description
       "Move to oc-inet types, add IETF attribution, add RADIUS\ncounters, "+
       "changed password leaf names to indicate hashed";
     reference
       "0.2.0";
   }
   revision "2017-01-29" {
     description
       "Initial public release";
     reference
       "0.1.0";
   }
   identity TACACS {
     base "oc-aaa-types:AAA_SERVER_TYPE";
     description
       "Terminal Access Controller Access Control System (TACACS+)\nAAA server";
     reference
       "The TACACS+ Protocol (draft-ietf-opsawg-tacacs-05)\nRFC 1492 - An Access"+
       " Control Protocol, Sometimes Called\nTACACS";
   }
 }

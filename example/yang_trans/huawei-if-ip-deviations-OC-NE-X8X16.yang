/*
Copyright (C) 2020 Huawei Technologies Co., Ltd. All rights reserved.
*/

 module huawei-if-ip-deviations-OC-NE-X8X16 {
   namespace "urn:huawei:yang:huawei-if-ip-deviations-OC-NE-X8X16";
   prefix "if-ip-devs-OC-NE-X8X16";
   import huawei-if-ip {
     prefix "if-ip";
   }
   import huawei-network-instance {
     prefix "ni";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "Common interface management, which includes the public configuration of "+
     "interfaces.";
   revision "2020-09-28" {
     description
       "Init revision.";
     reference
       "Huawei private.";
   }
   deviation "/ni:network-instance/ni:instances/ni:instance/if-ip:ipv4-ifs/if-ip"+
             ":ipv4-if/if-ip:address/if-ip:config-address/if-ip:addresses/if-ip:"+
             "address/if-ip:type" {
     deviate "add" {
       must "../if-ip:type='sub' and /ifm:ifm/ifm:global/ifm:ipv4-ignore-primary"+
            "-sub='false' or ../if-ip:type='main'";
     }
   }
 }

module ietf-origin {
   yang-version "1.1";
   namespace "urn:ietf:params:xml:ns:yang:ietf-origin";
   prefix "or";
   import ietf-yang-metadata {
     prefix "md";
   }
   organization
     "IETF Network Modeling (NETMOD) Working Group";
   contact
     "WG Web:   <https://datatracker.ietf.org/wg/netmod/>\n\nWG List:  "+
     "<mailto:netmod@ietf.org>\n\nAuthor:   Martin Bjorklund\n          "+
     "<mailto:mbj@tail-f.com>\n\nAuthor:   Juergen Schoenwaelder\n          "+
     "<mailto:j.schoenwaelder@jacobs-university.de>\n\nAuthor:   Phil Shafer\n  "+
     "        <mailto:phil@juniper.net>\n\nAuthor:   Kent Watsen\n          "+
     "<mailto:kwatsen@juniper.net>\n\nAuthor:   Rob Wilton\n          <rwilton@c"+
     "isco.com>";
   description
     "This YANG module defines an 'origin' metadata annotation and a\nset of "+
     "identities for the origin value.\n\nCopyright (c) 2018 IETF Trust and the "+
     "persons identified as\nauthors of the code.  All rights reserved.\n\nRedis"+
     "tribution and use in source and binary forms, with or\nwithout modificatio"+
     "n, is permitted pursuant to, and subject to\nthe license terms contained "+
     "in, the Simplified BSD License set\nforth in Section 4.c of the IETF "+
     "Trust's Legal Provisions\nRelating to IETF Documents\n(https://trustee.iet"+
     "f.org/license-info).\nThis version of this YANG module is part of RFC "+
     "8342\n(https://www.rfc-editor.org/info/rfc8342); see the RFC itself\nfor "+
     "full legal notices.";
   revision "2018-02-14" {
     description
       "Initial revision.";
     reference
       "RFC 8342: Network Management Datastore Architecture (NMDA)";
   }
   identity origin {
     description
       "Abstract base identity for the origin annotation.";
   }
   identity intended {
     base "origin";
     description
       "Denotes configuration from the intended configuration\ndatastore.";
   }
   identity dynamic {
     base "origin";
     description
       "Denotes configuration from a dynamic configuration\ndatastore.";
   }
   identity system {
     base "origin";
     description
       "Denotes configuration originated by the system itself.\n\nExamples of "+
       "system configuration include applied configuration\nfor an always-existi"+
       "ng loopback interface, or interface\nconfiguration that is auto-created "+
       "due to the hardware\ncurrently present in the device.";
   }
   identity learned {
     base "origin";
     description
       "Denotes configuration learned from protocol interactions with\nother "+
       "devices, instead of via either the intended\nconfiguration datastore or "+
       "any dynamic configuration\ndatastore.\n\nExamples of protocols that "+
       "provide learned configuration\ninclude link-layer negotiations, routing "+
       "protocols, and\nDHCP.";
   }
   identity default {
     base "origin";
     description
       "Denotes configuration that does not have a configured or\nlearned value "+
       "but has a default value in use.  Covers both\nvalues defined in a "+
       "'default' statement and values defined\nvia an explanation in a "+
       "'description' statement.";
   }
   identity unknown {
     base "origin";
     description
       "Denotes configuration for which the system cannot identify the\norigin.";
   }
   typedef origin-ref {
     type "identityref" {
       base "origin";
     }
     description
       "An origin identity reference.";
   }
   md:annotation "origin" {
     type "origin-ref";
     description
       "The 'origin' annotation can be present on any configuration\ndata node "+
       "in the operational state datastore.  It specifies\nfrom where the node "+
       "originated.  If not specified for a given\nconfiguration data node, then"+
       " the origin is the same as the\norigin of its parent node in the data "+
       "tree.  The origin for\nany top-level configuration data nodes must be "+
       "specified.";
   }
 }

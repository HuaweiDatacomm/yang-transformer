/*
Copyright (C) 2019 Huawei Technologies Co., Ltd. All rights reserved.
*/

 module huawei-evpn-deviations-OC-NE-X8X16 {
   namespace "urn:huawei:yang:huawei-evpn-deviations-OC-NE-X8X16";
   prefix "evpn-devs-OC-NE-X8X16";
   import huawei-evpn {
     prefix "evpn";
   }
   import huawei-ifm {
     prefix "ifm";
   }
   import huawei-nvo3 {
     prefix "nvo3";
   }
   import huawei-evpl {
     prefix "evpl";
   }
   import huawei-vrrp {
     prefix "vrrp";
   }
   import huawei-ip {
     prefix "ip";
   }
   import huawei-mac {
     prefix "mac";
   }
   import huawei-bd {
     prefix "bd";
   }
   import huawei-l2vpn {
     prefix "l2vpn";
   }
   organization
     "Huawei Technologies Co., Ltd.";
   contact
     "Huawei Industrial Base\nBantian, Longgang\nShenzhen 518129\nPeople's "+
     "Republic of China\nWebsite: http://www.huawei.com\nEmail: support@huawei.c"+
     "om";
   description
     "EVPN configuration.";
   revision "2019-03-22" {
     description
       "Initial revision.";
     reference
       "Huawei private.";
   }
   deviation "/evpn:evpn/evpn:base-process/evpn:source-address" {
     deviate "add" {
       must "not(/ifm:ifm/ifm:interfaces/ifm:interface/nvo3:nve/nvo3:attribute[n"+
            "vo3:source-vtep-ip=current()]) and not(/ifm:ifm/ifm:interfaces/ifm:"+
            "interface/nvo3:nve/nvo3:attribute[nvo3:bypass-vtep-ip=current()])";
     }
   }
   deviation "/evpl:evpl/evpl:instances/evpl:instance/evpn:evpn/evpn:vrrp" {
     deviate "add" {
       must "(not(../../evpl:interfaces/evpl:interface/evpl:name) or (/ifm:ifm/i"+
            "fm:interfaces/ifm:interface[ifm:name=current()/../../evpl:interface"+
            "s/evpl:interface/evpl:name]/ifm:type = 'Virtual-Ethernet')) and "+
            "((current()/version='vrrp' and /ifm:ifm/ifm:interfaces/ifm:interfac"+
            "e[ifm:name=current()/interface-name]/ip:ipv4/vrrp:vrrp/vrrp:groups/"+
            "vrrp:group[vrrp:id=current()/id]) or (current()/version='vrrp6' and"+
            " /ifm:ifm/ifm:interfaces/ifm:interface[ifm:name=current()/interface"+
            "-name]/ip:ipv6/vrrp:vrrp6/vrrp:group6s/vrrp:group6[vrrp:id=current("+
            ")/id]))";
     }
   }
   deviation "/bd:bd/bd:instances/bd:instance/evpn:evpn/evpn:umr-originate" {
     deviate "add" {
       must "(../umr-originate='true' and not(../../nvo3:nvo3/nvo3:vni-list/nvo3"+
            ":vni) and not(/l2vpn:l2vpn/l2vpn:instances/l2vpn:instance/l2vpn:vpl"+
            "s/l2vpn:bds/l2vpn:bd[l2vpn:id=current()/../../bd:id]) and "+
            "(../../bd:mac-learn-style!='qualify') and not(../../mac:mac-address"+
            "s/mac:mac-address[mac:address = '0000-0000-0000'])) or (../umr-orig"+
            "inate='false')";
     }
   }
 }

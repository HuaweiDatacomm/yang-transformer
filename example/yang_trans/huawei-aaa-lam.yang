/*
Copyright (C) 2020-2021 Huawei Technologies Co., Ltd. All rights reserved.
*/

 submodule huawei-aaa-lam {
   belongs-to huawei-aaa {
     prefix "aaa";
   }
   import huawei-pub-type {
     prefix "pub-type";
   }
   include huawei-aaa-type;
   organization
     "Huawei Technologies Co., Ltd.";
   contact
     "Huawei Industrial Base\nBantian, Longgang\nShenzhen 518129\nPeople's "+
     "Republic of China\nWebsite: http://www.huawei.com\nEmail: support@huawei.c"+
     "om";
   description
     "Description of local access manage submodule.";
   revision "2021-02-05" {
     description
       "Add node enable of login-failed-limit.";
     reference
       "Huawei private.";
   }
   revision "2020-03-02" {
     description
       "Init revision.";
     reference
       "Huawei private.";
   }
   rpc change-current-password {
     description
       "Modify password of current access-user.";
     input {
       leaf old-password {
         type "pub-type:one-input-password-extend" {
           length "1..128";
         }
         mandatory "true";
         description
           "The old password of the local user.";
       }
       leaf new-password {
         type "pub-type:password-extend" {
           length "1..128";
         }
         mandatory "true";
         description
           "New password to set.";
       }
     }
   }
 }

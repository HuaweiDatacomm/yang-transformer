module openconfig-alarm-types {
   yang-version "1";
   namespace "http://openconfig.net/yang/alarms/types";
   prefix "oc-alarm-types";
   import openconfig-extensions {
     prefix "oc-ext";
   }
   organization
     "OpenConfig working group";
   contact
     "OpenConfig working group\nwww.openconfig.net";
   description
     "This module defines operational state data related to alarms\nthat the "+
     "device is reporting.\n\nThis model reuses some data items defined in the "+
     "draft IETF\nYANG Alarm Module:\nhttps://tools.ietf.org/html/draft-vallin-n"+
     "etmod-alarm-module-02\n\nPortions of this code were derived from the draft"+
     " IETF YANG Alarm\nModule. Please reproduce this note if possible.\n\nIETF "+
     "code is subject to the following copyright and license:\nCopyright (c) "+
     "IETF Trust and the persons identified as authors of\nthe code.\nAll rights"+
     " reserved.\n\nRedistribution and use in source and binary forms, with or "+
     "without\nmodification, is permitted pursuant to, and subject to the "+
     "license\nterms contained in, the Simplified BSD License set forth "+
     "in\nSection 4.c of the IETF Trust's Legal Provisions Relating\nto IETF "+
     "Documents (http://trustee.ietf.org/license-info).";
   oc-ext:openconfig-version "0.2.0";
   revision "2018-01-16" {
     description
       "Moved alarm identities into separate types module";
     reference
       "0.2.0";
   }
   identity OPENCONFIG_ALARM_TYPE_ID {
     description
       "Base identity for alarm type ID profiles";
   }
   identity AIS {
     base "OPENCONFIG_ALARM_TYPE_ID";
     description
       "Defines an alarm indication signal type of alarm";
   }
   identity EQPT {
     base "OPENCONFIG_ALARM_TYPE_ID";
     description
       "Defines an equipment related type of alarm that is specific\nto the "+
       "physical hardware";
   }
   identity LOS {
     base "OPENCONFIG_ALARM_TYPE_ID";
     description
       "Defines a loss of signal type of alarm";
   }
   identity OTS {
     base "OPENCONFIG_ALARM_TYPE_ID";
     description
       "Defines a optical transport signal type of alarm";
   }
   identity OPENCONFIG_ALARM_SEVERITY {
     description
       "Base identity for alarm severity profiles. Derived\nidentities are based"+
       " on contents of the draft\nIETF YANG Alarm Module";
     reference
       "IETF YANG Alarm Module: Draft - typedef severity\nhttps://tools.ietf.org"+
       "/html/draft-vallin-netmod-alarm-module-02";
   }
   identity UNKNOWN {
     base "OPENCONFIG_ALARM_SEVERITY";
     description
       "Indicates that the severity level could not be determined.\nThis level "+
       "SHOULD be avoided.";
   }
   identity MINOR {
     base "OPENCONFIG_ALARM_SEVERITY";
     description
       "Indicates the existence of a non-service affecting fault\ncondition and "+
       "that corrective action should be taken in\norder to prevent a more "+
       "serious (for example, service\naffecting) fault. Such a severity can be "+
       "reported, for\nexample, when the detected alarm condition is not "+
       "currently\ndegrading the capacity of the resource";
   }
   identity WARNING {
     base "OPENCONFIG_ALARM_SEVERITY";
     description
       "Indicates the detection of a potential or impending service\naffecting "+
       "fault, before any significant effects have been felt.\nAction should be "+
       "taken to further diagnose (if necessary) and\ncorrect the problem in "+
       "order to prevent it from becoming a more\nserious service affecting "+
       "fault.";
   }
   identity MAJOR {
     base "OPENCONFIG_ALARM_SEVERITY";
     description
       "Indicates that a service affecting condition has developed\nand an "+
       "urgent corrective action is required. Such a severity\ncan be reported, "+
       "for example, when there is a severe\ndegradation in the capability of "+
       "the resource and its full\ncapability must be restored.";
   }
   identity CRITICAL {
     base "OPENCONFIG_ALARM_SEVERITY";
     description
       "Indicates that a service affecting condition has occurred\nand an "+
       "immediate corrective action is required. Such a\nseverity can be "+
       "reported, for example, when a resource becomes\ntotally out of service "+
       "and its capability must be restored.";
   }
 }

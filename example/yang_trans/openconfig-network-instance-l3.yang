module openconfig-network-instance-l3 {
   yang-version "1";
   namespace "http://openconfig.net/yang/network-instance-l3";
   prefix "oc-ni-l3";
   import openconfig-extensions {
     prefix "oc-ext";
   }
   organization
     "OpenConfig working group";
   contact
     "OpenConfig working group\nwww.openconfig.net";
   description
     "This module contains groupings which specifically relate to\nLayer 3 "+
     "network instance configuration and operational state\nparameters.";
   oc-ext:openconfig-version "0.11.1";
   revision "2018-11-21" {
     description
       "Add OpenConfig module metadata extensions.";
     reference
       "0.11.1";
   }
   revision "2018-08-17" {
     description
       "Add a route limit for L3 network instances.";
     reference
       "0.11.0";
   }
   revision "2017-12-13" {
     description
       "Fix incorrect constraint on SR and MPLS containers";
     reference
       "0.9.0";
   }
   revision "2017-08-24" {
     description
       "Minor formatting fixes";
     reference
       "0.8.1";
   }
   revision "2017-02-28" {
     description
       "Add OSPFv2 to network instance";
     reference
       "0.8.0";
   }
   revision "2017-01-26" {
     description
       "Add policy forwarding to network instance";
     reference
       "0.7.0";
   }
   revision "2017-01-13" {
     description
       "Add AFT to the network instance";
     reference
       "0.6.0";
   }
   revision "2016-12-15" {
     description
       "Add segment routing to network instance";
     reference
       "0.5.0";
   }
   revision "2016-11-10" {
     description
       "Update model to include IS-IS.";
     reference
       "0.4.1";
   }
   revision "2016-09-28" {
     description
       "Change L2 instance to submodule; add MAC table";
     reference
       "0.3.0";
   }
   revision "2016-08-11" {
     description
       "Resolve repeated container names in routing protocols";
     reference
       "0.2.3";
   }
   revision "2016-07-08" {
     description
       "Updated with refactored routing protocol models";
     reference
       "0.2.1";
   }
   revision "2016-03-29" {
     description
       "Initial revision";
     reference
       "0.2.0";
   }
   revision "2016-03-14" {
     description
       "Initial revision";
     reference
       "0.1.0";
   }
   oc-ext:regexp-posix;
   oc-ext:catalog-organization "openconfig";
   oc-ext:origin "openconfig";
 }

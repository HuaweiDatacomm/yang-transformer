/*
Copyright (C) 2020 Huawei Technologies Co., Ltd. All rights reserved.
*/

 module huawei-openconfig-routing-policy-deviations-OC-NE-X8X16 {
   yang-version "1";
   namespace "urn:huawei:yang:huawei-openconfig-routing-policy-deviations-OC-NE-"+
             "X8X16";
   prefix "of-rpol-devs-OC-NE-X8X16";
   import openconfig-routing-policy {
     prefix "oc-rpol";
   }
   organization
     "Huawei Technologies Co., Ltd.";
   contact
     "Huawei Industrial Base\nBantian, Longgang\nShenzhen 518129\nPeople's "+
     "Republic of China\nWebsite: http://www.huawei.com\nEmail: support@huawei.c"+
     "om";
   description
     "Policies are expressed as a set of top-level policy definitions,\neach of "+
     "which consists of a sequence of policy statements. Policy\nstatements "+
     "consist of simple condition-action tuples. Conditions\nmay include mutiple"+
     " match or comparison operations, and similarly\nactions may be multitude "+
     "of changes to route attributes or a\nfinal disposition of accepting or "+
     "rejecting the route.";
   revision "2020-10-23" {
     description
       "Initial revision.";
     reference
       "Huawei private.";
   }
   deviation "/oc-rpol:routing-policy/oc-rpol:policy-definitions/oc-rpol:policy-"+
             "definition/oc-rpol:statements/oc-rpol:statement/oc-rpol:actions/oc"+
             "-rpol:config/oc-rpol:policy-result" {
     deviate "add" {
       default "ACCEPT_ROUTE";
     }
   }
   deviation "/oc-rpol:routing-policy/oc-rpol:policy-definitions/oc-rpol:policy-"+
             "definition/oc-rpol:config/oc-rpol:name" {
     deviate "replace" {
       type "string" {
         length "1..200";
       }
     }
   }
   deviation "/oc-rpol:routing-policy/oc-rpol:policy-definitions/oc-rpol:policy-"+
             "definition/oc-rpol:statements/oc-rpol:statement/oc-rpol:config/oc-"+
             "rpol:name" {
     deviate "replace" {
       type "string" {
         length "1..5";
         pattern "(6553[0-5]|655[0-2][0-9]|65[0-4][0-9]{2}|6[0-4][0-9]{3}|[1-5]["+
                 "0-9]{4}|[1-9][0-9]{0,3}|0)";
       }
     }
   }
   deviation "/oc-rpol:routing-policy/oc-rpol:policy-definitions/oc-rpol:policy-"+
             "definition/oc-rpol:state/oc-rpol:name" {
     deviate "replace" {
       type "string" {
         length "1..200";
       }
     }
   }
   deviation "/oc-rpol:routing-policy/oc-rpol:policy-definitions/oc-rpol:policy-"+
             "definition/oc-rpol:statements/oc-rpol:statement/oc-rpol:state/oc-r"+
             "pol:name" {
     deviate "replace" {
       type "string" {
         length "1..5";
       }
     }
   }
   deviation "/oc-rpol:routing-policy/oc-rpol:policy-definitions/oc-rpol:policy-"+
             "definition/oc-rpol:statements/oc-rpol:statement" {
     deviate "add" {
       min-elements "1";
       max-elements "65535";
     }
   }
 }

submodule ietf-snmp-engine {
   belongs-to ietf-snmp {
     prefix "snmp";
   }
   include ietf-snmp-common;
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Martin Bjorklund\n          <mailto:mbj@tail-"+
     "f.com>\nEditor:   Juergen Schoenwaelder\n          <mailto:j.schoenwaelder"+
     "@jacobs-university.de>";
   description
     "This submodule contains a collection of YANG definitions\nfor configuring "+
     "SNMP engines.\nCopyright (c) 2014 IETF Trust and the persons identified "+
     "as\nauthors of the code.  All rights reserved.\nRedistribution and use in "+
     "source and binary forms, with or\nwithout modification, is permitted "+
     "pursuant to, and subject\nto the license terms contained in, the "+
     "Simplified BSD License\nset forth in Section 4.c of the IETF Trust's Legal"+
     " Provisions\nRelating to IETF Documents\n(http://trustee.ietf.org/license-"+
     "info).\nThis version of this YANG module is part of RFC 7407; see\nthe RFC"+
     " itself for full legal notices.";
   revision "2014-12-10" {
     description
       "Initial revision.";
     reference
       "RFC 7407: A YANG Data Model for SNMP Configuration";
   }
   augment "/snmp:snmp" {
     container engine {
       description
         "Configuration of the SNMP engine.";
       leaf enabled {
         type "boolean";
         default "false";
         description
           "Enables the SNMP engine.";
       }
       list listen {
         key "name";
         description
           "Configuration of the transport endpoints on which the\nengine "+
           "listens.";
         leaf name {
           type "snmp:identifier";
           description
             "An arbitrary name for the list entry.";
           default "snmpListen";
         }
         choice transport {
           mandatory "false";
           description
             "The transport-protocol-specific parameters for this\nendpoint.  "+
             "Submodules providing configuration for\nadditional transports are "+
             "expected to augment this\nchoice.";
           case udp {
             container udp {
               leaf port {
                 type "uint16" {
                   range "161 | 1025..65535";
                 }
                 description
                   "The UDP port on which the engine listens.\nIf the port is "+
                   "not configured, an engine that\nacts as a Command Responder "+
                   "uses port 161, and\nan engine that acts as a Notification "+
                   "Receiver\nuses port 162.";
                 default "161";
               }
             }
           }
         }
       }
       container version {
         description
           "SNMP version used by the engine.";
         leaf v1 {
           type "empty";
         }
         leaf v2c {
           type "empty";
         }
         leaf v3 {
           type "empty";
         }
       }
       leaf engine-id {
         type "snmp:engine-id";
         description
           "The local SNMP engine's administratively assigned unique\nidentifier"+
           ".\nIf this leaf is not set, the device automatically\ncalculates an "+
           "engine ID, as described in RFC 3411.  A\nserver MAY initialize this "+
           "leaf with the automatically\ncreated value.";
         reference
           "RFC 3411: An Architecture for Describing Simple Network\nManagement "+
           "Protocol (SNMP) Management\nFrameworks.\nSNMP-FRAMEWORK-MIB.snmpEngi"+
           "neID";
       }
       leaf enable-authen-traps {
         type "boolean";
         description
           "Indicates whether the SNMP entity is permitted to\ngenerate "+
           "authenticationFailure traps.";
         reference
           "RFC 3418: Management Information Base (MIB) for the\nSimple Network "+
           "Management Protocol (SNMP)\nSNMPv2-MIB.snmpEnableAuthenTraps";
         default "false";
       }
     }
   }
 }

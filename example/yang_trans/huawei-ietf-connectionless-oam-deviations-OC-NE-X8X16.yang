/*
Copyright (C) 2019 Huawei Technologies Co., Ltd. All rights reserved.
*/

 module huawei-ietf-connectionless-oam-deviations-OC-NE-X8X16 {
   yang-version "1.1";
   namespace "urn:huawei:yang:huawei-ietf-connectionless-oam-deviations-OC-NE-X8"+
             "X16";
   prefix "cl-oam-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for ietf-connectionless-oam "+
     "module.";
   revision "2019-11-06" {
     description
       "Initial revision.";
     reference
       "Huawei private.";
   }
 }

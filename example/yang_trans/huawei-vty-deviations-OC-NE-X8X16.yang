/*
Copyright (C) 2019 Huawei Technologies Co., Ltd. All rights reserved.
*/

 module huawei-vty-deviations-OC-NE-X8X16 {
   namespace "urn:huawei:yang:huawei-vty-deviations-OC-NE-X8X16";
   prefix "vty-devs-OC-NE-X8X16";
   import huawei-vty {
     prefix "vty";
   }
   organization
     "Huawei Technologies Co., Ltd.";
   contact
     "Huawei Industrial Base\nBantian, Longgang\nShenzhen 518129\nPeople's "+
     "Republic of China\nWebsite: http://www.huawei.com\nEmail: support@huawei.c"+
     "om";
   description
     "VTY.";
   revision "2019-05-01" {
     description
       "Init revision.";
     reference
       "Huawei private.";
   }
   typedef vty-authmode-type-deviations {
     type "enumeration" {
       enum "password" {
         value "2";
         description
           "VTY authentication mode password.";
       }
       enum "aaa" {
         value "3";
         description
           "VTY authentication mode aaa.";
       }
       enum "init" {
         value "4";
         description
           "Undo authentication mode.";
       }
     }
     description
       "Vty and tty authentication mode type.";
   }
   deviation "/vty:vty/vty:lines/vty:line/vty:auth-mode" {
     deviate "replace" {
       type "vty-devs-OC-NE-X8X16:vty-authmode-type-deviations";
     }
   }
 }

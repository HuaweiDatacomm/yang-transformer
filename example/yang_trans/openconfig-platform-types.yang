module openconfig-platform-types {
   yang-version "1";
   namespace "http://openconfig.net/yang/platform-types";
   prefix "oc-platform-types";
   import openconfig-extensions {
     prefix "oc-ext";
   }
   organization
     "OpenConfig working group";
   contact
     "OpenConfig working group\nwww.openconfig.net";
   description
     "This module defines data types (e.g., YANG identities)\nto support the "+
     "OpenConfig component inventory model.";
   oc-ext:openconfig-version "0.8.0";
   revision "2018-01-16" {
     description
       "Added new per-component common data; add temp alarm";
     reference
       "0.8.0";
   }
   revision "2017-12-14" {
     description
       "Added anchor containers for component data, added new\ncomponent types";
     reference
       "0.7.0";
   }
   revision "2017-08-16" {
     description
       "Added power state enumerated type";
     reference
       "0.6.0";
   }
   revision "2016-12-22" {
     description
       "Added temperature state variable to component";
     reference
       "0.5.0";
   }
   identity OPENCONFIG_HARDWARE_COMPONENT {
     description
       "Base identity for hardware related components in a managed\ndevice.  "+
       "Derived identities are partially based on contents\nof the IANA Entity "+
       "MIB.";
     reference
       "IANA Entity MIB and RFC 6933";
   }
   identity OPENCONFIG_SOFTWARE_COMPONENT {
     description
       "Base identity for software-related components in a managed\ndevice";
   }
   identity CHASSIS {
     base "OPENCONFIG_HARDWARE_COMPONENT";
     description
       "Chassis component, typically with multiple slots / shelves";
   }
   identity BACKPLANE {
     base "OPENCONFIG_HARDWARE_COMPONENT";
     description
       "Backplane component for aggregating traffic, typically\ncontained in a "+
       "chassis component";
   }
   identity FABRIC {
     base "OPENCONFIG_HARDWARE_COMPONENT";
     description
       "Interconnect between ingress and egress ports on the\ndevice (e.g., a "+
       "crossbar switch).";
   }
   identity POWER_SUPPLY {
     base "OPENCONFIG_HARDWARE_COMPONENT";
     description
       "Component that is supplying power to the device";
   }
   identity FAN {
     base "OPENCONFIG_HARDWARE_COMPONENT";
     description
       "Cooling fan, or could be some other heat-reduction component";
   }
   identity SENSOR {
     base "OPENCONFIG_HARDWARE_COMPONENT";
     description
       "Physical sensor, e.g., a temperature sensor in a chassis";
   }
   identity FRU {
     base "OPENCONFIG_HARDWARE_COMPONENT";
     description
       "Replaceable hardware component that does not have a more\nspecific "+
       "defined schema.";
   }
   identity LINECARD {
     base "OPENCONFIG_HARDWARE_COMPONENT";
     description
       "Linecard component, typically inserted into a chassis slot";
   }
   identity PORT {
     base "OPENCONFIG_HARDWARE_COMPONENT";
     description
       "Physical port, e.g., for attaching pluggables and networking\ncables";
   }
   identity TRANSCEIVER {
     base "OPENCONFIG_HARDWARE_COMPONENT";
     description
       "Pluggable module present in a port";
   }
   identity CPU {
     base "OPENCONFIG_HARDWARE_COMPONENT";
     description
       "Processing unit, e.g., a management processor";
   }
   identity STORAGE {
     base "OPENCONFIG_HARDWARE_COMPONENT";
     description
       "A storage subsystem on the device (disk, SSD, etc.)";
   }
   identity INTEGRATED_CIRCUIT {
     base "OPENCONFIG_HARDWARE_COMPONENT";
     description
       "A special purpose processing unit, typically for traffic\nswitching/forw"+
       "arding (e.g., switching ASIC, NPU, forwarding\nchip, etc.)";
   }
   identity OPERATING_SYSTEM {
     base "OPENCONFIG_SOFTWARE_COMPONENT";
     description
       "Operating system running on a component";
   }
   identity COMPONENT_OPER_STATUS {
     description
       "Current operational status of a platform component";
   }
   identity ACTIVE {
     base "COMPONENT_OPER_STATUS";
     description
       "Component is enabled and active (i.e., up)";
   }
   identity INACTIVE {
     base "COMPONENT_OPER_STATUS";
     description
       "Component is enabled but inactive (i.e., down)";
   }
   identity DISABLED {
     base "COMPONENT_OPER_STATUS";
     description
       "Component is administratively disabled.";
   }
 }

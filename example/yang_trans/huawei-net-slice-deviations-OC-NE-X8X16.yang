/*
Copyright (C) 2021 Huawei Technologies Co., Ltd. All rights reserved.
*/

 module huawei-net-slice-deviations-OC-NE-X8X16 {
   namespace "urn:huawei:yang:huawei-net-slice-deviations-OC-NE-X8X16";
   prefix "net-slice-devs-OC-NE-X8X16";
   import huawei-net-slice {
     prefix "net-slice";
   }
   import huawei-ifm {
     prefix "ifm";
   }
   import huawei-if-ip {
     prefix "if-ip";
   }
   import huawei-ip {
     prefix "ip";
   }
   import huawei-network-instance {
     prefix "ni";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-net-slice module.";
   revision "2021-05-07" {
     description
       "Initial revision.";
     reference
       "Huawei private.";
   }
   deviation "/ifm:ifm/ifm:interfaces/ifm:interface/net-slice:net-slice-binding/"+
             "net-slice:slice-id" {
     deviate "add" {
       must "not (../../net-slice:net-slices/net-slice:net-slice/net-slice:data-"+
            "plane or ../../net-slice:net-slices/net-slice:net-slice/net-slice:f"+
            "lex-channel) and (../../ip:ipv6 or /ni:network-instance/ni:instance"+
            "s/ni:instance/if-ip:ipv6-ifs/if-ip:ipv6-if[if-ip:name=current()/../"+
            "../ifm:name]) and ((../../ifm:type = 'FlexE' and (../../ip:ipv6/ip:"+
            "addresses/ip:address/ip:ip or /ni:network-instance/ni:instances/ni:"+
            "instance/if-ip:ipv6-ifs/if-ip:ipv6-if[if-ip:name=current()/../../if"+
            "m:name]/if-ip:addresses/if-ip:address/if-ip:ip)) or not (../../ifm:"+
            "type = 'FlexE'))";
     }
   }
   deviation "/ifm:ifm/ifm:interfaces/ifm:interface/net-slice:net-slices/net-sli"+
             "ce:net-slice/net-slice:mode/net-slice:data-plane-mode/net-slice:da"+
             "ta-plane" {
     deviate "add" {
       must "(../../../ip:ipv6 or /ni:network-instance/ni:instances/ni:instance/"+
            "if-ip:ipv6-ifs/if-ip:ipv6-if[if-ip:name=current()/../../../ifm:name"+
            "]) and ((../../../ifm:type = 'FlexE' and ((../../../ip:ipv6/ip:addr"+
            "esses/ip:address/ip:ip or /ni:network-instance/ni:instances/ni:inst"+
            "ance/if-ip:ipv6-ifs/if-ip:ipv6-if/if-ip:addresses/if-ip:address/if-"+
            "ip:ip) or ../../../net-slice:net-slice-binding)) or not (../../../i"+
            "fm:type = 'FlexE'))";
     }
   }
   deviation "/ifm:ifm/ifm:interfaces/ifm:interface/net-slice:net-slices/net-sli"+
             "ce:net-slice/net-slice:mode/net-slice:flex-channel-mode/net-slice:"+
             "flex-channel" {
     deviate "add" {
       must "(../../../ip:ipv6 or /ni:network-instance/ni:instances/ni:instance/"+
            "if-ip:ipv6-ifs/if-ip:ipv6-if[if-ip:name=current()/../../../ifm:name"+
            "]) and ((../../../ifm:type = 'FlexE' and ((../../../ip:ipv6/ip:addr"+
            "esses/ip:address/ip:ip or /ni:network-instance/ni:instances/ni:inst"+
            "ance/if-ip:ipv6-ifs/if-ip:ipv6-if/if-ip:addresses/if-ip:address/if-"+
            "ip:ip) or ../../../net-slice:net-slice-binding)) or not (../../../i"+
            "fm:type = 'FlexE'))";
     }
   }
 }

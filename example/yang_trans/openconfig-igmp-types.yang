module openconfig-igmp-types {
   yang-version "1";
   namespace "http://openconfig.net/yang/igmp/types";
   prefix "oc-igmp-types";
   import openconfig-extensions {
     prefix "oc-ext";
   }
   organization
     "OpenConfig working group";
   contact
     "OpenConfig working group\nwww.openconfig.net";
   description
     "This module defines types related to the IGMP protocol model.";
   oc-ext:openconfig-version "0.1.1";
   revision "2018-11-21" {
     description
       "Add OpenConfig module metadata extensions.";
     reference
       "0.1.1";
   }
   revision "2018-02-19" {
     description
       "Initial revision.";
     reference
       "0.1.0";
   }
   oc-ext:regexp-posix;
   oc-ext:catalog-organization "openconfig";
   oc-ext:origin "openconfig";
 }

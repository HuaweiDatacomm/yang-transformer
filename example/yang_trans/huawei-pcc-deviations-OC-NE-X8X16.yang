/*
Copyright (C) 2020 Huawei Technologies Co., Ltd. All rights reserved.
*/

 module huawei-pcc-deviations-OC-NE-X8X16 {
   namespace "urn:huawei:yang:huawei-pcc-deviations-OC-NE-X8X16";
   prefix "pcc-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Path Computation Client (PCC).";
   revision "2020-12-19" {
     description
       "Initial revision.";
     reference
       "Huawei private.";
   }
 }

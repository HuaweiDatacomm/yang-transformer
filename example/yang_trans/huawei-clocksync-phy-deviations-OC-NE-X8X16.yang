/*
Copyright (C) 2021 Huawei Technologies Co., Ltd. All rights reserved.
*/

 module huawei-clocksync-phy-deviations-OC-NE-X8X16 {
   namespace "urn:huawei:yang:huawei-clocksync-phy-deviations-OC-NE-X8X16";
   prefix "clocksync-phy-devs-OC-NE-X8X16";
   import huawei-clocksync-phy {
     prefix "clocksync-phy";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-clocksync-phy module.";
   revision "2021-05-07" {
     description
       "Initial revision.";
     reference
       "Huawei private.";
   }
   typedef source-selection-mode-deviations {
     type "enumeration" {
       enum "auto" {
         value "0";
         description
           "The source selection mode is the auto mode.";
       }
       enum "force" {
         value "2";
         description
           "The physical layer clock source selection mode is forcible "+
           "selection.";
       }
     }
     description
       "Clock source selection mode: forced clock source selection, manual clock"+
       " source selection, and automatic clock source selection.";
   }
   deviation "/clocksync-phy:clocksync-phy/clocksync-phy:common/clocksync-phy:ss"+
             "m-control-on" {
     deviate "replace" {
       default "false";
     }
   }
   deviation "/clocksync-phy:clocksync-phy/clocksync-phy:common/clocksync-phy:fr"+
             "eq-check-enable" {
     deviate "replace" {
       default "true";
     }
   }
   deviation "/clocksync-phy:clocksync-phy/clocksync-phy:selection-sources/clock"+
             "sync-phy:selection/clocksync-phy:source-name" {
     deviate "add" {
       must "((../source-type='system') and (../mode='force') and ((/ifm:ifm/ifm"+
            ":interfaces/ifm:interface[ifm:name=current()]/clocksync-phy:clock-p"+
            "ort-sources/clocksync-phy:source/clocksync-phy:sync-enable='true' "+
            "and not(/ifm:ifm/ifm:interfaces/ifm:interface[ifm:name=current()]/c"+
            "locksync-phy:clock-port-sources/clocksync-phy:source/clocksync-phy:"+
            "priority/clocksync-phy:system=0)) or (/clocksync-phy:clocksync-phy/"+
            "clocksync-phy:external-clock-sources/clocksync-phy:source[clocksync"+
            "-phy:name=current()]/clocksync-phy:sync-enable='true' and "+
            "not(/clocksync-phy:clocksync-phy/clocksync-phy:external-clock-sourc"+
            "es/clocksync-phy:source[clocksync-phy:name=current()]/clocksync-phy"+
            ":system-priority=0)))) or ((../source-type='sync2m-1') and "+
            "(../mode='force') and (/ifm:ifm/ifm:interfaces/ifm:interface[ifm:na"+
            "me=current()]/clocksync-phy:clock-port-sources/clocksync-phy:source"+
            "/clocksync-phy:sync-enable='true' and not(/ifm:ifm/ifm:interfaces/i"+
            "fm:interface[ifm:name=current()]/clocksync-phy:clock-port-sources/c"+
            "locksync-phy:source/clocksync-phy:priority/clocksync-phy:sync2m1=0)"+
            ")) or ((../source-type='sync2m-2') and (../mode='force') and "+
            "(/ifm:ifm/ifm:interfaces/ifm:interface[ifm:name=current()]/clocksyn"+
            "c-phy:clock-port-sources/clocksync-phy:source/clocksync-phy:sync-en"+
            "able='true' and not(/ifm:ifm/ifm:interfaces/ifm:interface[ifm:name="+
            "current()]/clocksync-phy:clock-port-sources/clocksync-phy:source/cl"+
            "ocksync-phy:priority/clocksync-phy:sync2m2=0)))";
     }
   }
   deviation "/clocksync-phy:clocksync-phy/clocksync-phy:selection-sources/clock"+
             "sync-phy:selection/clocksync-phy:mode" {
     deviate "replace" {
       type "clocksync-phy-devs-OC-NE-X8X16:source-selection-mode-deviations";
     }
   }
   deviation "/clocksync-phy:clocksync-phy/clocksync-phy:external-clock-sources/"+
             "clocksync-phy:source/clocksync-phy:bits-sources/clocksync-phy:sign"+
             "al-type" {
     deviate "add" {
       must "(../signal-type='2mhz' or ../signal-type='2mbps' or ../signal-type="+
            "'1pps' or ../signal-type='dcls')";
     }
   }
 }

submodule ietf-snmp-common {
   belongs-to ietf-snmp {
     prefix "snmp";
   }
   import ietf-yang-types {
     prefix "yang";
   }
   organization
     "IETF NETMOD (NETCONF Data Modeling Language) Working Group";
   contact
     "WG Web:   <http://tools.ietf.org/wg/netmod/>\nWG List:  <mailto:netmod@iet"+
     "f.org>\nWG Chair: Thomas Nadeau\n          <mailto:tnadeau@lucidvision.com"+
     ">\nWG Chair: Juergen Schoenwaelder\n          <mailto:j.schoenwaelder@jaco"+
     "bs-university.de>\nEditor:   Martin Bjorklund\n          <mailto:mbj@tail-"+
     "f.com>\nEditor:   Juergen Schoenwaelder\n          <mailto:j.schoenwaelder"+
     "@jacobs-university.de>";
   description
     "This submodule contains a collection of common YANG definitions\nfor "+
     "configuring SNMP engines.\nCopyright (c) 2014 IETF Trust and the persons "+
     "identified as\nauthors of the code.  All rights reserved.\nRedistribution "+
     "and use in source and binary forms, with or\nwithout modification, is "+
     "permitted pursuant to, and subject\nto the license terms contained in, the"+
     " Simplified BSD License\nset forth in Section 4.c of the IETF Trust's "+
     "Legal Provisions\nRelating to IETF Documents\n(http://trustee.ietf.org/lic"+
     "ense-info).\nThis version of this YANG module is part of RFC 7407; "+
     "see\nthe RFC itself for full legal notices.";
   revision "2014-12-10" {
     description
       "Initial revision.";
     reference
       "RFC 7407: A YANG Data Model for SNMP Configuration";
   }
   typedef admin-string {
     type "string" {
       length "0..255";
     }
     description
       "Represents SnmpAdminString as defined in RFC 3411.\nNote that the size "+
       "of an SnmpAdminString is measured in\noctets, not characters.";
     reference
       "RFC 3411: An Architecture for Describing Simple Network\nManagement "+
       "Protocol (SNMP) Management Frameworks.\nSNMP-FRAMEWORK-MIB.SnmpAdminStri"+
       "ng";
   }
   typedef identifier {
     type "admin-string" {
       length "1..32";
     }
     description
       "Identifiers are used to name items in the SNMP configuration\ndatastore."+
       "";
   }
   typedef context-name {
     type "admin-string" {
       length "0..32";
     }
     description
       "The context type represents an SNMP context name.";
     reference
       "RFC 3411: An Architecture for Describing Simple Network\nManagement "+
       "Protocol (SNMP) Management Frameworks";
   }
   typedef security-name {
     type "admin-string" {
       length "1..32";
     }
     description
       "The security-name type represents an SNMP security name.";
     reference
       "RFC 3411: An Architecture for Describing Simple Network\nManagement "+
       "Protocol (SNMP) Management Frameworks";
   }
   typedef security-model {
     type "union" {
       type "enumeration" {
         enum "v1" {
           value "1";
         }
         enum "v2c" {
           value "2";
         }
         enum "usm" {
           value "3";
         }
         enum "tsm" {
           value "4";
         }
       }
       type "int32" {
         range "1..2147483647";
       }
     }
     reference
       "RFC 3411: An Architecture for Describing Simple Network\nManagement "+
       "Protocol (SNMP) Management Frameworks";
   }
   typedef security-model-or-any {
     type "union" {
       type "enumeration" {
         enum "any" {
           value "0";
         }
       }
       type "security-model";
     }
     reference
       "RFC 3411: An Architecture for Describing Simple Network\nManagement "+
       "Protocol (SNMP) Management Frameworks";
   }
   typedef security-level {
     type "enumeration" {
       enum "no-auth-no-priv" {
         value "1";
       }
       enum "auth-no-priv" {
         value "2";
       }
       enum "auth-priv" {
         value "3";
       }
     }
     reference
       "RFC 3411: An Architecture for Describing Simple Network\nManagement "+
       "Protocol (SNMP) Management Frameworks";
   }
   typedef engine-id {
     type "yang:hex-string" {
       pattern "([0-9a-fA-F]){2}(:([0-9a-fA-F]){2}){4,31}";
     }
     description
       "The engine ID specified as a list of colon-specified\nhexadecimal "+
       "octets, e.g., '80:00:02:b8:04:61:62:63'.";
     reference
       "RFC 3411: An Architecture for Describing Simple Network\nManagement "+
       "Protocol (SNMP) Management Frameworks";
   }
   typedef wildcard-object-identifier {
     type "string";
     description
       "The wildcard-object-identifier type represents an SNMP object\nidentifie"+
       "r where subidentifiers can be given either as a label,\nin numeric form,"+
       " or a wildcard, represented by an asterisk\n('*').";
   }
   typedef tag-value {
     type "string" {
       length "0..255";
     }
     description
       "Represents SnmpTagValue as defined in RFC 3413.\nNote that the size of "+
       "an SnmpTagValue is measured in\noctets, not characters.";
     reference
       "RFC 3413: Simple Network Management Protocol (SNMP)\nApplications.\nSNMP"+
       "-TARGET-MIB.SnmpTagValue";
   }
   container snmp {
     description
       "Top-level container for SNMP-related configuration and\nstatus objects.";
   }
 }

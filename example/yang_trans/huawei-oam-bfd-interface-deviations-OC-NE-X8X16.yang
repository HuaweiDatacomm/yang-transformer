/*
Copyright (C) 2021 Huawei Technologies Co., Ltd. All rights reserved.
*/

 module huawei-oam-bfd-interface-deviations-OC-NE-X8X16 {
   yang-version "1";
   namespace "urn:huawei:yang:huawei-oam-bfd-interface-deviations-OC-NE-X8X16";
   prefix "oam-bfd-interface-devs-OC-NE-X8X16";
   import huawei-oammgr {
     prefix "oammgr";
   }
   import huawei-oam-bfd-interface {
     prefix "oam-bfd-interface";
   }
   import huawei-bfd {
     prefix "bfd";
   }
   import huawei-bfd-static-mpls-te {
     prefix "bfd-static-mpls-te";
   }
   import huawei-bfd-static-vpws {
     prefix "bfd-static-vpws";
   }
   import huawei-bfd-static-vpls {
     prefix "bfd-static-vpls";
   }
   organization
     "Huawei Technologies Co., Ltd.";
   contact
     "Huawei Industrial Base\nBantian, Longgang\nShenzhen 518129\nPeople's "+
     "Republic of China\nWebsite: http://www.huawei.com\nEmail: support@huawei.c"+
     "om";
   description
     "Configure the operation, administration and maintenance (OAM) association "+
     "function.";
   revision "2021-02-04" {
     description
       "Initial revision.";
     reference
       "Huawei private.";
   }
   deviation "/oammgr:oammgr/oam-bfd-interface:bfd-bind-interfaces/oam-bfd-inter"+
             "face:bfd-bind-interface/oam-bfd-interface:name-or-id/oam-bfd-inter"+
             "face:name/oam-bfd-interface:bfd-sess-name" {
     deviate "add" {
       must "count(/oammgr:oammgr/oam-bfd-interface:bfd-bind-interfaces/oam-bfd-"+
            "interface:bfd-bind-interface[oam-bfd-interface:bfd-sess-name=curren"+
            "t()]) <= 1 and count(/oammgr:oammgr/oam-bfd-interface:bfd-bind-inte"+
            "rfaces/oam-bfd-interface:bfd-bind-interface[oam-bfd-interface:bfd-s"+
            "ession-id=(/bfd:bfd/bfd:sessions/bfd:session[bfd:name=current()]/bf"+
            "d:local-discriminator-multicast-ipv4)]) = 0 and count(/oammgr:oammg"+
            "r/oam-bfd-interface:bfd-bind-interfaces/oam-bfd-interface:bfd-bind-"+
            "interface[oam-bfd-interface:bfd-session-id=(/bfd:bfd/bfd:sessions/b"+
            "fd:session[bfd:name=current()]/bfd:local-discriminator)]) = 0 and "+
            "count(/oammgr:oammgr/oam-bfd-interface:bfd-bind-interfaces/oam-bfd-"+
            "interface:bfd-bind-interface[oam-bfd-interface:bfd-session-id=(/bfd"+
            ":bfd/bfd:sessions/bfd:session[bfd:name=current()]/bfd:local-discrim"+
            "inator-static-ipv6)]) = 0 and count(/oammgr:oammgr/oam-bfd-interfac"+
            "e:bfd-bind-interfaces/oam-bfd-interface:bfd-bind-interface[oam-bfd-"+
            "interface:bfd-session-id=(/bfd:bfd/bfd:sessions/bfd:session[bfd:nam"+
            "e=current()]/bfd:local-discriminator-static-ldp-lsp)]) = 0 and "+
            "count(/oammgr:oammgr/oam-bfd-interface:bfd-bind-interfaces/oam-bfd-"+
            "interface:bfd-bind-interface[oam-bfd-interface:bfd-session-id=(/bfd"+
            ":bfd/bfd:sessions/bfd:session[bfd:name=current()]/bfd-static-mpls-t"+
            "e:local-discriminator-static-te-lsp)]) = 0 and count(/oammgr:oammgr"+
            "/oam-bfd-interface:bfd-bind-interfaces/oam-bfd-interface:bfd-bind-i"+
            "nterface[oam-bfd-interface:bfd-session-id=(/bfd:bfd/bfd:sessions/bf"+
            "d:session[bfd:name=current()]/bfd-static-mpls-te:local-discriminato"+
            "r-static-te-tunnel)]) = 0 and (not((/bfd:bfd/bfd:sessions/bfd:sessi"+
            "on[bfd:name=current()]/bfd:bundle-mode-auto-ipv4 and /bfd:bfd/bfd:s"+
            "essions/bfd:session[bfd:name=current()]/bfd:bundle-mode-auto-ipv4 "+
            "!='none') or (/bfd:bfd/bfd:sessions/bfd:session[bfd:name=current()]"+
            "/bfd:bundle-mode-auto-ipv6 and /bfd:bfd/bfd:sessions/bfd:session[bf"+
            "d:name=current()]/bfd:bundle-mode-auto-ipv6 !='none') or (/bfd:bfd/"+
            "bfd:sessions/bfd:session[bfd:name=current()]/bfd-static-vpls:vsi-na"+
            "me-static-vsi-pw) or (/bfd:bfd/bfd:sessions/bfd:session[bfd:name=cu"+
            "rrent()]/bfd-static-vpws:out-if-name-static-vll-pw)))";
     }
   }
   deviation "/oammgr:oammgr/oam-bfd-interface:bfd-bind-interfaces/oam-bfd-inter"+
             "face:bfd-bind-interface/oam-bfd-interface:name-or-id/oam-bfd-inter"+
             "face:id/oam-bfd-interface:bfd-session-id" {
     deviate "add" {
       must "count(/oammgr:oammgr/oam-bfd-interface:bfd-bind-interfaces/oam-bfd-"+
            "interface:bfd-bind-interface[oam-bfd-interface:bfd-session-id=curre"+
            "nt()]) <= 1 and count(/oammgr:oammgr/oam-bfd-interface:bfd-bind-int"+
            "erfaces/oam-bfd-interface:bfd-bind-interface[oam-bfd-interface:bfd-"+
            "sess-name=(/bfd:bfd/bfd:sessions/bfd:session[bfd:local-discriminato"+
            "r-multicast-ipv4=current()]/bfd:name)]) = 0 and count(/oammgr:oammg"+
            "r/oam-bfd-interface:bfd-bind-interfaces/oam-bfd-interface:bfd-bind-"+
            "interface[oam-bfd-interface:bfd-sess-name=(/bfd:bfd/bfd:sessions/bf"+
            "d:session[bfd:local-discriminator=current()]/bfd:name)]) = 0 and "+
            "count(/oammgr:oammgr/oam-bfd-interface:bfd-bind-interfaces/oam-bfd-"+
            "interface:bfd-bind-interface[oam-bfd-interface:bfd-sess-name=(/bfd:"+
            "bfd/bfd:sessions/bfd:session[bfd:local-discriminator-static-ipv6=cu"+
            "rrent()]/bfd:name)]) = 0 and count(/oammgr:oammgr/oam-bfd-interface"+
            ":bfd-bind-interfaces/oam-bfd-interface:bfd-bind-interface[oam-bfd-i"+
            "nterface:bfd-sess-name=(/bfd:bfd/bfd:sessions/bfd:session[bfd:local"+
            "-discriminator-static-ldp-lsp=current()]/bfd:name)]) = 0 and "+
            "count(/oammgr:oammgr/oam-bfd-interface:bfd-bind-interfaces/oam-bfd-"+
            "interface:bfd-bind-interface[oam-bfd-interface:bfd-sess-name=(/bfd:"+
            "bfd/bfd:sessions/bfd:session[bfd-static-mpls-te:local-discriminator"+
            "-static-te-lsp=current()]/bfd:name)]) = 0 and count(/oammgr:oammgr/"+
            "oam-bfd-interface:bfd-bind-interfaces/oam-bfd-interface:bfd-bind-in"+
            "terface[oam-bfd-interface:bfd-sess-name=(/bfd:bfd/bfd:sessions/bfd:"+
            "session[bfd-static-mpls-te:local-discriminator-static-te-tunnel=cur"+
            "rent()]/bfd:name)]) = 0 and (/bfd:bfd/bfd:sessions/bfd:session[bfd:"+
            "local-discriminator-multicast-ipv4=current()] or /bfd:bfd/bfd:sessi"+
            "ons/bfd:session[bfd:local-discriminator=current()] or /bfd:bfd/bfd:"+
            "sessions/bfd:session[bfd:local-discriminator-static-ipv6=current()]"+
            " or /bfd:bfd/bfd:sessions/bfd:session[bfd:local-discriminator-stati"+
            "c-ldp-lsp=current()] or /bfd:bfd/bfd:sessions/bfd:session[bfd-stati"+
            "c-mpls-te:local-discriminator-static-te-lsp=current()] or "+
            "/bfd:bfd/bfd:sessions/bfd:session[bfd-static-mpls-te:local-discrimi"+
            "nator-static-te-tunnel=current()])";
     }
   }
 }

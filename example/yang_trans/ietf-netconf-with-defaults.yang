module ietf-netconf-with-defaults {
   namespace "urn:ietf:params:xml:ns:yang:ietf-netconf-with-defaults";
   prefix "ncwd";
   import ietf-netconf {
     prefix "nc";
   }
   organization
     "IETF NETCONF (Network Configuration Protocol) Working Group";
   contact
     "WG Web:   <http://tools.ietf.org/wg/netconf/>\nWG List:  <netconf@ietf.org"+
     ">\nWG Chair: Bert Wijnen\n          <bertietf@bwijnen.net>\nWG Chair: "+
     "Mehmet Ersue\n          <mehmet.ersue@nsn.com>\nEditor: Andy Bierman\n    "+
     "    <andy.bierman@brocade.com>\nEditor: Balazs Lengyel\n        <balazs.le"+
     "ngyel@ericsson.com>";
   description
     "This module defines an extension to the NETCONF protocol\nthat allows the "+
     "NETCONF client to control how default\nvalues are handled by the server in"+
     " particular NETCONF\noperations.\nCopyright (c) 2011 IETF Trust and the "+
     "persons identified as\nthe document authors.  All rights reserved.\nRedist"+
     "ribution and use in source and binary forms, with or\nwithout modification"+
     ", is permitted pursuant to, and subject\nto the license terms contained "+
     "in, the Simplified BSD License\nset forth in Section 4.c of the IETF "+
     "Trust's Legal Provisions\nRelating to IETF Documents\n(http://trustee.ietf"+
     ".org/license-info).\nThis version of this YANG module is part of RFC 6243;"+
     " see\nthe RFC itself for full legal notices.";
   revision "2011-06-01" {
     description
       "Initial version.";
     reference
       "RFC 6243: With-defaults Capability for NETCONF";
   }
   typedef with-defaults-mode {
     description
       "Possible modes to report default data.";
     reference
       "RFC 6243; Section 3.";
     type "enumeration" {
       enum "report-all" {
         description
           "All default data is reported.";
         reference
           "RFC 6243; Section 3.1";
       }
       enum "report-all-tagged" {
         description
           "All default data is reported.\nAny nodes considered to be default "+
           "data\nwill contain a 'default' XML attribute,\nset to 'true' or "+
           "'1'.";
         reference
           "RFC 6243; Section 3.4";
       }
       enum "trim" {
         description
           "Values are not reported if they contain the default.";
         reference
           "RFC 6243; Section 3.2";
       }
       enum "explicit" {
         description
           "Report values that contain the definition of\nexplicitly set data.";
         reference
           "RFC 6243; Section 3.3";
       }
     }
   }
   augment "/nc:get-config/nc:input" {
     description
       "Adds the <with-defaults> parameter to the\ninput of the NETCONF "+
       "<get-config> operation.";
     reference
       "RFC 6243; Section 4.5.1";
     leaf with-defaults {
       description
         "The explicit defaults processing mode requested.";
       reference
         "RFC 6243; Section 4.5.1";
       type "with-defaults-mode";
     }
   }
   augment "/nc:get/nc:input" {
     description
       "Adds the <with-defaults> parameter to\nthe input of the NETCONF <get> "+
       "operation.";
     reference
       "RFC 6243; Section 4.5.1";
     leaf with-defaults {
       description
         "The explicit defaults processing mode requested.";
       reference
         "RFC 6243; Section 4.5.1";
       type "with-defaults-mode";
     }
   }
   augment "/nc:copy-config/nc:input" {
     description
       "Adds the <with-defaults> parameter to\nthe input of the NETCONF "+
       "<copy-config> operation.";
     reference
       "RFC 6243; Section 4.5.1";
     leaf with-defaults {
       description
         "The explicit defaults processing mode requested.";
       reference
         "RFC 6243; Section 4.5.1";
       type "with-defaults-mode";
     }
   }
 }

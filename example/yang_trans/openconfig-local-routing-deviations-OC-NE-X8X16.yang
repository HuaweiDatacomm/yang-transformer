/*
Copyright (C) 2021 Huawei Technologies Co., Ltd. All rights reserved.
*/

 module openconfig-local-routing-deviations-OC-NE-X8X16 {
   yang-version "1";
   namespace "urn:huawei:yang:openconfig-local-routing-deviations-OC-NE-X8X16";
   prefix "oc-loc-rt-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Deviations for openconfig-local-routing model.";
   revision "2021-06-04" {
     description
       "Initial revision.";
     reference
       "Huawei private.";
   }
 }

/*
Copyright (C) 2021 Huawei Technologies Co., Ltd. All rights reserved.
*/

 module huawei-clocksync-1588v2-deviations-OC-NE-X8X16 {
   namespace "urn:huawei:yang:huawei-clocksync-1588v2-deviations-OC-NE-X8X16";
   prefix "clocksync-1588v2-devs-OC-NE-X8X16";
   import huawei-clocksync-1588v2 {
     prefix "clocksync-1588v2";
   }
   import huawei-ifm {
     prefix "ifm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-clocksync-1588v2 "+
     "module.";
   revision "2021-05-07" {
     description
       "Initial revision.";
     reference
       "Huawei private.";
   }
   deviation "/clocksync-1588v2:clocksync-1588v2/clocksync-1588v2:ptp-common/clo"+
             "cksync-1588v2:profile" {
     deviate "add" {
       must "((../uhpc-enable='false' and ../profile='SMPTE2059-2') or "+
            "../profile!='SMPTE2059-2')";
     }
   }
   deviation "/clocksync-1588v2:clocksync-1588v2/clocksync-1588v2:ptp-common/clo"+
             "cksync-1588v2:std-time-port" {
     deviate "replace" {
       type "leafref" {
         path "/clocksync-1588v2:clocksync-1588v2/clocksync-1588v2:ptp-bits-srcs"+
              "/clocksync-1588v2:ptp-bits-src/clocksync-1588v2:bits-name";
       }
     }
     deviate "add" {
       must "((../../ptp-bits-srcs/ptp-bits-src[clocksync-1588v2:bits-name=curre"+
            "nt()]/clocksync-1588v2:bits-direction='in') and (../../ptp-bits-src"+
            "s/ptp-bits-src[clocksync-1588v2:bits-name=current()]/clocksync-1588"+
            "v2:bits-signal='1pps')) or (../../ptp-bits-srcs/ptp-bits-src[clocks"+
            "ync-1588v2:bits-name=current()]/clocksync-1588v2:bits-signal='dcls'"+
            ")";
     }
   }
   deviation "/clocksync-1588v2:clocksync-1588v2/clocksync-1588v2:ptp-common/clo"+
             "cksync-1588v2:offset-sum-alm-thd" {
     deviate "replace" {
       type "uint32" {
         range "0..1000000000";
       }
     }
   }
   deviation "/clocksync-1588v2:clocksync-1588v2/clocksync-1588v2:ptp-bits-srcs/"+
             "clocksync-1588v2:ptp-bits-src/clocksync-1588v2:bits-signal" {
     deviate "add" {
       must "((../bits-signal='1pps' or ../bits-signal='dcls') and (../bits-dire"+
            "ction='in' or ../bits-direction='out')) or ((../bits-signal='dcls' "+
            "or ../bits-signal='2mbps' or ../bits-signal='2mhz') and (../bits-di"+
            "rection='both'))";
     }
     deviate "add" {
       must "not(../bits-name='bits2' and ../bits-signal='dcls')";
     }
   }
   deviation "/clocksync-1588v2:clocksync-1588v2/clocksync-1588v2:ptp-bits-srcs/"+
             "clocksync-1588v2:ptp-bits-src/clocksync-1588v2:bits-send-delay" {
     deviate "replace" {
       type "int32" {
         range "0..10000";
       }
     }
   }
   deviation "/clocksync-1588v2:clocksync-1588v2/clocksync-1588v2:ptp-bits-srcs/"+
             "clocksync-1588v2:ptp-bits-src/clocksync-1588v2:ptp-bits-bmc-attrs/"+
             "clocksync-1588v2:local-priority" {
     deviate "add" {
       must "(((../../../../clocksync-1588v2:ptp-common/clocksync-1588v2:profile"+
            "='G8275.1') or (../../../../clocksync-1588v2:ptp-common/clocksync-1"+
            "588v2:profile='CU106')) or ((../../../../clocksync-1588v2:ptp-commo"+
            "n/clocksync-1588v2:profile!='G8275.1') and (../../../../clocksync-1"+
            "588v2:ptp-common/clocksync-1588v2:profile!='CU106') and ../clocksyn"+
            "c-1588v2:local-priority=128))";
     }
   }
   deviation "/ifm:ifm/ifm:interfaces/ifm:interface/clocksync-1588v2:ptp-port-sr"+
             "cs/clocksync-1588v2:ptp-port-advance/clocksync-1588v2:clk-step" {
     deviate "add" {
       must "((../clocksync-1588v2:clk-step='onestep') and (/clocksync-1588v2:cl"+
            "ocksync-1588v2/clocksync-1588v2:ptp-common/clocksync-1588v2:uhpc-en"+
            "able='false')) or (../clocksync-1588v2:clk-step='twostep' and "+
            "(((/clocksync-1588v2:clocksync-1588v2/clocksync-1588v2:ptp-common/c"+
            "locksync-1588v2:profile!='CU106' and /clocksync-1588v2:clocksync-15"+
            "88v2/clocksync-1588v2:ptp-common/clocksync-1588v2:profile!='G8275.1"+
            "') and (/clocksync-1588v2:clocksync-1588v2/clocksync-1588v2:ptp-com"+
            "mon/clocksync-1588v2:device-type!='e2etc' and /clocksync-1588v2:clo"+
            "cksync-1588v2/clocksync-1588v2:ptp-common/clocksync-1588v2:device-t"+
            "ype!='p2ptc' and /clocksync-1588v2:clocksync-1588v2/clocksync-1588v"+
            "2:ptp-common/clocksync-1588v2:device-type!='e2etcoc' and /clocksync"+
            "-1588v2:clocksync-1588v2/clocksync-1588v2:ptp-common/clocksync-1588"+
            "v2:device-type!='p2ptcoc' and /clocksync-1588v2:clocksync-1588v2/cl"+
            "ocksync-1588v2:ptp-common/clocksync-1588v2:device-type!='t-tc')) or"+
            " ((/clocksync-1588v2:clocksync-1588v2/clocksync-1588v2:ptp-common/c"+
            "locksync-1588v2:profile='CU106' or /clocksync-1588v2:clocksync-1588"+
            "v2/clocksync-1588v2:ptp-common/clocksync-1588v2:profile='G8275.1') "+
            "and /clocksync-1588v2:clocksync-1588v2/clocksync-1588v2:ptp-common/"+
            "clocksync-1588v2:device-type!='t-tc')) and ((/clocksync-1588v2:cloc"+
            "ksync-1588v2/clocksync-1588v2:ptp-common/clocksync-1588v2:device-ty"+
            "pe='tcandbc' and ../clocksync-1588v2:port-type-set!='tc') or "+
            "/clocksync-1588v2:clocksync-1588v2/clocksync-1588v2:ptp-common/cloc"+
            "ksync-1588v2:device-type!='tcandbc'))";
     }
   }
 }

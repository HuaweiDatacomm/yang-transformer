/*
Copyright (C) 2021 Huawei Technologies Co., Ltd. All rights reserved.
*/

 module huawei-openconfig-telemetry-deviations-OC-NE-X8X16 {
   namespace "urn:huawei:yang:huawei-openconfig-telemetry-deviations-OC-NE-X8X16"+
             "";
   prefix "oc-telemetry-devs-OC-NE-X8X16";
   import openconfig-telemetry {
     prefix "oc-telemetry";
   }
   import openconfig-telemetry-types {
     prefix "oc-telemetry-types";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for openconfig-telemetry module.";
   revision "2021-05-07" {
     description
       "Initial revision.";
     reference
       "Huawei private.";
   }
   deviation "/oc-telemetry:telemetry-system/oc-telemetry:sensor-groups/oc-telem"+
             "etry:sensor-group/oc-telemetry:config/oc-telemetry:sensor-group-id"+
             "" {
     deviate "replace" {
       type "string" {
         length "1..64";
         pattern "[A-Za-z0-9]+";
       }
     }
   }
   deviation "/oc-telemetry:telemetry-system/oc-telemetry:sensor-groups/oc-telem"+
             "etry:sensor-group/oc-telemetry:state/oc-telemetry:sensor-group-id" {
     deviate "replace" {
       type "string" {
         length "1..64";
         pattern "[A-Za-z0-9]+";
       }
     }
   }
   deviation "/oc-telemetry:telemetry-system/oc-telemetry:sensor-groups/oc-telem"+
             "etry:sensor-group/oc-telemetry:sensor-paths/oc-telemetry:sensor-pa"+
             "th/oc-telemetry:config/oc-telemetry:path" {
     deviate "replace" {
       type "string" {
         length "1..511";
       }
     }
   }
   deviation "/oc-telemetry:telemetry-system/oc-telemetry:sensor-groups/oc-telem"+
             "etry:sensor-group/oc-telemetry:sensor-paths/oc-telemetry:sensor-pa"+
             "th/oc-telemetry:state/oc-telemetry:path" {
     deviate "replace" {
       type "string" {
         length "1..511";
       }
     }
   }
   deviation "/oc-telemetry:telemetry-system/oc-telemetry:destination-groups/oc-"+
             "telemetry:destination-group/oc-telemetry:config/oc-telemetry:group"+
             "-id" {
     deviate "replace" {
       type "string" {
         length "1..64";
         pattern "[A-Za-z0-9]+";
       }
     }
   }
   deviation "/oc-telemetry:telemetry-system/oc-telemetry:destination-groups/oc-"+
             "telemetry:destination-group/oc-telemetry:state/oc-telemetry:group-"+
             "id" {
     deviate "replace" {
       type "string" {
         length "1..64";
         pattern "[A-Za-z0-9]+";
       }
     }
   }
   deviation "/oc-telemetry:telemetry-system/oc-telemetry:destination-groups/oc-"+
             "telemetry:destination-group/oc-telemetry:destinations/oc-telemetry"+
             ":destination/oc-telemetry:config/oc-telemetry:destination-port" {
     deviate "replace" {
       type "uint16" {
         range "1..65535";
       }
     }
   }
   deviation "/oc-telemetry:telemetry-system/oc-telemetry:destination-groups/oc-"+
             "telemetry:destination-group/oc-telemetry:destinations/oc-telemetry"+
             ":destination/oc-telemetry:state/oc-telemetry:destination-port" {
     deviate "replace" {
       type "uint16" {
         range "1..65535";
       }
     }
   }
   deviation "/oc-telemetry:telemetry-system/oc-telemetry:subscriptions/oc-telem"+
             "etry:persistent/oc-telemetry:subscription/oc-telemetry:config/oc-t"+
             "elemetry:subscription-name" {
     deviate "replace" {
       type "string" {
         length "1..64";
         pattern "[A-Za-z0-9]+";
       }
     }
   }
   deviation "/oc-telemetry:telemetry-system/oc-telemetry:subscriptions/oc-telem"+
             "etry:persistent/oc-telemetry:subscription/oc-telemetry:config/oc-t"+
             "elemetry:originated-qos-marking" {
     deviate "add" {
       default "0";
     }
   }
   deviation "/oc-telemetry:telemetry-system/oc-telemetry:subscriptions/oc-telem"+
             "etry:persistent/oc-telemetry:subscription/oc-telemetry:config/oc-t"+
             "elemetry:encoding" {
     deviate "add" {
       default "oc-telemetry-types:ENC_PROTO3";
     }
     deviate "add" {
       must "(../oc-telemetry:encoding='oc-telemetry-types:ENC_PROTO3') or "+
            "(../oc-telemetry:encoding='oc-telemetry-types:ENC_JSON_IETF')";
     }
   }
   deviation "/oc-telemetry:telemetry-system/oc-telemetry:subscriptions/oc-telem"+
             "etry:persistent/oc-telemetry:subscription/oc-telemetry:state/oc-te"+
             "lemetry:subscription-name" {
     deviate "replace" {
       type "string" {
         length "1..64";
         pattern "[A-Za-z0-9]+";
       }
     }
   }
   deviation "/oc-telemetry:telemetry-system/oc-telemetry:subscriptions/oc-telem"+
             "etry:persistent/oc-telemetry:subscription/oc-telemetry:state/oc-te"+
             "lemetry:originated-qos-marking" {
     deviate "add" {
       default "0";
     }
   }
   deviation "/oc-telemetry:telemetry-system/oc-telemetry:subscriptions/oc-telem"+
             "etry:persistent/oc-telemetry:subscription/oc-telemetry:state/oc-te"+
             "lemetry:encoding" {
     deviate "add" {
       default "oc-telemetry-types:ENC_PROTO3";
     }
     deviate "add" {
       must "(../oc-telemetry:encoding='oc-telemetry-types:ENC_PROTO3') or "+
            "(../oc-telemetry:encoding='oc-telemetry-types:ENC_JSON_IETF')";
     }
   }
   deviation "/oc-telemetry:telemetry-system/oc-telemetry:subscriptions/oc-telem"+
             "etry:persistent/oc-telemetry:subscription/oc-telemetry:sensor-prof"+
             "iles/oc-telemetry:sensor-profile/oc-telemetry:config" {
     deviate "add" {
       must "not(heartbeat-interval) or sample-interval=0 or ((heartbeat-interva"+
            "l*1000)mod(sample-interval)=0)";
     }
   }
   deviation "/oc-telemetry:telemetry-system/oc-telemetry:subscriptions/oc-telem"+
             "etry:persistent/oc-telemetry:subscription/oc-telemetry:sensor-prof"+
             "iles/oc-telemetry:sensor-profile/oc-telemetry:config/oc-telemetry:"+
             "sample-interval" {
     deviate "replace" {
       type "uint64" {
         range "0|10|100|1000|5000|10000|30000|60000|180000|300000|900000|180000"+
               "0";
       }
     }
     deviate "add" {
       default "60000";
     }
   }
   deviation "/oc-telemetry:telemetry-system/oc-telemetry:subscriptions/oc-telem"+
             "etry:persistent/oc-telemetry:subscription/oc-telemetry:sensor-prof"+
             "iles/oc-telemetry:sensor-profile/oc-telemetry:config/oc-telemetry:"+
             "heartbeat-interval" {
     deviate "replace" {
       type "uint64" {
         range "1..60";
       }
     }
     deviate "add" {
       must "(../oc-telemetry:sample-interval)";
     }
   }
   deviation "/oc-telemetry:telemetry-system/oc-telemetry:subscriptions/oc-telem"+
             "etry:persistent/oc-telemetry:subscription/oc-telemetry:sensor-prof"+
             "iles/oc-telemetry:sensor-profile/oc-telemetry:config/oc-telemetry:"+
             "suppress-redundant" {
     deviate "add" {
       default "false";
     }
   }
   deviation "/oc-telemetry:telemetry-system/oc-telemetry:subscriptions/oc-telem"+
             "etry:persistent/oc-telemetry:subscription/oc-telemetry:sensor-prof"+
             "iles/oc-telemetry:sensor-profile/oc-telemetry:state/oc-telemetry:s"+
             "ample-interval" {
     deviate "replace" {
       type "uint64" {
         range "0|10|100|1000|5000|10000|30000|60000|180000|300000|900000|180000"+
               "0";
       }
     }
     deviate "add" {
       default "60000";
     }
   }
   deviation "/oc-telemetry:telemetry-system/oc-telemetry:subscriptions/oc-telem"+
             "etry:persistent/oc-telemetry:subscription/oc-telemetry:sensor-prof"+
             "iles/oc-telemetry:sensor-profile/oc-telemetry:state/oc-telemetry:h"+
             "eartbeat-interval" {
     deviate "replace" {
       type "uint64" {
         range "1..60";
       }
     }
     deviate "add" {
       must "(../oc-telemetry:sample-interval)";
     }
   }
   deviation "/oc-telemetry:telemetry-system/oc-telemetry:subscriptions/oc-telem"+
             "etry:persistent/oc-telemetry:subscription/oc-telemetry:sensor-prof"+
             "iles/oc-telemetry:sensor-profile/oc-telemetry:state/oc-telemetry:s"+
             "uppress-redundant" {
     deviate "add" {
       default "false";
     }
   }
 }

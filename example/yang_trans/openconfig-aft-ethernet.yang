submodule openconfig-aft-ethernet {
   belongs-to openconfig-aft {
     prefix "oc-aft";
   }
   import openconfig-extensions {
     prefix "oc-ext";
   }
   include openconfig-aft-common;
   organization
     "OpenConfig working group";
   contact
     "OpenConfig working group\nwww.openconfig.net";
   description
     "Submodule containing definitions of groupings for the abstract\nforwarding"+
     " tables for Ethernet.";
   oc-ext:openconfig-version "0.4.0";
   revision "2019-08-02" {
     description
       "Add installing protocol for IPv[46] unicast entries.\nAdd the ability to"+
       " describe conditional next-hop groups\noutside of the policy forwarding "+
       "module to allow for efficient\nhandling of CBTS, where many prefixes may"+
       " share the same next-hop\ncriteria.";
     reference
       "0.4.0";
   }
   revision "2019-08-01" {
     description
       "Add lsp-name leaf to AFT next-hop.";
     reference
       "0.3.3";
   }
   revision "2018-11-21" {
     description
       "Add OpenConfig module metadata extensions.";
     reference
       "0.3.2";
   }
   revision "2017-08-24" {
     description
       "Formatting fixes";
     reference
       "0.3.1";
   }
   revision "2017-05-10" {
     description
       "Refactor to provide concretised per-AF schemas per AFT.";
     reference
       "0.3.0";
   }
 }

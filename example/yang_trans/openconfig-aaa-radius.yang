submodule openconfig-aaa-radius {
   yang-version "1";
   belongs-to openconfig-aaa {
     prefix "oc-aaa";
   }
   import openconfig-extensions {
     prefix "oc-ext";
   }
   import openconfig-aaa-types {
     prefix "oc-aaa-types";
   }
   organization
     "OpenConfig working group";
   contact
     "OpenConfig working group\nwww.openconfig.net";
   description
     "This module defines configuration and operational state data\nrelated to "+
     "the RADIUS protocol for authentication,\nauthorization, and accounting.";
   oc-ext:openconfig-version "0.3.0";
   revision "2017-09-18" {
     description
       "Updated to use OpenConfig types modules";
     reference
       "0.3.0";
   }
   revision "2017-07-06" {
     description
       "Move to oc-inet types, add IETF attribution, add RADIUS\ncounters, "+
       "changed password leaf names to indicate hashed";
     reference
       "0.2.0";
   }
   revision "2017-01-29" {
     description
       "Initial public release";
     reference
       "0.1.0";
   }
   identity RADIUS {
     base "oc-aaa-types:AAA_SERVER_TYPE";
     description
       "Remote Authentication Dial In User Service (RADIUS) AAA\nserver";
     reference
       "RFC 2865 - Remote Authentication Dial In User Service\n(RADIUS)";
   }
 }

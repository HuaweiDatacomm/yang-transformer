module openconfig-system-logging {
   yang-version "1";
   namespace "http://openconfig.net/yang/system/logging";
   prefix "oc-log";
   import openconfig-extensions {
     prefix "oc-ext";
   }
   organization
     "OpenConfig working group";
   contact
     "OpenConfig working group\nwww.openconfig.net";
   description
     "This module defines configuration and operational state data\nfor common "+
     "logging facilities on network systems.";
   oc-ext:openconfig-version "0.3.0";
   revision "2017-09-18" {
     description
       "Updated to use OpenConfig types modules";
     reference
       "0.3.0";
   }
   revision "2017-07-06" {
     description
       "Move to oc-inet types, add IETF attribution, add RADIUS\ncounters, "+
       "changed password leaf names to indicate hashed";
     reference
       "0.2.0";
   }
   revision "2017-01-29" {
     description
       "Initial public release";
     reference
       "0.1.0";
   }
   identity SYSLOG_FACILITY {
     description
       "Base identity for Syslog message facilities.";
     reference
       "IETF RFC 5424 - The Syslog Protocol";
   }
   identity ALL {
     base "SYSLOG_FACILITY";
     description
       "All supported facilities";
   }
   identity KERNEL {
     base "SYSLOG_FACILITY";
     description
       "The facility for kernel messages";
     reference
       "IETF RFC 5424 - The Syslog Protocol";
   }
   identity USER {
     base "SYSLOG_FACILITY";
     description
       "The facility for user-level messages.";
     reference
       "IETF RFC 5424 - The Syslog Protocol";
   }
   identity MAIL {
     base "SYSLOG_FACILITY";
     description
       "The facility for the mail system.";
     reference
       "IETF RFC 5424 - The Syslog Protocol";
   }
   identity SYSTEM_DAEMON {
     base "SYSLOG_FACILITY";
     description
       "The facility for the system daemons.";
     reference
       "IETF RFC 5424 - The Syslog Protocol";
   }
   identity AUTH {
     base "SYSLOG_FACILITY";
     description
       "The facility for security/authorization messages.";
     reference
       "IETF RFC 5424 - The Syslog Protocol";
   }
   identity SYSLOG {
     base "SYSLOG_FACILITY";
     description
       "The facility for messages generated internally by syslogd\nfacility.";
     reference
       "IETF RFC 5424 - The Syslog Protocol";
   }
   identity AUTHPRIV {
     base "SYSLOG_FACILITY";
     description
       "The facility for privileged security/authorization messages.";
     reference
       "IETF RFC 5424 - The Syslog Protocol";
   }
   identity NTP {
     base "SYSLOG_FACILITY";
     description
       "The facility for the NTP subsystem.";
     reference
       "IETF RFC 5424 - The Syslog Protocol";
   }
   identity AUDIT {
     base "SYSLOG_FACILITY";
     description
       "The facility for log audit messages.";
     reference
       "IETF RFC 5424 - The Syslog Protocol";
   }
   identity CONSOLE {
     base "SYSLOG_FACILITY";
     description
       "The facility for log alert messages.";
     reference
       "IETF RFC 5424 - The Syslog Protocol";
   }
   identity LOCAL0 {
     base "SYSLOG_FACILITY";
     description
       "The facility for local use 0 messages.";
     reference
       "IETF RFC 5424 - The Syslog Protocol";
   }
   identity LOCAL1 {
     base "SYSLOG_FACILITY";
     description
       "The facility for local use 1 messages.";
     reference
       "IETF RFC 5424 - The Syslog Protocol";
   }
   identity LOCAL2 {
     base "SYSLOG_FACILITY";
     description
       "The facility for local use 2 messages.";
     reference
       "IETF RFC 5424 - The Syslog Protocol";
   }
   identity LOCAL3 {
     base "SYSLOG_FACILITY";
     description
       "The facility for local use 3 messages.";
     reference
       "IETF RFC 5424 - The Syslog Protocol";
   }
   identity LOCAL4 {
     base "SYSLOG_FACILITY";
     description
       "The facility for local use 4 messages.";
     reference
       "IETF RFC 5424 - The Syslog Protocol";
   }
   identity LOCAL5 {
     base "SYSLOG_FACILITY";
     description
       "The facility for local use 5 messages.";
     reference
       "IETF RFC 5424 - The Syslog Protocol";
   }
   identity LOCAL6 {
     base "SYSLOG_FACILITY";
     description
       "The facility for local use 6 messages.";
     reference
       "IETF RFC 5424 - The Syslog Protocol";
   }
   identity LOCAL7 {
     base "SYSLOG_FACILITY";
     description
       "The facility for local use 7 messages.";
     reference
       "IETF RFC 5424 - The Syslog Protocol";
   }
   identity LOG_DESTINATION_TYPE {
     description
       "Base identity for destination for logging messages";
   }
   identity DEST_CONSOLE {
     base "LOG_DESTINATION_TYPE";
     description
       "Directs log messages to the console";
   }
   identity DEST_BUFFER {
     base "LOG_DESTINATION_TYPE";
     description
       "Directs log messages to and in-memory circular buffer";
   }
   identity DEST_FILE {
     base "LOG_DESTINATION_TYPE";
     description
       "Directs log messages to a local file";
   }
   identity DEST_REMOTE {
     base "LOG_DESTINATION_TYPE";
     description
       "Directs log messages to a remote syslog server";
   }
 }

module openconfig-ospfv2 {
   yang-version "1";
   namespace "http://openconfig.net/yang/ospfv2";
   prefix "oc-ospfv2";
   import openconfig-extensions {
     prefix "oc-ext";
   }
   include openconfig-ospfv2-global;
   include openconfig-ospfv2-area;
   include openconfig-ospfv2-area-interface;
   include openconfig-ospfv2-lsdb;
   include openconfig-ospfv2-common;
   organization
     "OpenConfig working group";
   contact
     "OpenConfig working group\nwww.openconfig.net";
   description
     "An OpenConfig model for Open Shortest Path First (OSPF)\nversion 2";
   oc-ext:openconfig-version "0.2.1";
   revision "2019-11-05" {
     description
       "Fix paths in when statements is LSDB model";
     reference
       "0.2.1";
   }
   revision "2019-07-09" {
     description
       "Normalise all timeticks64 to be expressed in nanoseconds.";
     reference
       "0.2.0";
   }
   revision "2018-11-21" {
     description
       "Add OpenConfig module metadata extensions.";
     reference
       "0.1.3";
   }
   revision "2018-06-05" {
     description
       "Bug fixes in when statements in lsdb";
     reference
       "0.1.2";
   }
   revision "2017-08-24" {
     description
       "Minor formatting fixes.";
     reference
       "0.1.1";
   }
   revision "2017-02-28" {
     description
       "Initial public release of OSPFv2";
     reference
       "0.1.0";
   }
   revision "2016-06-24" {
     description
       "Initial revision";
     reference
       "0.0.1";
   }
   oc-ext:regexp-posix;
   oc-ext:catalog-organization "openconfig";
   oc-ext:origin "openconfig";
 }

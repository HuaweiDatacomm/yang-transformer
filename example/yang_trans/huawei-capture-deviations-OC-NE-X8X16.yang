/*
Copyright (C) 2021 Huawei Technologies Co., Ltd. All rights reserved.
*/

 module huawei-capture-deviations-OC-NE-X8X16 {
   namespace "urn:huawei:yang:huawei-capture-deviations-OC-NE-X8X16";
   prefix "capture-devs-OC-NE-X8X16";
   import huawei-capture {
     prefix "capture";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-capture module.";
   revision "2021-05-07" {
     description
       "Initial revision.";
     reference
       "Huawei private.";
   }
   deviation "/capture:capture-packet/capture:input/capture:interface-name" {
     deviate "add" {
       min-elements "1";
     }
     deviate "add" {
       max-elements "8";
     }
   }
   deviation "/capture:capture-packet/capture:input/capture:packet-number" {
     deviate "replace" {
       type "uint32" {
         range "1..6000";
       }
     }
     deviate "replace" {
       default "10";
     }
   }
   deviation "/capture:capture-packet/capture:input/capture:packet-length" {
     deviate "replace" {
       default "20";
     }
   }
   deviation "/capture:capture-packet/capture:input/capture:timeout" {
     deviate "replace" {
       default "15";
     }
   }
   deviation "/capture:capture-packet/capture:input/capture:file-name" {
     deviate "delete" {
       default "capture.cap";
     }
   }
 }

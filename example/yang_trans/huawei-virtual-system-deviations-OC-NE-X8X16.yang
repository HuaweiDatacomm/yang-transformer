/*
Copyright (C) 2021 Huawei Technologies Co., Ltd. All rights reserved.
*/

 module huawei-virtual-system-deviations-OC-NE-X8X16 {
   namespace "urn:huawei:yang:huawei-virtual-system-deviations-OC-NE-X8X16";
   prefix "vs-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-virtual-system "+
     "module.";
   revision "2021-09-16" {
     description
       "Initial revision.";
     reference
       "Huawei private.";
   }
 }

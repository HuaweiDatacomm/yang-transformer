/*
Copyright (C) 2019 Huawei Technologies Co., Ltd. All rights reserved.
*/

 module huawei-devm-vnf-deviations-OC-NE-X8X16 {
   namespace "urn:huawei:yang:huawei-devm-vnf-deviations-OC-NE-X8X16";
   prefix "devm-vnf-devs-OC-NE-X8X16";
   organization
     "Huawei Technologies Co., Ltd.";
   contact
     "Huawei Industrial Base\nBantian, Longgang\nShenzhen 518129\nPeople's "+
     "Republic of China\nWebsite: http://www.huawei.com\nEmail: support@huawei.c"+
     "om";
   description
     "Global Configuration.";
   revision "2019-08-29" {
     description
       "Initial revision.";
     reference
       "Huawei private.";
   }
 }

/*
Copyright (C) 2019-2020 Huawei Technologies Co., Ltd. All rights reserved.
*/

 module huawei-l2protocol-fwd {
   namespace "urn:huawei:yang:huawei-l2protocol-fwd";
   prefix "l2protocol-fwd";
   import huawei-extension {
     prefix "ext";
   }
   import huawei-ifm {
     prefix "ifm";
   }
   import huawei-l2vpn {
     prefix "l2vpn";
   }
   import huawei-devm {
     prefix "devm";
   }
   import huawei-ethernet {
     prefix "ethernet";
   }
   import huawei-bd {
     prefix "bd";
   }
   import huawei-evpn {
     prefix "evpn";
   }
   import huawei-evpl {
     prefix "evpl";
   }
   import huawei-ifm-trunk {
     prefix "ifm-trunk";
   }
   ext:task-name "l2cpmanagement";
   organization
     "Huawei Technologies Co., Ltd.";
   contact
     "Huawei Industrial Base\nBantian, Longgang\nShenzhen 518129\nPeople's "+
     "Republic of China\nWebsite: http://www.huawei.com\nEmail: support@huawei.c"+
     "om";
   description
     "Forwarding L2 protocol service.";
   revision "2020-03-06" {
     description
       "Change description.";
     reference
       "Huawei private.";
   }
   revision "2019-04-15" {
     description
       "Init revision.";
     reference
       "Huawei private.";
   }
   typedef action-type {
     type "enumeration" {
       enum "transport" {
         value "3";
         description
           "Link protocol transport.";
       }
       enum "transport-tagged" {
         value "4";
         description
           "Link protocol tagged transport.";
       }
       enum "forwarding" {
         value "1";
         description
           "Link protocol forwarding.";
       }
       enum "discard" {
         value "2";
         description
           "Link protocol discard.";
       }
     }
     description
       "Link protocol transport action type.";
   }
   typedef vlan-action-type {
     type "enumeration" {
       enum "forwarding" {
         value "1";
         description
           "Link protocol forwarding.";
       }
     }
     description
       "Link protocol transport action type.";
   }
   typedef mode {
     type "enumeration" {
       enum "normal" {
         value "0";
         description
           "Link protocol transport mode which does not aware VC type.";
       }
       enum "untag" {
         value "1";
         description
           "Link protocol transport mode which support untag packet.";
       }
       enum "untag-vlan-check" {
         value "2";
         description
           "Link protocol transport mode which support untag packet and will "+
           "check port VLAN.";
       }
     }
     description
       "Link protocol transport mode.";
   }
   typedef mode-evpn {
     type "enumeration" {
       enum "normal" {
         value "0";
         description
           "Link protocol transport mode which does not aware VC type.";
       }
       enum "untag" {
         value "1";
         description
           "Link protocol transport mode which support untag packet.";
       }
       enum "untag-vlan-check" {
         value "2";
         description
           "Link protocol transport mode which support untag packet and will "+
           "check port VLAN.";
       }
     }
     description
       "Link protocol transport mode.";
   }
   typedef vlan-protocol-type {
     type "enumeration" {
       enum "lacp" {
         value "1";
         description
           "Link Aggregation Control Protocol.";
       }
     }
     description
       "Link protocol transport protocol type.";
   }
   typedef protocol-type {
     type "enumeration" {
       enum "bpdu" {
         value "4";
         description
           "Bridge protocol data unit.";
       }
       enum "lacp" {
         value "1";
         description
           "Link Aggregation Control Protocol.";
       }
       enum "lldp" {
         value "2";
         description
           "Link Layer Discovery Protocol.";
       }
       enum "cdp" {
         value "5";
         description
           "CDP.";
       }
       enum "udld" {
         value "6";
         description
           "Unidirectional Link Detection.";
       }
     }
     description
       "Link protocol transport protocol type.";
   }
   typedef link-protocol-status {
     type "enumeration" {
       enum "enable" {
         value "1";
         description
           "Link protocol transport function is enabled.";
       }
       enum "disable" {
         value "0";
         description
           "Link protocol transport function is disabled.";
       }
     }
     description
       "Link protocol transport state.";
   }
   augment "/ifm:ifm/ifm:interfaces/ifm:interface/ethernet:ethernet/ethernet:mai"+
           "n-interface/ethernet:l2-attribute" {
     description
       "Link protocol transport lacp.";
     container protocol-actions {
       when "../../../../ifm:type='Ethernet' or ../../../../ifm:type='GigabitEth"+
            "ernet' or ../../../../ifm:type='Eth-Trunk' or ../../../../ifm:type="+
            "'100GE' or ../../../../ifm:type='XGigabitEthernet' or ../../../../i"+
            "fm:type='40GE' or ../../../../ifm:type='10GE' or ../../../../ifm:ty"+
            "pe='400GE' or ../../../../ifm:type='25GE' or ../../../../ifm:type='"+
            "FlexE' or ../../../../ifm:type='50GE' or ../../../../ifm:type='50|1"+
            "00GE'";
       description
         "List of interface link protocol action.";
       list protocol-action {
         must "../../ethernet:pvid or ../../ethernet:trunk-vlans";
         key "protocol-type action";
         max-elements "1";
         description
           "Configure link-protocol action.";
         leaf protocol-type {
           type "vlan-protocol-type";
           description
             "Protocol type.";
         }
         leaf action {
           type "vlan-action-type";
           description
             "Protocol action.";
         }
       }
     }
   }
   augment "/l2vpn:l2vpn/l2vpn:instances/l2vpn:instance/l2vpn:vpws-local-ccc/l2v"+
           "pn:acs/l2vpn:ac" {
     description
       "L2 protocol service for VPWS.";
     container protocol-actions {
       description
         "List of interface link protocol action.";
       list protocol-action {
         must "/ifm:ifm/ifm:interfaces/ifm:interface[ifm:name=current()/../../l2"+
              "vpn:interface-name]/ifm:type='Ethernet' or\n/ifm:ifm/ifm:interfac"+
              "es/ifm:interface[ifm:name=current()/../../l2vpn:interface-name]/i"+
              "fm:type='GigabitEthernet' or\n/ifm:ifm/ifm:interfaces/ifm:interfa"+
              "ce[ifm:name=current()/../../l2vpn:interface-name]/ifm:type='Eth-T"+
              "runk' or\n/ifm:ifm/ifm:interfaces/ifm:interface[ifm:name=current("+
              ")/../../l2vpn:interface-name]/ifm:type='100GE' or\n/ifm:ifm/ifm:i"+
              "nterfaces/ifm:interface[ifm:name=current()/../../l2vpn:interface-"+
              "name]/ifm:type='XGigabitEthernet' or\n/ifm:ifm/ifm:interfaces/ifm"+
              ":interface[ifm:name=current()/../../l2vpn:interface-name]/ifm:typ"+
              "e='40GE' or\n/ifm:ifm/ifm:interfaces/ifm:interface[ifm:name=curre"+
              "nt()/../../l2vpn:interface-name]/ifm:type='10GE' or\n/ifm:ifm/ifm"+
              ":interfaces/ifm:interface[ifm:name=current()/../../l2vpn:interfac"+
              "e-name]/ifm:type='400GE' or\n/ifm:ifm/ifm:interfaces/ifm:interfac"+
              "e[ifm:name=current()/../../l2vpn:interface-name]/ifm:type='25GE' "+
              "or\n/ifm:ifm/ifm:interfaces/ifm:interface[ifm:name=current()/../."+
              "./l2vpn:interface-name]/ifm:type='FlexE' or\n/ifm:ifm/ifm:interfa"+
              "ces/ifm:interface[ifm:name=current()/../../l2vpn:interface-name]/"+
              "ifm:type='50GE' or\n/ifm:ifm/ifm:interfaces/ifm:interface[ifm:nam"+
              "e=current()/../../l2vpn:interface-name]/ifm:type='50|100GE'";
         must "(action='transport' and /ifm:ifm/ifm:interfaces/ifm:interface[ifm"+
              ":name=current()/../../l2vpn:interface-name]/ifm:parent-name "+
              "and\n/ifm:ifm/ifm:interfaces/ifm:interface[ifm:name=current()/../"+
              "../l2vpn:interface-name]/ifm:l2-mode-enable='false' and\n/ifm:ifm"+
              "/ifm:interfaces/ifm:interface[ifm:name=current()/../../l2vpn:inte"+
              "rface-name]/ethernet:ethernet/ethernet:l3-sub-interface/ethernet:"+
              "vlan-type-dot1q) or\n(action='transport-tagged' and /ifm:ifm/ifm:"+
              "interfaces/ifm:interface[ifm:name=current()/../../l2vpn:interface"+
              "-name]/ifm:parent-name and\n/ifm:ifm/ifm:interfaces/ifm:interface"+
              "[ifm:name=current()/../../l2vpn:interface-name]/ifm:l2-mode-enabl"+
              "e='false') or\n(action='discard' and not (/ifm:ifm/ifm:interfaces"+
              "/ifm:interface[ifm:name=current()/../../l2vpn:interface-name]/ifm"+
              ":parent-name))";
         must "action='transport' or (action='transport-tagged' and (protocol-ty"+
              "pe='lacp' or protocol-type='lldp')) or (action='discard' and "+
              "protocol-type='lacp')";
         must "(action='discard' and ((/ifm:ifm/ifm:interfaces/ifm:interface[ifm"+
              ":name=current()/../../l2vpn:interface-name]/ifm:type!='Eth-Trunk'"+
              ") or ((/ifm:ifm/ifm:interfaces/ifm:interface[ifm:name=current()/."+
              "./../l2vpn:interface-name]/ifm:type='Eth-Trunk') and (/ifm:ifm/if"+
              "m:interfaces/ifm:interface[ifm:name=current()/../../l2vpn:interfa"+
              "ce-name]/ifm-trunk:trunk/ifm-trunk:work-mode!='static')))) or "+
              "(action!='discard')";
         must "mode!='untag' or (mode='untag' and /ifm:ifm/ifm:interfaces/ifm:in"+
              "terface[ifm:name=current()/../../l2vpn:interface-name]/ethernet:e"+
              "thernet/ethernet:l3-sub-interface/ethernet:vlan-type-dot1q)";
         must "mode!='untag-vlan-check' or (mode='untag-vlan-check' and "+
              "/ifm:ifm/ifm:interfaces/ifm:interface[ifm:name=current()/../../l2"+
              "vpn:interface-name]/ethernet:ethernet/ethernet:l3-sub-interface/e"+
              "thernet:vlan-type-dot1q)";
         key "protocol-type action";
         description
           "Configure link-protocol action.";
         leaf protocol-type {
           type "protocol-type";
           description
             "Protocol type.";
         }
         leaf action {
           type "action-type";
           description
             "Protocol action.";
         }
         leaf mode {
           when "../action='transport'";
           type "mode";
           mandatory "true";
           description
             "Link-protocol transport mode.";
         }
       }
     }
   }
   augment "/l2vpn:l2vpn/l2vpn:instances/l2vpn:instance/l2vpn:vpws-remote-ccc/l2"+
           "vpn:acs/l2vpn:ac" {
     description
       "L2 protocol service for VPWS.";
     container protocol-actions {
       description
         "List of interface link protocol action.";
       list protocol-action {
         must "/ifm:ifm/ifm:interfaces/ifm:interface[ifm:name=current()/../../l2"+
              "vpn:interface-name]/ifm:type='Ethernet' or\n/ifm:ifm/ifm:interfac"+
              "es/ifm:interface[ifm:name=current()/../../l2vpn:interface-name]/i"+
              "fm:type='GigabitEthernet' or\n/ifm:ifm/ifm:interfaces/ifm:interfa"+
              "ce[ifm:name=current()/../../l2vpn:interface-name]/ifm:type='Eth-T"+
              "runk' or\n/ifm:ifm/ifm:interfaces/ifm:interface[ifm:name=current("+
              ")/../../l2vpn:interface-name]/ifm:type='100GE' or\n/ifm:ifm/ifm:i"+
              "nterfaces/ifm:interface[ifm:name=current()/../../l2vpn:interface-"+
              "name]/ifm:type='XGigabitEthernet' or\n/ifm:ifm/ifm:interfaces/ifm"+
              ":interface[ifm:name=current()/../../l2vpn:interface-name]/ifm:typ"+
              "e='40GE' or\n/ifm:ifm/ifm:interfaces/ifm:interface[ifm:name=curre"+
              "nt()/../../l2vpn:interface-name]/ifm:type='10GE' or\n/ifm:ifm/ifm"+
              ":interfaces/ifm:interface[ifm:name=current()/../../l2vpn:interfac"+
              "e-name]/ifm:type='400GE' or\n/ifm:ifm/ifm:interfaces/ifm:interfac"+
              "e[ifm:name=current()/../../l2vpn:interface-name]/ifm:type='25GE' "+
              "or\n/ifm:ifm/ifm:interfaces/ifm:interface[ifm:name=current()/../."+
              "./l2vpn:interface-name]/ifm:type='FlexE' or\n/ifm:ifm/ifm:interfa"+
              "ces/ifm:interface[ifm:name=current()/../../l2vpn:interface-name]/"+
              "ifm:type='50GE' or\n/ifm:ifm/ifm:interfaces/ifm:interface[ifm:nam"+
              "e=current()/../../l2vpn:interface-name]/ifm:type='50|100GE'";
         must "(action='transport' and /ifm:ifm/ifm:interfaces/ifm:interface[ifm"+
              ":name=current()/../../l2vpn:interface-name]/ifm:parent-name "+
              "and\n/ifm:ifm/ifm:interfaces/ifm:interface[ifm:name=current()/../"+
              "../l2vpn:interface-name]/ifm:l2-mode-enable='false' and\n/ifm:ifm"+
              "/ifm:interfaces/ifm:interface[ifm:name=current()/../../l2vpn:inte"+
              "rface-name]/ethernet:ethernet/ethernet:l3-sub-interface/ethernet:"+
              "vlan-type-dot1q) or\n(action='transport-tagged' and /ifm:ifm/ifm:"+
              "interfaces/ifm:interface[ifm:name=current()/../../l2vpn:interface"+
              "-name]/ifm:parent-name and\n/ifm:ifm/ifm:interfaces/ifm:interface"+
              "[ifm:name=current()/../../l2vpn:interface-name]/ifm:l2-mode-enabl"+
              "e='false') or\n(action='discard' and not (/ifm:ifm/ifm:interfaces"+
              "/ifm:interface[ifm:name=current()/../../l2vpn:interface-name]/ifm"+
              ":parent-name))";
         must "action='transport' or (action='transport-tagged' and (protocol-ty"+
              "pe='lacp' or protocol-type='lldp')) or (action='discard' and "+
              "protocol-type='lacp')";
         must "(action='discard' and ((/ifm:ifm/ifm:interfaces/ifm:interface[ifm"+
              ":name=current()/../../l2vpn:interface-name]/ifm:type!='Eth-Trunk'"+
              ") or ((/ifm:ifm/ifm:interfaces/ifm:interface[ifm:name=current()/."+
              "./../l2vpn:interface-name]/ifm:type='Eth-Trunk') and (/ifm:ifm/if"+
              "m:interfaces/ifm:interface[ifm:name=current()/../../l2vpn:interfa"+
              "ce-name]/ifm-trunk:trunk/ifm-trunk:work-mode!='static')))) or "+
              "(action!='discard')";
         must "mode!='untag' or (mode='untag' and /ifm:ifm/ifm:interfaces/ifm:in"+
              "terface[ifm:name=current()/../../l2vpn:interface-name]/ethernet:e"+
              "thernet/ethernet:l3-sub-interface/ethernet:vlan-type-dot1q)";
         must "mode!='untag-vlan-check' or (mode='untag-vlan-check' and "+
              "/ifm:ifm/ifm:interfaces/ifm:interface[ifm:name=current()/../../l2"+
              "vpn:interface-name]/ethernet:ethernet/ethernet:l3-sub-interface/e"+
              "thernet:vlan-type-dot1q)";
         key "protocol-type action";
         description
           "Configure link-protocol action.";
         leaf protocol-type {
           type "protocol-type";
           description
             "Protocol type.";
         }
         leaf action {
           type "action-type";
           description
             "Protocol action.";
         }
         leaf mode {
           when "../action='transport'";
           type "mode";
           mandatory "true";
           description
             "Link-protocol transport mode.";
         }
       }
     }
   }
   augment "/l2vpn:l2vpn/l2vpn:instances/l2vpn:instance/l2vpn:vpws-ldp/l2vpn:acs"+
           "/l2vpn:ac" {
     description
       "L2 protocol service for VPWS.";
     container protocol-actions {
       description
         "List of interface link protocol action.";
       list protocol-action {
         must "/ifm:ifm/ifm:interfaces/ifm:interface[ifm:name=current()/../../l2"+
              "vpn:interface-name]/ifm:type='Ethernet' or\n/ifm:ifm/ifm:interfac"+
              "es/ifm:interface[ifm:name=current()/../../l2vpn:interface-name]/i"+
              "fm:type='GigabitEthernet' or\n/ifm:ifm/ifm:interfaces/ifm:interfa"+
              "ce[ifm:name=current()/../../l2vpn:interface-name]/ifm:type='Eth-T"+
              "runk' or\n/ifm:ifm/ifm:interfaces/ifm:interface[ifm:name=current("+
              ")/../../l2vpn:interface-name]/ifm:type='100GE' or\n/ifm:ifm/ifm:i"+
              "nterfaces/ifm:interface[ifm:name=current()/../../l2vpn:interface-"+
              "name]/ifm:type='XGigabitEthernet' or\n/ifm:ifm/ifm:interfaces/ifm"+
              ":interface[ifm:name=current()/../../l2vpn:interface-name]/ifm:typ"+
              "e='40GE' or\n/ifm:ifm/ifm:interfaces/ifm:interface[ifm:name=curre"+
              "nt()/../../l2vpn:interface-name]/ifm:type='10GE' or\n/ifm:ifm/ifm"+
              ":interfaces/ifm:interface[ifm:name=current()/../../l2vpn:interfac"+
              "e-name]/ifm:type='400GE' or\n/ifm:ifm/ifm:interfaces/ifm:interfac"+
              "e[ifm:name=current()/../../l2vpn:interface-name]/ifm:type='25GE' "+
              "or\n/ifm:ifm/ifm:interfaces/ifm:interface[ifm:name=current()/../."+
              "./l2vpn:interface-name]/ifm:type='FlexE' or\n/ifm:ifm/ifm:interfa"+
              "ces/ifm:interface[ifm:name=current()/../../l2vpn:interface-name]/"+
              "ifm:type='50GE' or\n/ifm:ifm/ifm:interfaces/ifm:interface[ifm:nam"+
              "e=current()/../../l2vpn:interface-name]/ifm:type='50|100GE'";
         must "mode!='untag' or (mode='untag' and /ifm:ifm/ifm:interfaces/ifm:in"+
              "terface[ifm:name=current()/../../l2vpn:interface-name]/ethernet:e"+
              "thernet/ethernet:l3-sub-interface/ethernet:vlan-type-dot1q)";
         must "mode!='untag-vlan-check' or (mode='untag-vlan-check' and "+
              "/ifm:ifm/ifm:interfaces/ifm:interface[ifm:name=current()/../../l2"+
              "vpn:interface-name]/ethernet:ethernet/ethernet:l3-sub-interface/e"+
              "thernet:vlan-type-dot1q)";
         must "action='transport' or (action='transport-tagged' and (protocol-ty"+
              "pe='lacp' or protocol-type='lldp')) or (action='discard' and "+
              "protocol-type='lacp')";
         must "(action='transport' and\n/ifm:ifm/ifm:interfaces/ifm:interface[if"+
              "m:name=current()/../../l2vpn:interface-name]/ifm:parent-name "+
              "and\n/ifm:ifm/ifm:interfaces/ifm:interface[ifm:name=current()/../"+
              "../l2vpn:interface-name]/ifm:l2-mode-enable='false' and\n/ifm:ifm"+
              "/ifm:interfaces/ifm:interface[ifm:name=current()/../../l2vpn:inte"+
              "rface-name]/ethernet:ethernet/ethernet:l3-sub-interface/ethernet:"+
              "vlan-type-dot1q) or\n(action='transport-tagged' and\n/ifm:ifm/ifm"+
              ":interfaces/ifm:interface[ifm:name=current()/../../l2vpn:interfac"+
              "e-name]/ifm:parent-name and\n/ifm:ifm/ifm:interfaces/ifm:interfac"+
              "e[ifm:name=current()/../../l2vpn:interface-name]/ifm:l2-mode-enab"+
              "le='false') or\n(action='discard' and\nnot (/ifm:ifm/ifm:interfac"+
              "es/ifm:interface[ifm:name=current()/../../l2vpn:interface-name]/i"+
              "fm:parent-name))";
         key "protocol-type action";
         description
           "Configure link-protocol action.";
         leaf protocol-type {
           type "protocol-type";
           description
             "Protocol type.";
         }
         leaf action {
           type "action-type";
           description
             "Protocol action.";
         }
         leaf mode {
           when "../action='transport'";
           type "mode";
           mandatory "true";
           description
             "Link-protocol transport mode.";
         }
       }
     }
   }
   augment "/l2vpn:l2vpn/l2vpn:instances/l2vpn:instance/l2vpn:vpws-bgp/l2vpn:acs"+
           "/l2vpn:ac" {
     description
       "L2 protocol service for VPWS BGP.";
     container protocol-actions {
       description
         "List of interface link protocol action.";
       list protocol-action {
         must "/ifm:ifm/ifm:interfaces/ifm:interface[ifm:name=current()/../../l2"+
              "vpn:interface-name]/ifm:class='sub-interface' and /ifm:ifm/ifm:in"+
              "terfaces/ifm:interface[ifm:name=current()/../../l2vpn:interface-n"+
              "ame]/ifm:l2-mode-enable='false'";
         must "/ifm:ifm/ifm:interfaces/ifm:interface[ifm:name=current()/../../l2"+
              "vpn:interface-name]/ifm:type='Ethernet' or\n/ifm:ifm/ifm:interfac"+
              "es/ifm:interface[ifm:name=current()/../../l2vpn:interface-name]/i"+
              "fm:type='GigabitEthernet' or\n/ifm:ifm/ifm:interfaces/ifm:interfa"+
              "ce[ifm:name=current()/../../l2vpn:interface-name]/ifm:type='Eth-T"+
              "runk' or\n/ifm:ifm/ifm:interfaces/ifm:interface[ifm:name=current("+
              ")/../../l2vpn:interface-name]/ifm:type='100GE' or\n/ifm:ifm/ifm:i"+
              "nterfaces/ifm:interface[ifm:name=current()/../../l2vpn:interface-"+
              "name]/ifm:type='XGigabitEthernet' or\n/ifm:ifm/ifm:interfaces/ifm"+
              ":interface[ifm:name=current()/../../l2vpn:interface-name]/ifm:typ"+
              "e='40GE' or\n/ifm:ifm/ifm:interfaces/ifm:interface[ifm:name=curre"+
              "nt()/../../l2vpn:interface-name]/ifm:type='10GE' or\n/ifm:ifm/ifm"+
              ":interfaces/ifm:interface[ifm:name=current()/../../l2vpn:interfac"+
              "e-name]/ifm:type='400GE' or\n/ifm:ifm/ifm:interfaces/ifm:interfac"+
              "e[ifm:name=current()/../../l2vpn:interface-name]/ifm:type='25GE' "+
              "or\n/ifm:ifm/ifm:interfaces/ifm:interface[ifm:name=current()/../."+
              "./l2vpn:interface-name]/ifm:type='FlexE' or\n/ifm:ifm/ifm:interfa"+
              "ces/ifm:interface[ifm:name=current()/../../l2vpn:interface-name]/"+
              "ifm:type='50GE' or\n/ifm:ifm/ifm:interfaces/ifm:interface[ifm:nam"+
              "e=current()/../../l2vpn:interface-name]/ifm:type='50|100GE'";
         must "mode!='untag' or (mode='untag' and /ifm:ifm/ifm:interfaces/ifm:in"+
              "terface[ifm:name=current()/../../l2vpn:interface-name]/ethernet:e"+
              "thernet/ethernet:l3-sub-interface/ethernet:vlan-type-dot1q)";
         must "mode!='untag-vlan-check' or (mode='untag-vlan-check' and "+
              "/ifm:ifm/ifm:interfaces/ifm:interface[ifm:name=current()/../../l2"+
              "vpn:interface-name]/ethernet:ethernet/ethernet:l3-sub-interface/e"+
              "thernet:vlan-type-dot1q)";
         must "action='transport' or (action='transport-tagged' and (protocol-ty"+
              "pe='lacp' or protocol-type='lldp'))";
         must "(action='transport' and /ifm:ifm/ifm:interfaces/ifm:interface[ifm"+
              ":name=current()/../../l2vpn:interface-name]/ethernet:ethernet/eth"+
              "ernet:l3-sub-interface/ethernet:vlan-type-dot1q) or action='trans"+
              "port-tagged'";
         key "protocol-type action";
         description
           "Configure link-protocol action.";
         leaf protocol-type {
           type "protocol-type";
           description
             "Protocol type.";
         }
         leaf action {
           type "action-type";
           description
             "Protocol action.";
         }
         leaf mode {
           when "../action='transport'";
           type "mode";
           mandatory "true";
           description
             "Link-protocol transport mode.";
         }
       }
     }
   }
   augment "/l2vpn:l2vpn/l2vpn:instances/l2vpn:instance/l2vpn:vpls/l2vpn:acs/l2v"+
           "pn:ac" {
     description
       "L2 protocol service for VSI.";
     container protocol-actions {
       description
         "List of interface link protocol action.";
       list protocol-action {
         must "/ifm:ifm/ifm:interfaces/ifm:interface[ifm:name=current()/../../l2"+
              "vpn:interface-name]/ifm:type='Ethernet' or\n/ifm:ifm/ifm:interfac"+
              "es/ifm:interface[ifm:name=current()/../../l2vpn:interface-name]/i"+
              "fm:type='GigabitEthernet' or\n/ifm:ifm/ifm:interfaces/ifm:interfa"+
              "ce[ifm:name=current()/../../l2vpn:interface-name]/ifm:type='Eth-T"+
              "runk' or\n/ifm:ifm/ifm:interfaces/ifm:interface[ifm:name=current("+
              ")/../../l2vpn:interface-name]/ifm:type='100GE' or\n/ifm:ifm/ifm:i"+
              "nterfaces/ifm:interface[ifm:name=current()/../../l2vpn:interface-"+
              "name]/ifm:type='XGigabitEthernet' or\n/ifm:ifm/ifm:interfaces/ifm"+
              ":interface[ifm:name=current()/../../l2vpn:interface-name]/ifm:typ"+
              "e='40GE' or\n/ifm:ifm/ifm:interfaces/ifm:interface[ifm:name=curre"+
              "nt()/../../l2vpn:interface-name]/ifm:type='10GE' or\n/ifm:ifm/ifm"+
              ":interfaces/ifm:interface[ifm:name=current()/../../l2vpn:interfac"+
              "e-name]/ifm:type='400GE' or\n/ifm:ifm/ifm:interfaces/ifm:interfac"+
              "e[ifm:name=current()/../../l2vpn:interface-name]/ifm:type='25GE' "+
              "or\n/ifm:ifm/ifm:interfaces/ifm:interface[ifm:name=current()/../."+
              "./l2vpn:interface-name]/ifm:type='FlexE' or\n/ifm:ifm/ifm:interfa"+
              "ces/ifm:interface[ifm:name=current()/../../l2vpn:interface-name]/"+
              "ifm:type='50GE' or\n/ifm:ifm/ifm:interfaces/ifm:interface[ifm:nam"+
              "e=current()/../../l2vpn:interface-name]/ifm:type='50|100GE'";
         must "mode!='untag' or (mode='untag' and /ifm:ifm/ifm:interfaces/ifm:in"+
              "terface[ifm:name=current()/../../l2vpn:interface-name]/ethernet:e"+
              "thernet/ethernet:l3-sub-interface/ethernet:vlan-type-dot1q)";
         must "mode!='untag-vlan-check' or (mode='untag-vlan-check' and "+
              "/ifm:ifm/ifm:interfaces/ifm:interface[ifm:name=current()/../../l2"+
              "vpn:interface-name]/ethernet:ethernet/ethernet:l3-sub-interface/e"+
              "thernet:vlan-type-dot1q)";
         must "(action='transport' and\n/ifm:ifm/ifm:interfaces/ifm:interface[if"+
              "m:name=current()/../../l2vpn:interface-name]/ifm:parent-name "+
              "and\n/ifm:ifm/ifm:interfaces/ifm:interface[ifm:name=current()/../"+
              "../l2vpn:interface-name]/ethernet:ethernet/ethernet:l3-sub-interf"+
              "ace/ethernet:vlan-type-dot1q) or\n(action='forwarding' and\nnot "+
              "(/ifm:ifm/ifm:interfaces/ifm:interface[ifm:name=current()/../../l"+
              "2vpn:interface-name]/ifm:parent-name))";
         must "action='transport' or (action='forwarding' and protocol-type='lac"+
              "p')";
         key "protocol-type action";
         description
           "Configure link-protocol action.";
         leaf protocol-type {
           type "protocol-type";
           description
             "Protocol type.";
         }
         leaf action {
           type "action-type";
           description
             "Protocol action.";
         }
         leaf mode {
           when "../action='transport'";
           type "mode";
           mandatory "true";
           description
             "Link-protocol transport mode.";
         }
       }
     }
   }
   augment "/bd:bd/bd:instances/bd:instance/bd:service-points/bd:service-point" {
     description
       "L2 protocol service for BD.";
     container protocol-actions {
       description
         "List of interface link protocol action.";
       list protocol-action {
         must "/ifm:ifm/ifm:interfaces/ifm:interface[ifm:name=current()/../../bd"+
              ":interface-name]/ifm:type='Ethernet' or\n/ifm:ifm/ifm:interfaces/"+
              "ifm:interface[ifm:name=current()/../../bd:interface-name]/ifm:typ"+
              "e='GigabitEthernet' or\n/ifm:ifm/ifm:interfaces/ifm:interface[ifm"+
              ":name=current()/../../bd:interface-name]/ifm:type='Eth-Trunk' "+
              "or\n/ifm:ifm/ifm:interfaces/ifm:interface[ifm:name=current()/../."+
              "./bd:interface-name]/ifm:type='100GE' or\n/ifm:ifm/ifm:interfaces"+
              "/ifm:interface[ifm:name=current()/../../bd:interface-name]/ifm:ty"+
              "pe='XGigabitEthernet' or\n/ifm:ifm/ifm:interfaces/ifm:interface[i"+
              "fm:name=current()/../../bd:interface-name]/ifm:type='40GE' "+
              "or\n/ifm:ifm/ifm:interfaces/ifm:interface[ifm:name=current()/../."+
              "./bd:interface-name]/ifm:type='10GE' or\n/ifm:ifm/ifm:interfaces/"+
              "ifm:interface[ifm:name=current()/../../bd:interface-name]/ifm:typ"+
              "e='400GE' or\n/ifm:ifm/ifm:interfaces/ifm:interface[ifm:name=curr"+
              "ent()/../../bd:interface-name]/ifm:type='25GE' or\n/ifm:ifm/ifm:i"+
              "nterfaces/ifm:interface[ifm:name=current()/../../bd:interface-nam"+
              "e]/ifm:type='FlexE' or\n/ifm:ifm/ifm:interfaces/ifm:interface[ifm"+
              ":name=current()/../../bd:interface-name]/ifm:type='50GE' "+
              "or\n/ifm:ifm/ifm:interfaces/ifm:interface[ifm:name=current()/../."+
              "./bd:interface-name]/ifm:type='50|100GE'";
         must "action='transport' and\n(/ifm:ifm/ifm:interfaces/ifm:interface[if"+
              "m:name=current()/../../bd:interface-name]/ethernet:ethernet/ether"+
              "net:l2-sub-interface/ethernet:dot1q/ethernet:vlans or\n((/ifm:ifm"+
              "/ifm:interfaces/ifm:interface[ifm:name=current()/../../bd:interfa"+
              "ce-name]/ethernet:ethernet/ethernet:l2-sub-interface/ethernet:dot"+
              "1q/ethernet:policy-vlans or\n/ifm:ifm/ifm:interfaces/ifm:interfac"+
              "e[ifm:name=current()/../../bd:interface-name]/ethernet:ethernet/e"+
              "thernet:l2-sub-interface/ethernet:default or\n/ifm:ifm/ifm:interf"+
              "aces/ifm:interface[ifm:name=current()/../../bd:interface-name]/et"+
              "hernet:ethernet/ethernet:l2-sub-interface/ethernet:untag "+
              "or\n/ifm:ifm/ifm:interfaces/ifm:interface[ifm:name=current()/../."+
              "./bd:interface-name]/ethernet:ethernet/ethernet:l2-sub-interface/"+
              "ethernet:qinqs) and (mode='untag') or (mode='untag-vlan-check')))"+
              " and\n(not (/ifm:ifm/ifm:interfaces/ifm:interface[ifm:name=curren"+
              "t()/../../bd:interface-name]/ethernet:ethernet/ethernet:l2-sub-in"+
              "terface/ethernet:flow-action) or (mode='untag') or (mode='untag-v"+
              "lan-check')) and\n((/l2vpn:l2vpn/l2vpn:instances/l2vpn:instance/l"+
              "2vpn:vpls/l2vpn:bds/l2vpn:bd[l2vpn:id=current()/../../../../bd:id"+
              "]) or ../../../../evpn:evpn)";
         key "protocol-type action";
         description
           "Configure link-protocol action.";
         leaf protocol-type {
           type "protocol-type";
           description
             "Protocol type.";
         }
         leaf action {
           type "action-type";
           description
             "Protocol action.";
         }
         leaf mode {
           when "../action='transport'";
           type "mode-evpn";
           mandatory "true";
           description
             "Link-protocol transport mode.";
         }
       }
     }
   }
   augment "/evpl:evpl/evpl:instances/evpl:instance/evpl:interfaces/evpl:interfa"+
           "ce" {
     description
       "L2 protocol service for EVPL.";
     container protocol-actions {
       description
         "List of interface link protocol action.";
       list protocol-action {
         must "/ifm:ifm/ifm:interfaces/ifm:interface[ifm:name=current()/../../ev"+
              "pl:name]/ifm:type='Ethernet' or\n/ifm:ifm/ifm:interfaces/ifm:inte"+
              "rface[ifm:name=current()/../../evpl:name]/ifm:type='GigabitEthern"+
              "et' or\n/ifm:ifm/ifm:interfaces/ifm:interface[ifm:name=current()/"+
              "../../evpl:name]/ifm:type='Eth-Trunk' or\n/ifm:ifm/ifm:interfaces"+
              "/ifm:interface[ifm:name=current()/../../evpl:name]/ifm:type='100G"+
              "E' or\n/ifm:ifm/ifm:interfaces/ifm:interface[ifm:name=current()/."+
              "./../evpl:name]/ifm:type='XGigabitEthernet' or\n/ifm:ifm/ifm:inte"+
              "rfaces/ifm:interface[ifm:name=current()/../../evpl:name]/ifm:type"+
              "='40GE' or\n/ifm:ifm/ifm:interfaces/ifm:interface[ifm:name=curren"+
              "t()/../../evpl:name]/ifm:type='10GE' or\n/ifm:ifm/ifm:interfaces/"+
              "ifm:interface[ifm:name=current()/../../evpl:name]/ifm:type='400GE"+
              "' or\n/ifm:ifm/ifm:interfaces/ifm:interface[ifm:name=current()/.."+
              "/../evpl:name]/ifm:type='25GE' or\n/ifm:ifm/ifm:interfaces/ifm:in"+
              "terface[ifm:name=current()/../../evpl:name]/ifm:type='FlexE' "+
              "or\n/ifm:ifm/ifm:interfaces/ifm:interface[ifm:name=current()/../."+
              "./evpl:name]/ifm:type='50GE' or\n/ifm:ifm/ifm:interfaces/ifm:inte"+
              "rface[ifm:name=current()/../../evpl:name]/ifm:type='50|100GE'";
         must "/ifm:ifm/ifm:interfaces/ifm:interface[ifm:name=current()/../../ev"+
              "pl:name]/ifm:parent-name and /ifm:ifm/ifm:interfaces/ifm:interfac"+
              "e[ifm:name=current()/../../evpl:name]/ifm:l2-mode-enable='false'";
         must "(action='transport' and /ifm:ifm/ifm:interfaces/ifm:interface[ifm"+
              ":name=current()/../../evpl:name]/ethernet:ethernet/ethernet:l3-su"+
              "b-interface/ethernet:vlan-type-dot1q) or (action='transport-tagge"+
              "d' and (protocol-type='lacp' or protocol-type='lldp'))";
         key "protocol-type action";
         description
           "Configure link-protocol action.";
         leaf protocol-type {
           type "protocol-type";
           description
             "Protocol type.";
         }
         leaf action {
           type "action-type";
           description
             "Protocol action.";
         }
         leaf mode {
           when "../action='transport'";
           type "mode-evpn";
           mandatory "true";
           description
             "Link-protocol transport mode.";
         }
       }
     }
   }
   augment "/ifm:ifm/ifm:interfaces/ifm:interface/evpn:evpn" {
     description
       "L2 protocol service for EVPN.";
     container protocol-actions {
       when "(../../ifm:type='Ethernet' or ../../ifm:type='GigabitEthernet' or "+
            "../../ifm:type='Eth-Trunk' or ../../ifm:type='100GE' or ../../ifm:t"+
            "ype='XGigabitEthernet' or ../../ifm:type='40GE' or ../../ifm:type='"+
            "10GE' or ../../ifm:type='400GE' or ../../ifm:type='25GE' or "+
            "../../ifm:type='FlexE' or ../../ifm:type='50GE' or ../../ifm:type='"+
            "50|100GE') and ../evpn:name";
       description
         "List of interface link protocol action.";
       list protocol-action {
         key "protocol-type action";
         description
           "Configure link-protocol action.";
         leaf protocol-type {
           type "protocol-type";
           description
             "Protocol type.";
         }
         leaf action {
           type "action-type";
           description
             "Protocol action.";
         }
         leaf mode {
           when "../action='transport'";
           type "mode-evpn";
           mandatory "true";
           description
             "Link-protocol transport mode.";
         }
         must "(action='transport' and\n../../../ifm:parent-name and\n../../../i"+
              "fm:l2-mode-enable='false' and\n../../../ethernet:ethernet/etherne"+
              "t:l3-sub-interface/ethernet:vlan-type-dot1q) or\n(action='forward"+
              "ing' and not (../../../ifm:parent-name))";
         must "action='transport' or\n(action='forwarding' and protocol-type='la"+
              "cp')";
       }
     }
   }
   augment "/devm:devm/devm:lpu-boards/devm:lpu-board" {
     description
       "L2 protocol transport configuration.";
     container link-protocol-transport {
       description
         "Configure transparent transmission of link-layer protocol information."+
         "";
       leaf lldp {
         type "link-protocol-status";
         default "disable";
         description
           "Link Layer Discovery Protocol.";
       }
       leaf lacp {
         type "link-protocol-status";
         default "disable";
         description
           "Link Aggregation Control Protocol.";
       }
       leaf oam {
         type "link-protocol-status";
         default "disable";
         description
           "Operation, Administration and Maintenance Protocol.";
       }
       leaf esmc {
         type "link-protocol-status";
         default "disable";
         description
           "Ethernet Synchronization Messaging Channel.";
       }
     }
   }
   augment "/devm:devm/devm:mpu-boards/devm:mpu-board" {
     description
       "L2 protocol transport configuration.";
   }
 }

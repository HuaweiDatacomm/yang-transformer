/*
Copyright (C) 2021 Huawei Technologies Co., Ltd. All rights reserved.
*/

 module huawei-bras-l2tp-access-deviations-OC-NE-X8X16 {
   namespace "urn:huawei:yang:huawei-bras-l2tp-access-deviations-OC-NE-X8X16";
   prefix "bras-l2tp-access-devs-OC-NE-X8X16";
   import huawei-bras-l2tp-access {
     prefix "bras-l2tp-access";
   }
   import huawei-devm {
     prefix "devm";
   }
   organization
     "Huawei Technologies Co., Ltd.";
   contact
     "Huawei Industrial Base\nBantian, Longgang\nShenzhen 518129\nPeople's "+
     "Republic of China\nWebsite: http://www.huawei.com\nEmail: support@huawei.c"+
     "om";
   description
     "This module defines deviation statements for huawei-bras-l2tp-access "+
     "module.";
   revision "2021-05-07" {
     description
       "Initial revision.";
     reference
       "Huawei private.";
   }
   deviation "/bras-l2tp-access:bras-l2tp-access/bras-l2tp-access:lns-global/bra"+
             "s-l2tp-access:lns-fast-replys/bras-l2tp-access:lns-fast-reply/bras"+
             "-l2tp-access:slot-id" {
     deviate "replace" {
       type "leafref" {
         path "/devm:devm/devm:lpu-boards/devm:lpu-board/devm:position";
       }
     }
   }
   deviation "/bras-l2tp-access:bras-l2tp-access/bras-l2tp-access:lns-global/bra"+
             "s-l2tp-access:slot-block/bras-l2tp-access:slot-id" {
     deviate "replace" {
       type "leafref" {
         path "/devm:devm/devm:lpu-boards/devm:lpu-board/devm:position";
       }
     }
   }
   deviation "/bras-l2tp-access:bras-l2tp-access/bras-l2tp-access:lns-groups/bra"+
             "s-l2tp-access:lns-group/bras-l2tp-access:bind-board/bras-l2tp-acce"+
             "ss:bind-slots/bras-l2tp-access:bind-slots/bras-l2tp-access:bind-sl"+
             "ot/bras-l2tp-access:slot-id" {
     deviate "replace" {
       type "leafref" {
         path "/devm:devm/devm:lpu-boards/devm:lpu-board/devm:position";
       }
     }
   }
   deviation "/bras-l2tp-access:bras-l2tp-access/bras-l2tp-access:lns-backup-gro"+
             "ups/bras-l2tp-access:lns-backup-group/bras-l2tp-access:bind-slots/"+
             "bras-l2tp-access:master-slot-id" {
     deviate "replace" {
       type "leafref" {
         path "/devm:devm/devm:lpu-boards/devm:lpu-board/devm:position";
       }
     }
   }
   deviation "/bras-l2tp-access:bras-l2tp-access/bras-l2tp-access:lns-backup-gro"+
             "ups/bras-l2tp-access:lns-backup-group/bras-l2tp-access:bind-slots/"+
             "bras-l2tp-access:slave-slot-id" {
     deviate "replace" {
       type "leafref" {
         path "/devm:devm/devm:lpu-boards/devm:lpu-board/devm:position";
       }
     }
   }
 }
